-- *****************************************************************
-- MRP-MIB:  Microsemi ENT private MIB
-- ****************************************************************

VTSS-MRP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    Unsigned32 FROM SNMPv2-SMI
    TruthValue FROM SNMPv2-TC
    VTSSInterfaceIndex FROM VTSS-TC
    ;

vtssMrpMib MODULE-IDENTITY
    LAST-UPDATED "201510190000Z"
    ORGANIZATION
        "Microsemi Corporation"
    CONTACT-INFO
        "Application support: http://www.microchip.com/support"
    DESCRIPTION
        "Private MRP MIB."
    REVISION    "201510190000Z"
    DESCRIPTION
        "Initial version"
    ::= { vtssSwitchMgmt 86 }


vtssMrpMibObjects OBJECT IDENTIFIER
    ::= { vtssMrpMib 1 }

vtssMrpCapabilities OBJECT IDENTIFIER
    ::= { vtssMrpMibObjects 1 }

vtssMrpCapabilitiesJoinTimeoutMin OBJECT-TYPE
    SYNTAX      Unsigned32
    MAX-ACCESS  read-only
    STATUS      current
    DESCRIPTION
        "Minimum value of MRP Join timeout in centiseconds."
    ::= { vtssMrpCapabilities 1 }

vtssMrpCapabilitiesJoinTimeoutMax OBJECT-TYPE
    SYNTAX      Unsigned32
    MAX-ACCESS  read-only
    STATUS      current
    DESCRIPTION
        "Maximum value of MRP Join timeout in centiseconds."
    ::= { vtssMrpCapabilities 2 }

vtssMrpCapabilitiesLeaveTimeoutMin OBJECT-TYPE
    SYNTAX      Unsigned32
    MAX-ACCESS  read-only
    STATUS      current
    DESCRIPTION
        "Minimum value of MRP Leave timeout in centiseconds."
    ::= { vtssMrpCapabilities 3 }

vtssMrpCapabilitiesLeaveTimeoutMax OBJECT-TYPE
    SYNTAX      Unsigned32
    MAX-ACCESS  read-only
    STATUS      current
    DESCRIPTION
        "Maximum value of MRP Leave timeout in centiseconds."
    ::= { vtssMrpCapabilities 4 }

vtssMrpCapabilitiesLeaveAllTimeoutMin OBJECT-TYPE
    SYNTAX      Unsigned32
    MAX-ACCESS  read-only
    STATUS      current
    DESCRIPTION
        "Minimum value of MRP LeaveAll timeout in centiseconds."
    ::= { vtssMrpCapabilities 5 }

vtssMrpCapabilitiesLeaveAllTimeoutMax OBJECT-TYPE
    SYNTAX      Unsigned32
    MAX-ACCESS  read-only
    STATUS      current
    DESCRIPTION
        "Maximum value of MRP LeaveAll timeout in centiseconds."
    ::= { vtssMrpCapabilities 6 }

vtssMrpConfig OBJECT IDENTIFIER
    ::= { vtssMrpMibObjects 2 }

vtssMrpConfigInterface OBJECT IDENTIFIER
    ::= { vtssMrpConfig 1 }

vtssMrpConfigInterfaceTable OBJECT-TYPE
    SYNTAX      SEQUENCE OF VTSSMrpConfigInterfaceEntry
    MAX-ACCESS  not-accessible
    STATUS      current
    DESCRIPTION
        "This is the MRP interface configuration table. The number of interfaces
         is the total number of ports available on the switch/stack. MRP timer
         values and the state of the PeriodicTransmission STM can be configured
         for each interface."
    ::= { vtssMrpConfigInterface 1 }

vtssMrpConfigInterfaceEntry OBJECT-TYPE
    SYNTAX      VTSSMrpConfigInterfaceEntry
    MAX-ACCESS  not-accessible
    STATUS      current
    DESCRIPTION
        "Each entry has a set of parameters."
    INDEX       { vtssMrpConfigInterfaceIfIndex }
    ::= { vtssMrpConfigInterfaceTable 1 }

VTSSMrpConfigInterfaceEntry ::= SEQUENCE {
    vtssMrpConfigInterfaceIfIndex               VTSSInterfaceIndex,
    vtssMrpConfigInterfaceJoinTimeout           Integer32,
    vtssMrpConfigInterfaceLeaveTimeout          Integer32,
    vtssMrpConfigInterfaceLeaveAllTimeout       Integer32,
    vtssMrpConfigInterfacePeriodicTransmission  TruthValue
}

vtssMrpConfigInterfaceIfIndex OBJECT-TYPE
    SYNTAX      VTSSInterfaceIndex
    MAX-ACCESS  accessible-for-notify
    STATUS      current
    DESCRIPTION
        "Interface index number."
    ::= { vtssMrpConfigInterfaceEntry 1 }

vtssMrpConfigInterfaceJoinTimeout OBJECT-TYPE
    SYNTAX      Integer32 (1..20)
    MAX-ACCESS  read-write
    STATUS      current
    DESCRIPTION
        "Join-timeout protocol parameter. Range [1, 20]cs."
    ::= { vtssMrpConfigInterfaceEntry 2 }

vtssMrpConfigInterfaceLeaveTimeout OBJECT-TYPE
    SYNTAX      Integer32 (60..300)
    MAX-ACCESS  read-write
    STATUS      current
    DESCRIPTION
        "Leave-timeout protocol parameter. Range [60, 300]cs."
    ::= { vtssMrpConfigInterfaceEntry 3 }

vtssMrpConfigInterfaceLeaveAllTimeout OBJECT-TYPE
    SYNTAX      Integer32 (1000..5000)
    MAX-ACCESS  read-write
    STATUS      current
    DESCRIPTION
        "LeaveAll-timeout protocol parameter. Range [1000, 5000] cs."
    ::= { vtssMrpConfigInterfaceEntry 4 }

vtssMrpConfigInterfacePeriodicTransmission OBJECT-TYPE
    SYNTAX      TruthValue
    MAX-ACCESS  read-write
    STATUS      current
    DESCRIPTION
        "PeriodicTransmission state of MRP. TRUE - enable PeriodicTransmission,
         FALSE - disable PeriodicTransmission."
    ::= { vtssMrpConfigInterfaceEntry 5 }

vtssMrpMibConformance OBJECT IDENTIFIER
    ::= { vtssMrpMib 2 }

vtssMrpMibCompliances OBJECT IDENTIFIER
    ::= { vtssMrpMibConformance 1 }

vtssMrpMibGroups OBJECT IDENTIFIER
    ::= { vtssMrpMibConformance 2 }

vtssMrpCapabilitiesInfoGroup OBJECT-GROUP
    OBJECTS     { vtssMrpCapabilitiesJoinTimeoutMin,
                  vtssMrpCapabilitiesJoinTimeoutMax,
                  vtssMrpCapabilitiesLeaveTimeoutMin,
                  vtssMrpCapabilitiesLeaveTimeoutMax,
                  vtssMrpCapabilitiesLeaveAllTimeoutMin,
                  vtssMrpCapabilitiesLeaveAllTimeoutMax }
    STATUS      current
    DESCRIPTION
        "A collection of objects."
    ::= { vtssMrpMibGroups 1 }

vtssMrpConfigInterfaceTableInfoGroup OBJECT-GROUP
    OBJECTS     { vtssMrpConfigInterfaceIfIndex,
                  vtssMrpConfigInterfaceJoinTimeout,
                  vtssMrpConfigInterfaceLeaveTimeout,
                  vtssMrpConfigInterfaceLeaveAllTimeout,
                  vtssMrpConfigInterfacePeriodicTransmission }
    STATUS      current
    DESCRIPTION
        "A collection of objects."
    ::= { vtssMrpMibGroups 2 }

vtssMrpMibCompliance MODULE-COMPLIANCE
    STATUS      current
    DESCRIPTION
        "The compliance statement for the implementation."

    MODULE      -- this module

    MANDATORY-GROUPS { vtssMrpCapabilitiesInfoGroup,
                       vtssMrpConfigInterfaceTableInfoGroup }

    ::= { vtssMrpMibCompliances 1 }

END
