-- *****************************************************************
-- IP-MIB:  Microsemi ENT private MIB
-- ****************************************************************

VTSS-IP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    Counter64 FROM SNMPv2-SMI
    Integer32 FROM SNMPv2-SMI
    IpAddress FROM SNMPv2-SMI
    Unsigned32 FROM SNMPv2-SMI
    MacAddress FROM SNMPv2-TC
    TruthValue FROM SNMPv2-TC
    VTSSDisplayString FROM VTSS-TC
    VTSSInterfaceIndex FROM VTSS-TC
    VTSSRowEditorState FROM VTSS-TC
    VTSSUnsigned64 FROM VTSS-TC
    VTSSUnsigned8 FROM VTSS-TC
    ;

vtssIpMib MODULE-IDENTITY
    LAST-UPDATED "202011060000Z"
    ORGANIZATION
        "Microsemi Corporation"
    CONTACT-INFO
        "Application support: http://www.microchip.com/support"
    DESCRIPTION
        "Private IP MIB."
    REVISION    "202011060000Z"
    DESCRIPTION
        "Added global status trap to indicate H/W routing table depletion."
    REVISION    "202006250000Z"
    DESCRIPTION
        "Non-backwards compatible change in ipStatusRoutesIpv4 and
         ipStatusRoutesIpv6 to make snmp-walk work for multiple link-local IPv6
         addresses."
    REVISION    "202003050000Z"
    DESCRIPTION
        "Non-backwards compatible changes due to (re-)introduction of dynamic
         routing."
    REVISION    "201805290000Z"
    DESCRIPTION
        "Replace 'protoConneted(1)' with 'protoConnected(1)'."
    REVISION    "201801300000Z"
    DESCRIPTION
        "Add IPv4 route distance configuration and routing information base
         table."
    REVISION    "201705240000Z"
    DESCRIPTION
        "Add DHCP client hostname and client identifier configuration."
    REVISION    "201607280000Z"
    DESCRIPTION
        "Add ability to clear address conflict detection table."
    REVISION    "201508240000Z"
    DESCRIPTION
        "Add capability for IPv4/IPv6 statistics availability."
    REVISION    "201410290000Z"
    DESCRIPTION
        "Removed the fields arpRetransmitTime and reasmMaxSize."
    REVISION    "201410210000Z"
    DESCRIPTION
        "Added arpCheck in the DhcpClientState enum"
    REVISION    "201409110000Z"
    DESCRIPTION
        "Revise definition of IPv4/IPv6 interface status table index."
    REVISION    "201407010000Z"
    DESCRIPTION
        "Initial version."
    ::= { vtssSwitchMgmt 102 }


VTSSIpDhcpClientState ::= TEXTUAL-CONVENTION
    STATUS      current
    DESCRIPTION
        "The state of the DHCP client"
    SYNTAX      INTEGER { stopped(0), init(1), selecting(2),
                          requesting(3), rebinding(4), bound(5),
                          renewing(6), fallback(7), arpCheck(8) }

VTSSIpDhcpClientType ::= TEXTUAL-CONVENTION
    STATUS      current
    DESCRIPTION
        "The type of the DHCP client identifier."
    SYNTAX      INTEGER { auto(0), ifmac(1), ascii(2), hex(3) }

VTSSIpRouteProtocol ::= TEXTUAL-CONVENTION
    STATUS      current
    DESCRIPTION
        "The protocol of the route."
    SYNTAX      INTEGER { protoKernel(0), protoDhcp(1),
                          protoConnected(2), protoStatic(3),
                          protoOspf(4), protoRip(5), protoUnknown(6) }

vtssIpMibObjects OBJECT IDENTIFIER
    ::= { vtssIpMib 1 }

vtssIpCapabilities OBJECT IDENTIFIER
    ::= { vtssIpMibObjects 1 }

vtssIpCapabilitiesHasIpv4HostCapabilities OBJECT-TYPE
    SYNTAX      TruthValue
    MAX-ACCESS  read-only
    STATUS      current
    DESCRIPTION
        "The device has IPv4 host capabilities for management."
    ::= { vtssIpCapabilities 1 }

vtssIpCapabilitiesHasIpv6HostCapabilities OBJECT-TYPE
    SYNTAX      TruthValue
    MAX-ACCESS  read-only
    STATUS      current
    DESCRIPTION
        "The device has IPv6 host capabilities for management."
    ::= { vtssIpCapabilities 2 }

vtssIpCapabilitiesHasIpv4UnicastRoutingCapabilities OBJECT-TYPE
    SYNTAX      TruthValue
    MAX-ACCESS  read-only
    STATUS      current
    DESCRIPTION
        "The device has IPv4 unicast routing capabilities."
    ::= { vtssIpCapabilities 3 }

vtssIpCapabilitiesHasIpv4UnicastHwRoutingCapabilities OBJECT-TYPE
    SYNTAX      TruthValue
    MAX-ACCESS  read-only
    STATUS      current
    DESCRIPTION
        "The device has IPv4 unicast hardware accelerated routing capabilities."
    ::= { vtssIpCapabilities 4 }

vtssIpCapabilitiesHasIpv6UnicastRoutingCapabilities OBJECT-TYPE
    SYNTAX      TruthValue
    MAX-ACCESS  read-only
    STATUS      current
    DESCRIPTION
        "The device has IPv6 unicast routing capabilities."
    ::= { vtssIpCapabilities 5 }

vtssIpCapabilitiesHasIpv6UnicastHwRoutingCapabilities OBJECT-TYPE
    SYNTAX      TruthValue
    MAX-ACCESS  read-only
    STATUS      current
    DESCRIPTION
        "The device has IPv6 unicast hardware accelerated routing capabilities."
    ::= { vtssIpCapabilities 6 }

vtssIpCapabilitiesMaxNumberOfIpInterfaces OBJECT-TYPE
    SYNTAX      Unsigned32
    MAX-ACCESS  read-only
    STATUS      current
    DESCRIPTION
        "Maximum number of IP interfaces supported by the device."
    ::= { vtssIpCapabilities 7 }

vtssIpCapabilitiesMaxNumberOfStaticRoutes OBJECT-TYPE
    SYNTAX      Unsigned32
    MAX-ACCESS  read-only
    STATUS      current
    DESCRIPTION
        "Maximum number of static configured IP routes (shared by IPv4 and
         IPv6)."
    ::= { vtssIpCapabilities 8 }

vtssIpCapabilitiesNumberOfLpmHardwareEntries OBJECT-TYPE
    SYNTAX      Unsigned32
    MAX-ACCESS  read-only
    STATUS      current
    DESCRIPTION
        "Number of hardware LPM (longest prefix match) entries."
    ::= { vtssIpCapabilities 9 }

vtssIpCapabilitiesHasPerInterfaceIpv4Statistics OBJECT-TYPE
    SYNTAX      TruthValue
    MAX-ACCESS  read-only
    STATUS      current
    DESCRIPTION
        "If true, the platform supports detailed IPv4 statistics per interface."
    ::= { vtssIpCapabilities 10 }

vtssIpCapabilitiesHasPerInterfaceIpv6Statistics OBJECT-TYPE
    SYNTAX      TruthValue
    MAX-ACCESS  read-only
    STATUS      current
    DESCRIPTION
        "If true, the platform supports detailed IPv6 statistics per interface."
    ::= { vtssIpCapabilities 11 }

vtssIpConfig OBJECT IDENTIFIER
    ::= { vtssIpMibObjects 2 }

vtssIpConfigGlobals OBJECT IDENTIFIER
    ::= { vtssIpConfig 1 }

vtssIpConfigGlobalsMain OBJECT IDENTIFIER
    ::= { vtssIpConfigGlobals 1 }

vtssIpConfigGlobalsMainEnableRouting OBJECT-TYPE
    SYNTAX      TruthValue
    MAX-ACCESS  read-write
    STATUS      current
    DESCRIPTION
        "Enable routing."
    ::= { vtssIpConfigGlobalsMain 1 }

vtssIpConfigInterfaces OBJECT IDENTIFIER
    ::= { vtssIpConfig 2 }

vtssIpConfigInterfacesTable OBJECT-TYPE
    SYNTAX      SEQUENCE OF VTSSIpConfigInterfacesEntry
    MAX-ACCESS  not-accessible
    STATUS      current
    DESCRIPTION
        "This is the IP interface table. When an IP interface is created it can
         be configured in the other tables found in this MIB."
    ::= { vtssIpConfigInterfaces 1 }

vtssIpConfigInterfacesEntry OBJECT-TYPE
    SYNTAX      VTSSIpConfigInterfacesEntry
    MAX-ACCESS  not-accessible
    STATUS      current
    DESCRIPTION
        "Entries in this table represent IP interfaces created on the system"
    INDEX       { vtssIpConfigInterfacesIfIndex }
    ::= { vtssIpConfigInterfacesTable 1 }

VTSSIpConfigInterfacesEntry ::= SEQUENCE {
    vtssIpConfigInterfacesIfIndex  VTSSInterfaceIndex,
    vtssIpConfigInterfacesMtu      Unsigned32,
    vtssIpConfigInterfacesAction   VTSSRowEditorState
}

vtssIpConfigInterfacesIfIndex OBJECT-TYPE
    SYNTAX      VTSSInterfaceIndex
    MAX-ACCESS  accessible-for-notify
    STATUS      current
    DESCRIPTION
        "Interface index number."
    ::= { vtssIpConfigInterfacesEntry 1 }

vtssIpConfigInterfacesMtu OBJECT-TYPE
    SYNTAX      Unsigned32
    MAX-ACCESS  read-write
    STATUS      current
    DESCRIPTION
        "MTU for this IP interface."
    ::= { vtssIpConfigInterfacesEntry 2 }

vtssIpConfigInterfacesAction OBJECT-TYPE
    SYNTAX      VTSSRowEditorState
    MAX-ACCESS  read-write
    STATUS      current
    DESCRIPTION
        "Action"
    ::= { vtssIpConfigInterfacesEntry 100 }

vtssIpConfigInterfacesTableRowEditor OBJECT IDENTIFIER
    ::= { vtssIpConfigInterfaces 2 }

vtssIpConfigInterfacesTableRowEditorIfIndex OBJECT-TYPE
    SYNTAX      VTSSInterfaceIndex
    MAX-ACCESS  read-write
    STATUS      current
    DESCRIPTION
        "Interface index number."
    ::= { vtssIpConfigInterfacesTableRowEditor 1 }

vtssIpConfigInterfacesTableRowEditorMtu OBJECT-TYPE
    SYNTAX      Unsigned32
    MAX-ACCESS  read-write
    STATUS      current
    DESCRIPTION
        "MTU for this IP interface."
    ::= { vtssIpConfigInterfacesTableRowEditor 2 }

vtssIpConfigInterfacesTableRowEditorAction OBJECT-TYPE
    SYNTAX      VTSSRowEditorState
    MAX-ACCESS  read-write
    STATUS      current
    DESCRIPTION
        "Action"
    ::= { vtssIpConfigInterfacesTableRowEditor 100 }

vtssIpConfigInterfacesIpv4Table OBJECT-TYPE
    SYNTAX      SEQUENCE OF VTSSIpConfigInterfacesIpv4Entry
    MAX-ACCESS  not-accessible
    STATUS      current
    DESCRIPTION
        "IPv4 interface configuration table. This table enables IPv4 related
         configuration of the corresponding IP interface."
    ::= { vtssIpConfigInterfaces 3 }

vtssIpConfigInterfacesIpv4Entry OBJECT-TYPE
    SYNTAX      VTSSIpConfigInterfacesIpv4Entry
    MAX-ACCESS  not-accessible
    STATUS      current
    DESCRIPTION
        "Each entry in this table represents an IP interface."
    INDEX       { vtssIpConfigInterfacesIpv4IfIndex }
    ::= { vtssIpConfigInterfacesIpv4Table 1 }

VTSSIpConfigInterfacesIpv4Entry ::= SEQUENCE {
    vtssIpConfigInterfacesIpv4IfIndex                    VTSSInterfaceIndex,
    vtssIpConfigInterfacesIpv4Active                     TruthValue,
    vtssIpConfigInterfacesIpv4EnableDhcpClient           TruthValue,
    vtssIpConfigInterfacesIpv4Ipv4Address                IpAddress,
    vtssIpConfigInterfacesIpv4PrefixSize                 Unsigned32,
    vtssIpConfigInterfacesIpv4DhcpClientFallbackTimeout  Unsigned32,
    vtssIpConfigInterfacesIpv4DhcpClientHostname         VTSSDisplayString,
    vtssIpConfigInterfacesIpv4DhcpClientIdType           VTSSIpDhcpClientType,
    vtssIpConfigInterfacesIpv4DhcpClientIdIfMac          VTSSInterfaceIndex,
    vtssIpConfigInterfacesIpv4DhcpClientIdAscii          VTSSDisplayString,
    vtssIpConfigInterfacesIpv4DhcpClientIdHex            VTSSDisplayString
}

vtssIpConfigInterfacesIpv4IfIndex OBJECT-TYPE
    SYNTAX      VTSSInterfaceIndex
    MAX-ACCESS  accessible-for-notify
    STATUS      current
    DESCRIPTION
        "Interface index number."
    ::= { vtssIpConfigInterfacesIpv4Entry 1 }

vtssIpConfigInterfacesIpv4Active OBJECT-TYPE
    SYNTAX      TruthValue
    MAX-ACCESS  read-write
    STATUS      current
    DESCRIPTION
        "Enable IPv4.
         
         IPv4 can only be enabled if either the DHCP client is enabled, or a
         valid address has been configured."
    ::= { vtssIpConfigInterfacesIpv4Entry 2 }

vtssIpConfigInterfacesIpv4EnableDhcpClient OBJECT-TYPE
    SYNTAX      TruthValue
    MAX-ACCESS  read-write
    STATUS      current
    DESCRIPTION
        "Enable IPv4 DHCP client.
         
         Note: the DHCP client can only be enabled if there is no conflict in
         the values of: ipv4Address, prefixSize, and dhcpClientFallbackTimeout."
    ::= { vtssIpConfigInterfacesIpv4Entry 3 }

vtssIpConfigInterfacesIpv4Ipv4Address OBJECT-TYPE
    SYNTAX      IpAddress
    MAX-ACCESS  read-write
    STATUS      current
    DESCRIPTION
        "IPv4 address.
         
         Note: Multiple interfaces may not have overlapping networks."
    ::= { vtssIpConfigInterfacesIpv4Entry 4 }

vtssIpConfigInterfacesIpv4PrefixSize OBJECT-TYPE
    SYNTAX      Unsigned32
    MAX-ACCESS  read-write
    STATUS      current
    DESCRIPTION
        "Prefix size of the network.
         
         Note: Multiple interfaces may not have overlapping networks."
    ::= { vtssIpConfigInterfacesIpv4Entry 5 }

vtssIpConfigInterfacesIpv4DhcpClientFallbackTimeout OBJECT-TYPE
    SYNTAX      Unsigned32
    MAX-ACCESS  read-write
    STATUS      current
    DESCRIPTION
        "DHCP client fallback timer.
         
         If DHCP is disabled then this object has no effect. If DHCP is enabled
         and the fallback timeout value is different from zero, then this timer
         will stop the DHCP process and assign the ipv4Address to the interface
         instead."
    ::= { vtssIpConfigInterfacesIpv4Entry 6 }

vtssIpConfigInterfacesIpv4DhcpClientHostname OBJECT-TYPE
    SYNTAX      VTSSDisplayString (SIZE(0..63))
    MAX-ACCESS  read-write
    STATUS      current
    DESCRIPTION
        "The hostname of DHCP client. If DHCPv4 client is enabled, the
         configured hostname will be used in the DHCP option 12 field. When this
         value is empty string, the field use the configured system name plus
         the latest three bytes of system MAC addresses as the hostname."
    ::= { vtssIpConfigInterfacesIpv4Entry 7 }

vtssIpConfigInterfacesIpv4DhcpClientIdType OBJECT-TYPE
    SYNTAX      VTSSIpDhcpClientType
    MAX-ACCESS  read-write
    STATUS      current
    DESCRIPTION
        "The type of the DHCP client identifier."
    ::= { vtssIpConfigInterfacesIpv4Entry 8 }

vtssIpConfigInterfacesIpv4DhcpClientIdIfMac OBJECT-TYPE
    SYNTAX      VTSSInterfaceIndex
    MAX-ACCESS  read-write
    STATUS      current
    DESCRIPTION
        "The interface name of DHCP client identifier. When DHCPv4 client is
         enabled and the client identifier type is 'ifmac', the configured
         interface's hardware MAC address will be used in the DHCP option 61
         field."
    ::= { vtssIpConfigInterfacesIpv4Entry 9 }

vtssIpConfigInterfacesIpv4DhcpClientIdAscii OBJECT-TYPE
    SYNTAX      VTSSDisplayString (SIZE(0..31))
    MAX-ACCESS  read-write
    STATUS      current
    DESCRIPTION
        "The ASCII string of DHCP client identifier. When DHCPv4 client is
         enabled and the client identifier type is 'ascii', the ASCII string
         will be used in the DHCP option 61 field."
    ::= { vtssIpConfigInterfacesIpv4Entry 10 }

vtssIpConfigInterfacesIpv4DhcpClientIdHex OBJECT-TYPE
    SYNTAX      VTSSDisplayString (SIZE(0..64))
    MAX-ACCESS  read-write
    STATUS      current
    DESCRIPTION
        "The hexadecimal string of DHCP client identifier. When DHCPv4 client is
         enabled and the client identifier type 'hex', the hexadecimal value
         will be used in the DHCP option 61 field."
    ::= { vtssIpConfigInterfacesIpv4Entry 11 }

vtssIpConfigInterfacesIpv6Table OBJECT-TYPE
    SYNTAX      SEQUENCE OF VTSSIpConfigInterfacesIpv6Entry
    MAX-ACCESS  not-accessible
    STATUS      current
    DESCRIPTION
        "IPv6 interface configuration table. This table enables IPv6 related
         configuration of the corresponding IP interface."
    ::= { vtssIpConfigInterfaces 4 }

vtssIpConfigInterfacesIpv6Entry OBJECT-TYPE
    SYNTAX      VTSSIpConfigInterfacesIpv6Entry
    MAX-ACCESS  not-accessible
    STATUS      current
    DESCRIPTION
        "Each entry in this table represents an IP interface."
    INDEX       { vtssIpConfigInterfacesIpv6IfIndex }
    ::= { vtssIpConfigInterfacesIpv6Table 1 }

VTSSIpConfigInterfacesIpv6Entry ::= SEQUENCE {
    vtssIpConfigInterfacesIpv6IfIndex      VTSSInterfaceIndex,
    vtssIpConfigInterfacesIpv6Active       TruthValue,
    vtssIpConfigInterfacesIpv6Ipv6Address  InetAddressIPv6,
    vtssIpConfigInterfacesIpv6PrefixSize   Unsigned32
}

vtssIpConfigInterfacesIpv6IfIndex OBJECT-TYPE
    SYNTAX      VTSSInterfaceIndex
    MAX-ACCESS  accessible-for-notify
    STATUS      current
    DESCRIPTION
        "Interface index number."
    ::= { vtssIpConfigInterfacesIpv6Entry 1 }

vtssIpConfigInterfacesIpv6Active OBJECT-TYPE
    SYNTAX      TruthValue
    MAX-ACCESS  read-write
    STATUS      current
    DESCRIPTION
        "Enable the static configured IPv6 address.
         
         The static configured IPv6 address can only be configured if a valid
         address has been written into 'ipv6Address' and 'prefixSize'."
    ::= { vtssIpConfigInterfacesIpv6Entry 2 }

vtssIpConfigInterfacesIpv6Ipv6Address OBJECT-TYPE
    SYNTAX      InetAddressIPv6
    MAX-ACCESS  read-write
    STATUS      current
    DESCRIPTION
        "Static configured IPv6 address."
    ::= { vtssIpConfigInterfacesIpv6Entry 3 }

vtssIpConfigInterfacesIpv6PrefixSize OBJECT-TYPE
    SYNTAX      Unsigned32
    MAX-ACCESS  read-write
    STATUS      current
    DESCRIPTION
        "Prefix size of the network."
    ::= { vtssIpConfigInterfacesIpv6Entry 4 }

vtssIpConfigRoutes OBJECT IDENTIFIER
    ::= { vtssIpConfig 3 }

vtssIpConfigRoutesIpv4Table OBJECT-TYPE
    SYNTAX      SEQUENCE OF VTSSIpConfigRoutesIpv4Entry
    MAX-ACCESS  not-accessible
    STATUS      current
    DESCRIPTION
        "This is the IPv4 route configuration table."
    ::= { vtssIpConfigRoutes 1 }

vtssIpConfigRoutesIpv4Entry OBJECT-TYPE
    SYNTAX      VTSSIpConfigRoutesIpv4Entry
    MAX-ACCESS  not-accessible
    STATUS      current
    DESCRIPTION
        "Each entry in this table represents a configured route.
         
         Note: A route may be configured without being active."
    INDEX       { vtssIpConfigRoutesIpv4NetworkAddress,
                  vtssIpConfigRoutesIpv4NetworkPrefixSize,
                  vtssIpConfigRoutesIpv4NextHop }
    ::= { vtssIpConfigRoutesIpv4Table 1 }

VTSSIpConfigRoutesIpv4Entry ::= SEQUENCE {
    vtssIpConfigRoutesIpv4NetworkAddress     IpAddress,
    vtssIpConfigRoutesIpv4NetworkPrefixSize  Integer32,
    vtssIpConfigRoutesIpv4NextHop            IpAddress,
    vtssIpConfigRoutesIpv4Distance           VTSSUnsigned8,
    vtssIpConfigRoutesIpv4Action             VTSSRowEditorState
}

vtssIpConfigRoutesIpv4NetworkAddress OBJECT-TYPE
    SYNTAX      IpAddress
    MAX-ACCESS  accessible-for-notify
    STATUS      current
    DESCRIPTION
        "Network address."
    ::= { vtssIpConfigRoutesIpv4Entry 1 }

vtssIpConfigRoutesIpv4NetworkPrefixSize OBJECT-TYPE
    SYNTAX      Integer32 (0..32)
    MAX-ACCESS  accessible-for-notify
    STATUS      current
    DESCRIPTION
        "Network prefix size."
    ::= { vtssIpConfigRoutesIpv4Entry 2 }

vtssIpConfigRoutesIpv4NextHop OBJECT-TYPE
    SYNTAX      IpAddress
    MAX-ACCESS  accessible-for-notify
    STATUS      current
    DESCRIPTION
        "Next-hop address."
    ::= { vtssIpConfigRoutesIpv4Entry 3 }

vtssIpConfigRoutesIpv4Distance OBJECT-TYPE
    SYNTAX      VTSSUnsigned8
    MAX-ACCESS  read-write
    STATUS      current
    DESCRIPTION
        "distance value for this route "
    ::= { vtssIpConfigRoutesIpv4Entry 5 }

vtssIpConfigRoutesIpv4Action OBJECT-TYPE
    SYNTAX      VTSSRowEditorState
    MAX-ACCESS  read-write
    STATUS      current
    DESCRIPTION
        "Action"
    ::= { vtssIpConfigRoutesIpv4Entry 100 }

vtssIpConfigRoutesIpv4RowEditor OBJECT IDENTIFIER
    ::= { vtssIpConfigRoutes 2 }

vtssIpConfigRoutesIpv4RowEditorNetworkAddress OBJECT-TYPE
    SYNTAX      IpAddress
    MAX-ACCESS  read-write
    STATUS      current
    DESCRIPTION
        "Network address."
    ::= { vtssIpConfigRoutesIpv4RowEditor 1 }

vtssIpConfigRoutesIpv4RowEditorNetworkPrefixSize OBJECT-TYPE
    SYNTAX      Integer32 (0..32)
    MAX-ACCESS  read-write
    STATUS      current
    DESCRIPTION
        "Network prefix size."
    ::= { vtssIpConfigRoutesIpv4RowEditor 2 }

vtssIpConfigRoutesIpv4RowEditorNextHop OBJECT-TYPE
    SYNTAX      IpAddress
    MAX-ACCESS  read-write
    STATUS      current
    DESCRIPTION
        "Next-hop address."
    ::= { vtssIpConfigRoutesIpv4RowEditor 3 }

vtssIpConfigRoutesIpv4RowEditorDistance OBJECT-TYPE
    SYNTAX      VTSSUnsigned8
    MAX-ACCESS  read-write
    STATUS      current
    DESCRIPTION
        "distance value for this route "
    ::= { vtssIpConfigRoutesIpv4RowEditor 5 }

vtssIpConfigRoutesIpv4RowEditorAction OBJECT-TYPE
    SYNTAX      VTSSRowEditorState
    MAX-ACCESS  read-write
    STATUS      current
    DESCRIPTION
        "Action"
    ::= { vtssIpConfigRoutesIpv4RowEditor 100 }

vtssIpConfigRoutesIpv6Table OBJECT-TYPE
    SYNTAX      SEQUENCE OF VTSSIpConfigRoutesIpv6Entry
    MAX-ACCESS  not-accessible
    STATUS      current
    DESCRIPTION
        "This is the IPv6 route configuration table."
    ::= { vtssIpConfigRoutes 3 }

vtssIpConfigRoutesIpv6Entry OBJECT-TYPE
    SYNTAX      VTSSIpConfigRoutesIpv6Entry
    MAX-ACCESS  not-accessible
    STATUS      current
    DESCRIPTION
        "Each entry in this table represents a configured route.
         
         Note: a route may be configured without being active."
    INDEX       { vtssIpConfigRoutesIpv6NetworkAddress,
                  vtssIpConfigRoutesIpv6NetworkPrefixSize,
                  vtssIpConfigRoutesIpv6NextHop,
                  vtssIpConfigRoutesIpv6NextHopInterface }
    ::= { vtssIpConfigRoutesIpv6Table 1 }

VTSSIpConfigRoutesIpv6Entry ::= SEQUENCE {
    vtssIpConfigRoutesIpv6NetworkAddress     InetAddressIPv6,
    vtssIpConfigRoutesIpv6NetworkPrefixSize  Integer32,
    vtssIpConfigRoutesIpv6NextHop            InetAddressIPv6,
    vtssIpConfigRoutesIpv6NextHopInterface   VTSSInterfaceIndex,
    vtssIpConfigRoutesIpv6Distance           VTSSUnsigned8,
    vtssIpConfigRoutesIpv6Action             VTSSRowEditorState
}

vtssIpConfigRoutesIpv6NetworkAddress OBJECT-TYPE
    SYNTAX      InetAddressIPv6
    MAX-ACCESS  accessible-for-notify
    STATUS      current
    DESCRIPTION
        "Network address."
    ::= { vtssIpConfigRoutesIpv6Entry 1 }

vtssIpConfigRoutesIpv6NetworkPrefixSize OBJECT-TYPE
    SYNTAX      Integer32 (0..128)
    MAX-ACCESS  accessible-for-notify
    STATUS      current
    DESCRIPTION
        "Network prefix size."
    ::= { vtssIpConfigRoutesIpv6Entry 2 }

vtssIpConfigRoutesIpv6NextHop OBJECT-TYPE
    SYNTAX      InetAddressIPv6
    MAX-ACCESS  accessible-for-notify
    STATUS      current
    DESCRIPTION
        "Next-hop address."
    ::= { vtssIpConfigRoutesIpv6Entry 3 }

vtssIpConfigRoutesIpv6NextHopInterface OBJECT-TYPE
    SYNTAX      VTSSInterfaceIndex
    MAX-ACCESS  accessible-for-notify
    STATUS      current
    DESCRIPTION
        "If the next-hop address is a link-local address, then the VLAN
         interface of the link-local address must be specified here. Otherwise
         this value is not used."
    ::= { vtssIpConfigRoutesIpv6Entry 4 }

vtssIpConfigRoutesIpv6Distance OBJECT-TYPE
    SYNTAX      VTSSUnsigned8
    MAX-ACCESS  read-write
    STATUS      current
    DESCRIPTION
        "distance value for this route "
    ::= { vtssIpConfigRoutesIpv6Entry 5 }

vtssIpConfigRoutesIpv6Action OBJECT-TYPE
    SYNTAX      VTSSRowEditorState
    MAX-ACCESS  read-write
    STATUS      current
    DESCRIPTION
        "Action"
    ::= { vtssIpConfigRoutesIpv6Entry 100 }

vtssIpConfigRoutesIpv6RowEditor OBJECT IDENTIFIER
    ::= { vtssIpConfigRoutes 4 }

vtssIpConfigRoutesIpv6RowEditorNetworkAddress OBJECT-TYPE
    SYNTAX      InetAddressIPv6
    MAX-ACCESS  read-write
    STATUS      current
    DESCRIPTION
        "Network address."
    ::= { vtssIpConfigRoutesIpv6RowEditor 1 }

vtssIpConfigRoutesIpv6RowEditorNetworkPrefixSize OBJECT-TYPE
    SYNTAX      Integer32 (0..128)
    MAX-ACCESS  read-write
    STATUS      current
    DESCRIPTION
        "Network prefix size."
    ::= { vtssIpConfigRoutesIpv6RowEditor 2 }

vtssIpConfigRoutesIpv6RowEditorNextHop OBJECT-TYPE
    SYNTAX      InetAddressIPv6
    MAX-ACCESS  read-write
    STATUS      current
    DESCRIPTION
        "Next-hop address."
    ::= { vtssIpConfigRoutesIpv6RowEditor 3 }

vtssIpConfigRoutesIpv6RowEditorNextHopInterface OBJECT-TYPE
    SYNTAX      VTSSInterfaceIndex
    MAX-ACCESS  read-write
    STATUS      current
    DESCRIPTION
        "If the next-hop address is a link-local address, then the VLAN
         interface of the link-local address must be specified here. Otherwise
         this value is not used."
    ::= { vtssIpConfigRoutesIpv6RowEditor 4 }

vtssIpConfigRoutesIpv6RowEditorDistance OBJECT-TYPE
    SYNTAX      VTSSUnsigned8
    MAX-ACCESS  read-write
    STATUS      current
    DESCRIPTION
        "distance value for this route "
    ::= { vtssIpConfigRoutesIpv6RowEditor 5 }

vtssIpConfigRoutesIpv6RowEditorAction OBJECT-TYPE
    SYNTAX      VTSSRowEditorState
    MAX-ACCESS  read-write
    STATUS      current
    DESCRIPTION
        "Action"
    ::= { vtssIpConfigRoutesIpv6RowEditor 100 }

vtssIpStatus OBJECT IDENTIFIER
    ::= { vtssIpMibObjects 3 }

vtssIpStatusGlobals OBJECT IDENTIFIER
    ::= { vtssIpStatus 1 }

vtssIpStatusGlobalsIpv4NeighborTable OBJECT-TYPE
    SYNTAX      SEQUENCE OF VTSSIpStatusGlobalsIpv4NeighborEntry
    MAX-ACCESS  not-accessible
    STATUS      current
    DESCRIPTION
        "This is the IPv4 neighbor (ARP) table."
    ::= { vtssIpStatusGlobals 1 }

vtssIpStatusGlobalsIpv4NeighborEntry OBJECT-TYPE
    SYNTAX      VTSSIpStatusGlobalsIpv4NeighborEntry
    MAX-ACCESS  not-accessible
    STATUS      current
    DESCRIPTION
        "Each entry in this table represents an entry in the underlying
         operating system's ARP table."
    INDEX       { vtssIpStatusGlobalsIpv4NeighborIpv4 }
    ::= { vtssIpStatusGlobalsIpv4NeighborTable 1 }

VTSSIpStatusGlobalsIpv4NeighborEntry ::= SEQUENCE {
    vtssIpStatusGlobalsIpv4NeighborIpv4        IpAddress,
    vtssIpStatusGlobalsIpv4NeighborMacAddress  MacAddress,
    vtssIpStatusGlobalsIpv4NeighborInterface   VTSSInterfaceIndex
}

vtssIpStatusGlobalsIpv4NeighborIpv4 OBJECT-TYPE
    SYNTAX      IpAddress
    MAX-ACCESS  accessible-for-notify
    STATUS      current
    DESCRIPTION
        "IPv4 address."
    ::= { vtssIpStatusGlobalsIpv4NeighborEntry 1 }

vtssIpStatusGlobalsIpv4NeighborMacAddress OBJECT-TYPE
    SYNTAX      MacAddress
    MAX-ACCESS  read-only
    STATUS      current
    DESCRIPTION
        "MAC address associated with the IP address"
    ::= { vtssIpStatusGlobalsIpv4NeighborEntry 2 }

vtssIpStatusGlobalsIpv4NeighborInterface OBJECT-TYPE
    SYNTAX      VTSSInterfaceIndex
    MAX-ACCESS  read-only
    STATUS      current
    DESCRIPTION
        "Interface the neighbor can be reached on."
    ::= { vtssIpStatusGlobalsIpv4NeighborEntry 3 }

vtssIpStatusGlobalsIpv6NeighborTable OBJECT-TYPE
    SYNTAX      SEQUENCE OF VTSSIpStatusGlobalsIpv6NeighborEntry
    MAX-ACCESS  not-accessible
    STATUS      current
    DESCRIPTION
        "This is the IPv6 neighbor table."
    ::= { vtssIpStatusGlobals 2 }

vtssIpStatusGlobalsIpv6NeighborEntry OBJECT-TYPE
    SYNTAX      VTSSIpStatusGlobalsIpv6NeighborEntry
    MAX-ACCESS  not-accessible
    STATUS      current
    DESCRIPTION
        "Each entry in this table represents an entry in the underlying
         operating system's neighbor table."
    INDEX       { vtssIpStatusGlobalsIpv6NeighborIpv6,
                  vtssIpStatusGlobalsIpv6NeighborIfindex }
    ::= { vtssIpStatusGlobalsIpv6NeighborTable 1 }

VTSSIpStatusGlobalsIpv6NeighborEntry ::= SEQUENCE {
    vtssIpStatusGlobalsIpv6NeighborIpv6        InetAddressIPv6,
    vtssIpStatusGlobalsIpv6NeighborIfindex     VTSSInterfaceIndex,
    vtssIpStatusGlobalsIpv6NeighborMacAddress  MacAddress,
    vtssIpStatusGlobalsIpv6NeighborInterface   VTSSInterfaceIndex
}

vtssIpStatusGlobalsIpv6NeighborIpv6 OBJECT-TYPE
    SYNTAX      InetAddressIPv6
    MAX-ACCESS  accessible-for-notify
    STATUS      current
    DESCRIPTION
        "IPv6 address."
    ::= { vtssIpStatusGlobalsIpv6NeighborEntry 1 }

vtssIpStatusGlobalsIpv6NeighborIfindex OBJECT-TYPE
    SYNTAX      VTSSInterfaceIndex
    MAX-ACCESS  accessible-for-notify
    STATUS      current
    DESCRIPTION
        "If 'ipAddress' is a link-local address, then the interface index where
         the host can be reached must be specified here, otherwise set this to
         zero."
    ::= { vtssIpStatusGlobalsIpv6NeighborEntry 2 }

vtssIpStatusGlobalsIpv6NeighborMacAddress OBJECT-TYPE
    SYNTAX      MacAddress
    MAX-ACCESS  read-only
    STATUS      current
    DESCRIPTION
        "MAC address associated with the IP address"
    ::= { vtssIpStatusGlobalsIpv6NeighborEntry 3 }

vtssIpStatusGlobalsIpv6NeighborInterface OBJECT-TYPE
    SYNTAX      VTSSInterfaceIndex
    MAX-ACCESS  read-only
    STATUS      current
    DESCRIPTION
        "Interface the neighbor can be reached on."
    ::= { vtssIpStatusGlobalsIpv6NeighborEntry 4 }

vtssIpStatusGlobalsNotification OBJECT IDENTIFIER
    ::= { vtssIpStatusGlobals 3 }

vtssIpStatusGlobalsNotificationHwRoutingTableDepleted OBJECT-TYPE
    SYNTAX      TruthValue
    MAX-ACCESS  read-only
    STATUS      current
    DESCRIPTION
        "TRUE if the H/W routing table is full and yet another route is
         attempted added, causing the kernel's FIB database to become out of
         sync with H/W. This in turn means that proper routing can no longer be
         guaranteed.
         
         FALSE as long as everything is fine or the platform does not support
         H/W routing."
    ::= { vtssIpStatusGlobalsNotification 1 }

vtssIpStatusInterfaces OBJECT IDENTIFIER
    ::= { vtssIpStatus 2 }

vtssIpStatusInterfacesLinkTable OBJECT-TYPE
    SYNTAX      SEQUENCE OF VTSSIpStatusInterfacesLinkEntry
    MAX-ACCESS  not-accessible
    STATUS      current
    DESCRIPTION
        "This table provides link-layer status information for IP interfaces."
    ::= { vtssIpStatusInterfaces 1 }

vtssIpStatusInterfacesLinkEntry OBJECT-TYPE
    SYNTAX      VTSSIpStatusInterfacesLinkEntry
    MAX-ACCESS  not-accessible
    STATUS      current
    DESCRIPTION
        "Each entry in this table represents an IP interface."
    INDEX       { vtssIpStatusInterfacesLinkIfIndex }
    ::= { vtssIpStatusInterfacesLinkTable 1 }

VTSSIpStatusInterfacesLinkEntry ::= SEQUENCE {
    vtssIpStatusInterfacesLinkIfIndex           VTSSInterfaceIndex,
    vtssIpStatusInterfacesLinkOsInterfaceIndex  Unsigned32,
    vtssIpStatusInterfacesLinkMtu               Unsigned32,
    vtssIpStatusInterfacesLinkMacAddress        MacAddress,
    vtssIpStatusInterfacesLinkUp                TruthValue,
    vtssIpStatusInterfacesLinkBroadcast         TruthValue,
    vtssIpStatusInterfacesLinkLoopback          TruthValue,
    vtssIpStatusInterfacesLinkRunning           TruthValue,
    vtssIpStatusInterfacesLinkNoarp             TruthValue,
    vtssIpStatusInterfacesLinkPromisc           TruthValue,
    vtssIpStatusInterfacesLinkMulticast         TruthValue
}

vtssIpStatusInterfacesLinkIfIndex OBJECT-TYPE
    SYNTAX      VTSSInterfaceIndex
    MAX-ACCESS  accessible-for-notify
    STATUS      current
    DESCRIPTION
        "Interface index number."
    ::= { vtssIpStatusInterfacesLinkEntry 1 }

vtssIpStatusInterfacesLinkOsInterfaceIndex OBJECT-TYPE
    SYNTAX      Unsigned32
    MAX-ACCESS  read-only
    STATUS      current
    DESCRIPTION
        "Interface index used by the operating system."
    ::= { vtssIpStatusInterfacesLinkEntry 2 }

vtssIpStatusInterfacesLinkMtu OBJECT-TYPE
    SYNTAX      Unsigned32
    MAX-ACCESS  read-only
    STATUS      current
    DESCRIPTION
        "MTU for the interface."
    ::= { vtssIpStatusInterfacesLinkEntry 3 }

vtssIpStatusInterfacesLinkMacAddress OBJECT-TYPE
    SYNTAX      MacAddress
    MAX-ACCESS  read-only
    STATUS      current
    DESCRIPTION
        "MAC-address of the interface."
    ::= { vtssIpStatusInterfacesLinkEntry 4 }

vtssIpStatusInterfacesLinkUp OBJECT-TYPE
    SYNTAX      TruthValue
    MAX-ACCESS  read-only
    STATUS      current
    DESCRIPTION
        "Indicates if the interface is up."
    ::= { vtssIpStatusInterfacesLinkEntry 5 }

vtssIpStatusInterfacesLinkBroadcast OBJECT-TYPE
    SYNTAX      TruthValue
    MAX-ACCESS  read-only
    STATUS      current
    DESCRIPTION
        "Indicates if the interface is capable of transmitting broadcast
         traffic."
    ::= { vtssIpStatusInterfacesLinkEntry 6 }

vtssIpStatusInterfacesLinkLoopback OBJECT-TYPE
    SYNTAX      TruthValue
    MAX-ACCESS  read-only
    STATUS      current
    DESCRIPTION
        "Indicates if the interface is a loop-back interface."
    ::= { vtssIpStatusInterfacesLinkEntry 7 }

vtssIpStatusInterfacesLinkRunning OBJECT-TYPE
    SYNTAX      TruthValue
    MAX-ACCESS  read-only
    STATUS      current
    DESCRIPTION
        "Interface is running (according to the operating system)."
    ::= { vtssIpStatusInterfacesLinkEntry 8 }

vtssIpStatusInterfacesLinkNoarp OBJECT-TYPE
    SYNTAX      TruthValue
    MAX-ACCESS  read-only
    STATUS      current
    DESCRIPTION
        "Indicates if the interface will answer to ARP requests."
    ::= { vtssIpStatusInterfacesLinkEntry 9 }

vtssIpStatusInterfacesLinkPromisc OBJECT-TYPE
    SYNTAX      TruthValue
    MAX-ACCESS  read-only
    STATUS      current
    DESCRIPTION
        "Indicates if the interface is in promisc mode."
    ::= { vtssIpStatusInterfacesLinkEntry 10 }

vtssIpStatusInterfacesLinkMulticast OBJECT-TYPE
    SYNTAX      TruthValue
    MAX-ACCESS  read-only
    STATUS      current
    DESCRIPTION
        "Indicates if the interface supports multicast."
    ::= { vtssIpStatusInterfacesLinkEntry 11 }

vtssIpStatusInterfacesIpv4Table OBJECT-TYPE
    SYNTAX      SEQUENCE OF VTSSIpStatusInterfacesIpv4Entry
    MAX-ACCESS  not-accessible
    STATUS      current
    DESCRIPTION
        "This table provides IPv4 status information for IP interfaces. If an
         interface is configured to use a DHCP client, then the address can be
         found here."
    ::= { vtssIpStatusInterfaces 2 }

vtssIpStatusInterfacesIpv4Entry OBJECT-TYPE
    SYNTAX      VTSSIpStatusInterfacesIpv4Entry
    MAX-ACCESS  not-accessible
    STATUS      current
    DESCRIPTION
        "Each entry in this table represents an IP interface."
    INDEX       { vtssIpStatusInterfacesIpv4IfIndex,
                  vtssIpStatusInterfacesIpv4NetworkAddress,
                  vtssIpStatusInterfacesIpv4NetworkMaskLength }
    ::= { vtssIpStatusInterfacesIpv4Table 1 }

VTSSIpStatusInterfacesIpv4Entry ::= SEQUENCE {
    vtssIpStatusInterfacesIpv4IfIndex            VTSSInterfaceIndex,
    vtssIpStatusInterfacesIpv4NetworkAddress     IpAddress,
    vtssIpStatusInterfacesIpv4NetworkMaskLength  Integer32,
    vtssIpStatusInterfacesIpv4Broadcast          IpAddress
}

vtssIpStatusInterfacesIpv4IfIndex OBJECT-TYPE
    SYNTAX      VTSSInterfaceIndex
    MAX-ACCESS  accessible-for-notify
    STATUS      current
    DESCRIPTION
        "Interface index number."
    ::= { vtssIpStatusInterfacesIpv4Entry 1 }

vtssIpStatusInterfacesIpv4NetworkAddress OBJECT-TYPE
    SYNTAX      IpAddress
    MAX-ACCESS  accessible-for-notify
    STATUS      current
    DESCRIPTION
        "IPv4 network address."
    ::= { vtssIpStatusInterfacesIpv4Entry 2 }

vtssIpStatusInterfacesIpv4NetworkMaskLength OBJECT-TYPE
    SYNTAX      Integer32 (0..32)
    MAX-ACCESS  accessible-for-notify
    STATUS      current
    DESCRIPTION
        "IPv4 network mask length."
    ::= { vtssIpStatusInterfacesIpv4Entry 3 }

vtssIpStatusInterfacesIpv4Broadcast OBJECT-TYPE
    SYNTAX      IpAddress
    MAX-ACCESS  read-only
    STATUS      current
    DESCRIPTION
        "Broadcast address."
    ::= { vtssIpStatusInterfacesIpv4Entry 4 }

vtssIpStatusInterfacesDhcpClientV4Table OBJECT-TYPE
    SYNTAX      SEQUENCE OF VTSSIpStatusInterfacesDhcpClientV4Entry
    MAX-ACCESS  not-accessible
    STATUS      current
    DESCRIPTION
        "This table provides status on the DHCP client running on a given
         interface."
    ::= { vtssIpStatusInterfaces 3 }

vtssIpStatusInterfacesDhcpClientV4Entry OBJECT-TYPE
    SYNTAX      VTSSIpStatusInterfacesDhcpClientV4Entry
    MAX-ACCESS  not-accessible
    STATUS      current
    DESCRIPTION
        "Each entry in this table represents an instance of a DHCP client."
    INDEX       { vtssIpStatusInterfacesDhcpClientV4IfIndex }
    ::= { vtssIpStatusInterfacesDhcpClientV4Table 1 }

VTSSIpStatusInterfacesDhcpClientV4Entry ::= SEQUENCE {
    vtssIpStatusInterfacesDhcpClientV4IfIndex   VTSSInterfaceIndex,
    vtssIpStatusInterfacesDhcpClientV4State     VTSSIpDhcpClientState,
    vtssIpStatusInterfacesDhcpClientV4ServerIp  IpAddress
}

vtssIpStatusInterfacesDhcpClientV4IfIndex OBJECT-TYPE
    SYNTAX      VTSSInterfaceIndex
    MAX-ACCESS  accessible-for-notify
    STATUS      current
    DESCRIPTION
        "Interface index number."
    ::= { vtssIpStatusInterfacesDhcpClientV4Entry 1 }

vtssIpStatusInterfacesDhcpClientV4State OBJECT-TYPE
    SYNTAX      VTSSIpDhcpClientState
    MAX-ACCESS  read-only
    STATUS      current
    DESCRIPTION
        "State of the DHCP client."
    ::= { vtssIpStatusInterfacesDhcpClientV4Entry 2 }

vtssIpStatusInterfacesDhcpClientV4ServerIp OBJECT-TYPE
    SYNTAX      IpAddress
    MAX-ACCESS  read-only
    STATUS      current
    DESCRIPTION
        "IP address of the DHCP server that has provided the DHCP offer."
    ::= { vtssIpStatusInterfacesDhcpClientV4Entry 3 }

vtssIpStatusInterfacesIpv6Table OBJECT-TYPE
    SYNTAX      SEQUENCE OF VTSSIpStatusInterfacesIpv6Entry
    MAX-ACCESS  not-accessible
    STATUS      current
    DESCRIPTION
        "This table provides IPv6 status information for IP interfaces. If an
         interface is configured to use a DHCP client, then the address can be
         found here."
    ::= { vtssIpStatusInterfaces 4 }

vtssIpStatusInterfacesIpv6Entry OBJECT-TYPE
    SYNTAX      VTSSIpStatusInterfacesIpv6Entry
    MAX-ACCESS  not-accessible
    STATUS      current
    DESCRIPTION
        "Each entry in this table represents an IP interface."
    INDEX       { vtssIpStatusInterfacesIpv6IfIndex,
                  vtssIpStatusInterfacesIpv6NetworkAddress,
                  vtssIpStatusInterfacesIpv6NetworkMaskLength }
    ::= { vtssIpStatusInterfacesIpv6Table 1 }

VTSSIpStatusInterfacesIpv6Entry ::= SEQUENCE {
    vtssIpStatusInterfacesIpv6IfIndex            VTSSInterfaceIndex,
    vtssIpStatusInterfacesIpv6NetworkAddress     InetAddressIPv6,
    vtssIpStatusInterfacesIpv6NetworkMaskLength  Integer32,
    vtssIpStatusInterfacesIpv6Tentative          TruthValue,
    vtssIpStatusInterfacesIpv6Duplicated         TruthValue,
    vtssIpStatusInterfacesIpv6Detached           TruthValue,
    vtssIpStatusInterfacesIpv6Nodad              TruthValue,
    vtssIpStatusInterfacesIpv6Autoconf           TruthValue
}

vtssIpStatusInterfacesIpv6IfIndex OBJECT-TYPE
    SYNTAX      VTSSInterfaceIndex
    MAX-ACCESS  accessible-for-notify
    STATUS      current
    DESCRIPTION
        "Interface index number."
    ::= { vtssIpStatusInterfacesIpv6Entry 1 }

vtssIpStatusInterfacesIpv6NetworkAddress OBJECT-TYPE
    SYNTAX      InetAddressIPv6
    MAX-ACCESS  accessible-for-notify
    STATUS      current
    DESCRIPTION
        "IPv6 network address."
    ::= { vtssIpStatusInterfacesIpv6Entry 2 }

vtssIpStatusInterfacesIpv6NetworkMaskLength OBJECT-TYPE
    SYNTAX      Integer32 (0..128)
    MAX-ACCESS  accessible-for-notify
    STATUS      current
    DESCRIPTION
        "IPv6 network mask length."
    ::= { vtssIpStatusInterfacesIpv6Entry 3 }

vtssIpStatusInterfacesIpv6Tentative OBJECT-TYPE
    SYNTAX      TruthValue
    MAX-ACCESS  read-only
    STATUS      current
    DESCRIPTION
        "An address whose uniqueness on a link is being verified, prior to its
         assignment to an interface. A tentative address is not considered
         assigned to an interface in the usual sense."
    ::= { vtssIpStatusInterfacesIpv6Entry 4 }

vtssIpStatusInterfacesIpv6Duplicated OBJECT-TYPE
    SYNTAX      TruthValue
    MAX-ACCESS  read-only
    STATUS      current
    DESCRIPTION
        "Indicates the address duplication is detected by Duplicate Address
         Detection (DAD).
         
         If the address is a link-local address formed from an interface
         identifier based on the hardware address, which is supposed to be
         uniquely assigned (e.g., EUI-64 for an Ethernet interface), IP
         operation on the interface should be disabled."
    ::= { vtssIpStatusInterfacesIpv6Entry 5 }

vtssIpStatusInterfacesIpv6Detached OBJECT-TYPE
    SYNTAX      TruthValue
    MAX-ACCESS  read-only
    STATUS      current
    DESCRIPTION
        "Indicates this address is ready to be detached from the link (IPv6
         network)."
    ::= { vtssIpStatusInterfacesIpv6Entry 6 }

vtssIpStatusInterfacesIpv6Nodad OBJECT-TYPE
    SYNTAX      TruthValue
    MAX-ACCESS  read-only
    STATUS      current
    DESCRIPTION
        "Indicates this address does not perform Duplicate Address Detection
         (DAD)."
    ::= { vtssIpStatusInterfacesIpv6Entry 7 }

vtssIpStatusInterfacesIpv6Autoconf OBJECT-TYPE
    SYNTAX      TruthValue
    MAX-ACCESS  read-only
    STATUS      current
    DESCRIPTION
        "Indicates this address is capable of being retrieved by stateless
         address autoconfiguration."
    ::= { vtssIpStatusInterfacesIpv6Entry 8 }

vtssIpStatusRoutes OBJECT IDENTIFIER
    ::= { vtssIpStatus 3 }

vtssIpStatusRoutesIpv4Table OBJECT-TYPE
    SYNTAX      SEQUENCE OF VTSSIpStatusRoutesIpv4Entry
    MAX-ACCESS  not-accessible
    STATUS      current
    DESCRIPTION
        "This table provides IPv4 routing status."
    ::= { vtssIpStatusRoutes 1 }

vtssIpStatusRoutesIpv4Entry OBJECT-TYPE
    SYNTAX      VTSSIpStatusRoutesIpv4Entry
    MAX-ACCESS  not-accessible
    STATUS      current
    DESCRIPTION
        "Each entry in this table represents an IPv4 route."
    INDEX       { vtssIpStatusRoutesIpv4NetworkAddress,
                  vtssIpStatusRoutesIpv4NetworkPrefixSize,
                  vtssIpStatusRoutesIpv4Protocol,
                  vtssIpStatusRoutesIpv4NextHop,
                  vtssIpStatusRoutesIpv4NextHopInterface }
    ::= { vtssIpStatusRoutesIpv4Table 1 }

VTSSIpStatusRoutesIpv4Entry ::= SEQUENCE {
    vtssIpStatusRoutesIpv4NetworkAddress     IpAddress,
    vtssIpStatusRoutesIpv4NetworkPrefixSize  Integer32,
    vtssIpStatusRoutesIpv4Protocol           VTSSIpRouteProtocol,
    vtssIpStatusRoutesIpv4NextHop            IpAddress,
    vtssIpStatusRoutesIpv4NextHopInterface   VTSSInterfaceIndex,
    vtssIpStatusRoutesIpv4Selected           TruthValue,
    vtssIpStatusRoutesIpv4Active             TruthValue,
    vtssIpStatusRoutesIpv4Fib                TruthValue,
    vtssIpStatusRoutesIpv4DirectlyConnected  TruthValue,
    vtssIpStatusRoutesIpv4Onlink             TruthValue,
    vtssIpStatusRoutesIpv4Duplicate          TruthValue,
    vtssIpStatusRoutesIpv4Recursive          TruthValue,
    vtssIpStatusRoutesIpv4Unreachable        TruthValue,
    vtssIpStatusRoutesIpv4Reject             TruthValue,
    vtssIpStatusRoutesIpv4AdminProhib        TruthValue,
    vtssIpStatusRoutesIpv4Blackhole          TruthValue,
    vtssIpStatusRoutesIpv4Metric             Unsigned32,
    vtssIpStatusRoutesIpv4Distance           VTSSUnsigned8,
    vtssIpStatusRoutesIpv4Uptime             VTSSUnsigned64
}

vtssIpStatusRoutesIpv4NetworkAddress OBJECT-TYPE
    SYNTAX      IpAddress
    MAX-ACCESS  accessible-for-notify
    STATUS      current
    DESCRIPTION
        "Network address."
    ::= { vtssIpStatusRoutesIpv4Entry 1 }

vtssIpStatusRoutesIpv4NetworkPrefixSize OBJECT-TYPE
    SYNTAX      Integer32 (0..32)
    MAX-ACCESS  accessible-for-notify
    STATUS      current
    DESCRIPTION
        "Network prefix size."
    ::= { vtssIpStatusRoutesIpv4Entry 2 }

vtssIpStatusRoutesIpv4Protocol OBJECT-TYPE
    SYNTAX      VTSSIpRouteProtocol
    MAX-ACCESS  accessible-for-notify
    STATUS      current
    DESCRIPTION
        "The protocol that installed this route."
    ::= { vtssIpStatusRoutesIpv4Entry 3 }

vtssIpStatusRoutesIpv4NextHop OBJECT-TYPE
    SYNTAX      IpAddress
    MAX-ACCESS  accessible-for-notify
    STATUS      current
    DESCRIPTION
        "Next-hop IP address. All-zeroes indicates the link is directly
         connected and all-ones indicates it is a blackhole route."
    ::= { vtssIpStatusRoutesIpv4Entry 4 }

vtssIpStatusRoutesIpv4NextHopInterface OBJECT-TYPE
    SYNTAX      VTSSInterfaceIndex
    MAX-ACCESS  accessible-for-notify
    STATUS      current
    DESCRIPTION
        "Next-hop interface."
    ::= { vtssIpStatusRoutesIpv4Entry 5 }

vtssIpStatusRoutesIpv4Selected OBJECT-TYPE
    SYNTAX      TruthValue
    MAX-ACCESS  read-only
    STATUS      current
    DESCRIPTION
        "Route is the best."
    ::= { vtssIpStatusRoutesIpv4Entry 6 }

vtssIpStatusRoutesIpv4Active OBJECT-TYPE
    SYNTAX      TruthValue
    MAX-ACCESS  read-only
    STATUS      current
    DESCRIPTION
        "Destination is active."
    ::= { vtssIpStatusRoutesIpv4Entry 7 }

vtssIpStatusRoutesIpv4Fib OBJECT-TYPE
    SYNTAX      TruthValue
    MAX-ACCESS  read-only
    STATUS      current
    DESCRIPTION
        "Route is installed in system's forward information base."
    ::= { vtssIpStatusRoutesIpv4Entry 8 }

vtssIpStatusRoutesIpv4DirectlyConnected OBJECT-TYPE
    SYNTAX      TruthValue
    MAX-ACCESS  read-only
    STATUS      current
    DESCRIPTION
        "Destination is directly connected."
    ::= { vtssIpStatusRoutesIpv4Entry 9 }

vtssIpStatusRoutesIpv4Onlink OBJECT-TYPE
    SYNTAX      TruthValue
    MAX-ACCESS  read-only
    STATUS      current
    DESCRIPTION
        "Gateway is forced on interface."
    ::= { vtssIpStatusRoutesIpv4Entry 10 }

vtssIpStatusRoutesIpv4Duplicate OBJECT-TYPE
    SYNTAX      TruthValue
    MAX-ACCESS  read-only
    STATUS      current
    DESCRIPTION
        "Route is a duplicate."
    ::= { vtssIpStatusRoutesIpv4Entry 11 }

vtssIpStatusRoutesIpv4Recursive OBJECT-TYPE
    SYNTAX      TruthValue
    MAX-ACCESS  read-only
    STATUS      current
    DESCRIPTION
        "Route is recursive."
    ::= { vtssIpStatusRoutesIpv4Entry 12 }

vtssIpStatusRoutesIpv4Unreachable OBJECT-TYPE
    SYNTAX      TruthValue
    MAX-ACCESS  read-only
    STATUS      current
    DESCRIPTION
        "Nexthop is unreachable."
    ::= { vtssIpStatusRoutesIpv4Entry 13 }

vtssIpStatusRoutesIpv4Reject OBJECT-TYPE
    SYNTAX      TruthValue
    MAX-ACCESS  read-only
    STATUS      current
    DESCRIPTION
        "Route is rejected."
    ::= { vtssIpStatusRoutesIpv4Entry 14 }

vtssIpStatusRoutesIpv4AdminProhib OBJECT-TYPE
    SYNTAX      TruthValue
    MAX-ACCESS  read-only
    STATUS      current
    DESCRIPTION
        "Route is prohibited by admin."
    ::= { vtssIpStatusRoutesIpv4Entry 15 }

vtssIpStatusRoutesIpv4Blackhole OBJECT-TYPE
    SYNTAX      TruthValue
    MAX-ACCESS  read-only
    STATUS      current
    DESCRIPTION
        "Destination is a black hole."
    ::= { vtssIpStatusRoutesIpv4Entry 16 }

vtssIpStatusRoutesIpv4Metric OBJECT-TYPE
    SYNTAX      Unsigned32
    MAX-ACCESS  read-only
    STATUS      current
    DESCRIPTION
        "Metric of the route."
    ::= { vtssIpStatusRoutesIpv4Entry 17 }

vtssIpStatusRoutesIpv4Distance OBJECT-TYPE
    SYNTAX      VTSSUnsigned8
    MAX-ACCESS  read-only
    STATUS      current
    DESCRIPTION
        "Distance of the route."
    ::= { vtssIpStatusRoutesIpv4Entry 18 }

vtssIpStatusRoutesIpv4Uptime OBJECT-TYPE
    SYNTAX      VTSSUnsigned64
    MAX-ACCESS  read-only
    STATUS      current
    DESCRIPTION
        "Time (in seconds) since this route was created"
    ::= { vtssIpStatusRoutesIpv4Entry 19 }

vtssIpStatusRoutesIpv6Table OBJECT-TYPE
    SYNTAX      SEQUENCE OF VTSSIpStatusRoutesIpv6Entry
    MAX-ACCESS  not-accessible
    STATUS      current
    DESCRIPTION
        "This table provides IPv6 routing status."
    ::= { vtssIpStatusRoutes 2 }

vtssIpStatusRoutesIpv6Entry OBJECT-TYPE
    SYNTAX      VTSSIpStatusRoutesIpv6Entry
    MAX-ACCESS  not-accessible
    STATUS      current
    DESCRIPTION
        "Each entry in this table represents an IPv6 route."
    INDEX       { vtssIpStatusRoutesIpv6NetworkAddress,
                  vtssIpStatusRoutesIpv6NetworkPrefixSize,
                  vtssIpStatusRoutesIpv6Protocol,
                  vtssIpStatusRoutesIpv6NextHop,
                  vtssIpStatusRoutesIpv6NextHopInterface }
    ::= { vtssIpStatusRoutesIpv6Table 1 }

VTSSIpStatusRoutesIpv6Entry ::= SEQUENCE {
    vtssIpStatusRoutesIpv6NetworkAddress     InetAddressIPv6,
    vtssIpStatusRoutesIpv6NetworkPrefixSize  Integer32,
    vtssIpStatusRoutesIpv6Protocol           VTSSIpRouteProtocol,
    vtssIpStatusRoutesIpv6NextHop            InetAddressIPv6,
    vtssIpStatusRoutesIpv6NextHopInterface   VTSSInterfaceIndex,
    vtssIpStatusRoutesIpv6Selected           TruthValue,
    vtssIpStatusRoutesIpv6Active             TruthValue,
    vtssIpStatusRoutesIpv6Fib                TruthValue,
    vtssIpStatusRoutesIpv6DirectlyConnected  TruthValue,
    vtssIpStatusRoutesIpv6Onlink             TruthValue,
    vtssIpStatusRoutesIpv6Duplicate          TruthValue,
    vtssIpStatusRoutesIpv6Recursive          TruthValue,
    vtssIpStatusRoutesIpv6Unreachable        TruthValue,
    vtssIpStatusRoutesIpv6Reject             TruthValue,
    vtssIpStatusRoutesIpv6AdminProhib        TruthValue,
    vtssIpStatusRoutesIpv6Blackhole          TruthValue,
    vtssIpStatusRoutesIpv6Metric             Unsigned32,
    vtssIpStatusRoutesIpv6Distance           VTSSUnsigned8,
    vtssIpStatusRoutesIpv6Uptime             VTSSUnsigned64
}

vtssIpStatusRoutesIpv6NetworkAddress OBJECT-TYPE
    SYNTAX      InetAddressIPv6
    MAX-ACCESS  accessible-for-notify
    STATUS      current
    DESCRIPTION
        "Network address."
    ::= { vtssIpStatusRoutesIpv6Entry 1 }

vtssIpStatusRoutesIpv6NetworkPrefixSize OBJECT-TYPE
    SYNTAX      Integer32 (0..128)
    MAX-ACCESS  accessible-for-notify
    STATUS      current
    DESCRIPTION
        "Network prefix size."
    ::= { vtssIpStatusRoutesIpv6Entry 2 }

vtssIpStatusRoutesIpv6Protocol OBJECT-TYPE
    SYNTAX      VTSSIpRouteProtocol
    MAX-ACCESS  accessible-for-notify
    STATUS      current
    DESCRIPTION
        "The protocol that installed this route."
    ::= { vtssIpStatusRoutesIpv6Entry 3 }

vtssIpStatusRoutesIpv6NextHop OBJECT-TYPE
    SYNTAX      InetAddressIPv6
    MAX-ACCESS  accessible-for-notify
    STATUS      current
    DESCRIPTION
        "Next-hop address. All-zeroes indicates the link is directly connected
         and all-ones indicates it is a blackhole route"
    ::= { vtssIpStatusRoutesIpv6Entry 4 }

vtssIpStatusRoutesIpv6NextHopInterface OBJECT-TYPE
    SYNTAX      VTSSInterfaceIndex
    MAX-ACCESS  accessible-for-notify
    STATUS      current
    DESCRIPTION
        "If the next-hop address is a link-local address, then this is the VLAN
         interface of the link-local address. Otherwise this value is not used"
    ::= { vtssIpStatusRoutesIpv6Entry 5 }

vtssIpStatusRoutesIpv6Selected OBJECT-TYPE
    SYNTAX      TruthValue
    MAX-ACCESS  read-only
    STATUS      current
    DESCRIPTION
        "Route is the best."
    ::= { vtssIpStatusRoutesIpv6Entry 6 }

vtssIpStatusRoutesIpv6Active OBJECT-TYPE
    SYNTAX      TruthValue
    MAX-ACCESS  read-only
    STATUS      current
    DESCRIPTION
        "Destination is active."
    ::= { vtssIpStatusRoutesIpv6Entry 7 }

vtssIpStatusRoutesIpv6Fib OBJECT-TYPE
    SYNTAX      TruthValue
    MAX-ACCESS  read-only
    STATUS      current
    DESCRIPTION
        "Route is installed in system's forward information base."
    ::= { vtssIpStatusRoutesIpv6Entry 8 }

vtssIpStatusRoutesIpv6DirectlyConnected OBJECT-TYPE
    SYNTAX      TruthValue
    MAX-ACCESS  read-only
    STATUS      current
    DESCRIPTION
        "Destination is directly connected."
    ::= { vtssIpStatusRoutesIpv6Entry 9 }

vtssIpStatusRoutesIpv6Onlink OBJECT-TYPE
    SYNTAX      TruthValue
    MAX-ACCESS  read-only
    STATUS      current
    DESCRIPTION
        "Gateway is forced on interface."
    ::= { vtssIpStatusRoutesIpv6Entry 10 }

vtssIpStatusRoutesIpv6Duplicate OBJECT-TYPE
    SYNTAX      TruthValue
    MAX-ACCESS  read-only
    STATUS      current
    DESCRIPTION
        "Route is a duplicate."
    ::= { vtssIpStatusRoutesIpv6Entry 11 }

vtssIpStatusRoutesIpv6Recursive OBJECT-TYPE
    SYNTAX      TruthValue
    MAX-ACCESS  read-only
    STATUS      current
    DESCRIPTION
        "Route is recursive."
    ::= { vtssIpStatusRoutesIpv6Entry 12 }

vtssIpStatusRoutesIpv6Unreachable OBJECT-TYPE
    SYNTAX      TruthValue
    MAX-ACCESS  read-only
    STATUS      current
    DESCRIPTION
        "Nexthop is unreachable."
    ::= { vtssIpStatusRoutesIpv6Entry 13 }

vtssIpStatusRoutesIpv6Reject OBJECT-TYPE
    SYNTAX      TruthValue
    MAX-ACCESS  read-only
    STATUS      current
    DESCRIPTION
        "Route is rejected."
    ::= { vtssIpStatusRoutesIpv6Entry 14 }

vtssIpStatusRoutesIpv6AdminProhib OBJECT-TYPE
    SYNTAX      TruthValue
    MAX-ACCESS  read-only
    STATUS      current
    DESCRIPTION
        "Route is prohibited by admin."
    ::= { vtssIpStatusRoutesIpv6Entry 15 }

vtssIpStatusRoutesIpv6Blackhole OBJECT-TYPE
    SYNTAX      TruthValue
    MAX-ACCESS  read-only
    STATUS      current
    DESCRIPTION
        "Destination is a black hole."
    ::= { vtssIpStatusRoutesIpv6Entry 16 }

vtssIpStatusRoutesIpv6Metric OBJECT-TYPE
    SYNTAX      Unsigned32
    MAX-ACCESS  read-only
    STATUS      current
    DESCRIPTION
        "Metric of the route."
    ::= { vtssIpStatusRoutesIpv6Entry 17 }

vtssIpStatusRoutesIpv6Distance OBJECT-TYPE
    SYNTAX      VTSSUnsigned8
    MAX-ACCESS  read-only
    STATUS      current
    DESCRIPTION
        "Distance of the route."
    ::= { vtssIpStatusRoutesIpv6Entry 18 }

vtssIpStatusRoutesIpv6Uptime OBJECT-TYPE
    SYNTAX      VTSSUnsigned64
    MAX-ACCESS  read-only
    STATUS      current
    DESCRIPTION
        "Time (in seconds) since this route was created"
    ::= { vtssIpStatusRoutesIpv6Entry 19 }

vtssIpControl OBJECT IDENTIFIER
    ::= { vtssIpMibObjects 4 }

vtssIpControlGlobals OBJECT IDENTIFIER
    ::= { vtssIpControl 1 }

vtssIpControlGlobalsIpv4NeighborTableClear OBJECT-TYPE
    SYNTAX      TruthValue
    MAX-ACCESS  read-write
    STATUS      current
    DESCRIPTION
        "Flush the entries in IPv4 ARP cache except for the permanent ones."
    ::= { vtssIpControlGlobals 1 }

vtssIpControlGlobalsIpv6NeighborTableClear OBJECT-TYPE
    SYNTAX      TruthValue
    MAX-ACCESS  read-write
    STATUS      current
    DESCRIPTION
        "Erase all the NDP (Neighbor Discovery Protocol) entries registered in
         IPv6 neighbor cache."
    ::= { vtssIpControlGlobals 2 }

vtssIpControlGlobalsIpv4SystemStatisticsClear OBJECT-TYPE
    SYNTAX      VTSSUnsigned8
    MAX-ACCESS  read-write
    STATUS      current
    DESCRIPTION
        "Clear the system-wide IPv4 traffic statistics."
    ::= { vtssIpControlGlobals 3 }

vtssIpControlGlobalsIpv6SystemStatisticsClear OBJECT-TYPE
    SYNTAX      VTSSUnsigned8
    MAX-ACCESS  read-write
    STATUS      current
    DESCRIPTION
        "Clear the system-wide IPv6 traffic statistics."
    ::= { vtssIpControlGlobals 4 }

vtssIpControlGlobalsIpv4AcdStatusClear OBJECT-TYPE
    SYNTAX      VTSSUnsigned8
    MAX-ACCESS  read-write
    STATUS      current
    DESCRIPTION
        "Clear the Address Conflict Detection table."
    ::= { vtssIpControlGlobals 5 }

vtssIpControlInterface OBJECT IDENTIFIER
    ::= { vtssIpControl 2 }

vtssIpControlInterfaceDhcpClientTable OBJECT-TYPE
    SYNTAX      SEQUENCE OF VTSSIpControlInterfaceDhcpClientEntry
    MAX-ACCESS  not-accessible
    STATUS      current
    DESCRIPTION
        "This table provides control facilities to control an instance of the
         DHCP client."
    ::= { vtssIpControlInterface 1 }

vtssIpControlInterfaceDhcpClientEntry OBJECT-TYPE
    SYNTAX      VTSSIpControlInterfaceDhcpClientEntry
    MAX-ACCESS  not-accessible
    STATUS      current
    DESCRIPTION
        "Each entry in this table represents an instance of the DHCP client."
    INDEX       { vtssIpControlInterfaceDhcpClientIfIndex }
    ::= { vtssIpControlInterfaceDhcpClientTable 1 }

VTSSIpControlInterfaceDhcpClientEntry ::= SEQUENCE {
    vtssIpControlInterfaceDhcpClientIfIndex  VTSSInterfaceIndex,
    vtssIpControlInterfaceDhcpClientRestart  TruthValue
}

vtssIpControlInterfaceDhcpClientIfIndex OBJECT-TYPE
    SYNTAX      VTSSInterfaceIndex
    MAX-ACCESS  accessible-for-notify
    STATUS      current
    DESCRIPTION
        "Interface index number."
    ::= { vtssIpControlInterfaceDhcpClientEntry 1 }

vtssIpControlInterfaceDhcpClientRestart OBJECT-TYPE
    SYNTAX      TruthValue
    MAX-ACCESS  read-write
    STATUS      current
    DESCRIPTION
        "Restart the DHCP client."
    ::= { vtssIpControlInterfaceDhcpClientEntry 2 }

vtssIpStatistics OBJECT IDENTIFIER
    ::= { vtssIpMibObjects 5 }

vtssIpStatisticsGlobals OBJECT IDENTIFIER
    ::= { vtssIpStatistics 1 }

vtssIpStatisticsGlobalsIpv4 OBJECT IDENTIFIER
    ::= { vtssIpStatisticsGlobals 1 }

vtssIpStatisticsGlobalsIpv4InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime."
    ::= { vtssIpStatisticsGlobalsIpv4 1 }

vtssIpStatisticsGlobalsIpv4HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime."
    ::= { vtssIpStatisticsGlobalsIpv4 2 }

vtssIpStatisticsGlobalsIpv4InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime."
    ::= { vtssIpStatisticsGlobalsIpv4 3 }

vtssIpStatisticsGlobalsIpv4HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime."
    ::= { vtssIpStatisticsGlobalsIpv4 4 }

vtssIpStatisticsGlobalsIpv4InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime."
    ::= { vtssIpStatisticsGlobalsIpv4 5 }

vtssIpStatisticsGlobalsIpv4InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime."
    ::= { vtssIpStatisticsGlobalsIpv4 6 }

vtssIpStatisticsGlobalsIpv4InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime."
    ::= { vtssIpStatisticsGlobalsIpv4 7 }

vtssIpStatisticsGlobalsIpv4InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { vtssIpStatisticsGlobalsIpv4 8 }

vtssIpStatisticsGlobalsIpv4InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime."
    ::= { vtssIpStatisticsGlobalsIpv4 9 }

vtssIpStatisticsGlobalsIpv4InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime."
    ::= { vtssIpStatisticsGlobalsIpv4 10 }

vtssIpStatisticsGlobalsIpv4HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime."
    ::= { vtssIpStatisticsGlobalsIpv4 11 }

vtssIpStatisticsGlobalsIpv4ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime."
    ::= { vtssIpStatisticsGlobalsIpv4 12 }

vtssIpStatisticsGlobalsIpv4ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { vtssIpStatisticsGlobalsIpv4 13 }

vtssIpStatisticsGlobalsIpv4ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime."
    ::= { vtssIpStatisticsGlobalsIpv4 14 }

vtssIpStatisticsGlobalsIpv4InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime."
    ::= { vtssIpStatisticsGlobalsIpv4 15 }

vtssIpStatisticsGlobalsIpv4InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { vtssIpStatisticsGlobalsIpv4 16 }

vtssIpStatisticsGlobalsIpv4HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime."
    ::= { vtssIpStatisticsGlobalsIpv4 17 }

vtssIpStatisticsGlobalsIpv4OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime."
    ::= { vtssIpStatisticsGlobalsIpv4 18 }

vtssIpStatisticsGlobalsIpv4HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime."
    ::= { vtssIpStatisticsGlobalsIpv4 19 }

vtssIpStatisticsGlobalsIpv4OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime."
    ::= { vtssIpStatisticsGlobalsIpv4 20 }

vtssIpStatisticsGlobalsIpv4OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime."
    ::= { vtssIpStatisticsGlobalsIpv4 21 }

vtssIpStatisticsGlobalsIpv4HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime."
    ::= { vtssIpStatisticsGlobalsIpv4 22 }

vtssIpStatisticsGlobalsIpv4OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime."
    ::= { vtssIpStatisticsGlobalsIpv4 23 }

vtssIpStatisticsGlobalsIpv4OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime."
    ::= { vtssIpStatisticsGlobalsIpv4 24 }

vtssIpStatisticsGlobalsIpv4OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime."
    ::= { vtssIpStatisticsGlobalsIpv4 25 }

vtssIpStatisticsGlobalsIpv4OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime."
    ::= { vtssIpStatisticsGlobalsIpv4 26 }

vtssIpStatisticsGlobalsIpv4OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime."
    ::= { vtssIpStatisticsGlobalsIpv4 27 }

vtssIpStatisticsGlobalsIpv4OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime."
    ::= { vtssIpStatisticsGlobalsIpv4 28 }

vtssIpStatisticsGlobalsIpv4HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime."
    ::= { vtssIpStatisticsGlobalsIpv4 29 }

vtssIpStatisticsGlobalsIpv4OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime."
    ::= { vtssIpStatisticsGlobalsIpv4 30 }

vtssIpStatisticsGlobalsIpv4HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime."
    ::= { vtssIpStatisticsGlobalsIpv4 31 }

vtssIpStatisticsGlobalsIpv4InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime."
    ::= { vtssIpStatisticsGlobalsIpv4 32 }

vtssIpStatisticsGlobalsIpv4HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime."
    ::= { vtssIpStatisticsGlobalsIpv4 33 }

vtssIpStatisticsGlobalsIpv4InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime."
    ::= { vtssIpStatisticsGlobalsIpv4 34 }

vtssIpStatisticsGlobalsIpv4HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime."
    ::= { vtssIpStatisticsGlobalsIpv4 35 }

vtssIpStatisticsGlobalsIpv4OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime."
    ::= { vtssIpStatisticsGlobalsIpv4 36 }

vtssIpStatisticsGlobalsIpv4HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime."
    ::= { vtssIpStatisticsGlobalsIpv4 37 }

vtssIpStatisticsGlobalsIpv4OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime."
    ::= { vtssIpStatisticsGlobalsIpv4 38 }

vtssIpStatisticsGlobalsIpv4HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime."
    ::= { vtssIpStatisticsGlobalsIpv4 39 }

vtssIpStatisticsGlobalsIpv4InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime."
    ::= { vtssIpStatisticsGlobalsIpv4 40 }

vtssIpStatisticsGlobalsIpv4HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime."
    ::= { vtssIpStatisticsGlobalsIpv4 41 }

vtssIpStatisticsGlobalsIpv4OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime."
    ::= { vtssIpStatisticsGlobalsIpv4 42 }

vtssIpStatisticsGlobalsIpv4HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime."
    ::= { vtssIpStatisticsGlobalsIpv4 43 }

vtssIpStatisticsGlobalsIpv4DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value."
    ::= { vtssIpStatisticsGlobalsIpv4 44 }

vtssIpStatisticsGlobalsIpv4RefreshRate OBJECT-TYPE
    SYNTAX      Unsigned32
    MAX-ACCESS  read-only
    STATUS      current
    DESCRIPTION
        "The minimum reasonable polling interval for this entry. This object
         provides an indication of the minimum amount of time required to update
         the counters in this entry."
    ::= { vtssIpStatisticsGlobalsIpv4 45 }

vtssIpStatisticsGlobalsIpv6 OBJECT IDENTIFIER
    ::= { vtssIpStatisticsGlobals 2 }

vtssIpStatisticsGlobalsIpv6InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime."
    ::= { vtssIpStatisticsGlobalsIpv6 1 }

vtssIpStatisticsGlobalsIpv6HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime."
    ::= { vtssIpStatisticsGlobalsIpv6 2 }

vtssIpStatisticsGlobalsIpv6InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime."
    ::= { vtssIpStatisticsGlobalsIpv6 3 }

vtssIpStatisticsGlobalsIpv6HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime."
    ::= { vtssIpStatisticsGlobalsIpv6 4 }

vtssIpStatisticsGlobalsIpv6InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime."
    ::= { vtssIpStatisticsGlobalsIpv6 5 }

vtssIpStatisticsGlobalsIpv6InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime."
    ::= { vtssIpStatisticsGlobalsIpv6 6 }

vtssIpStatisticsGlobalsIpv6InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime."
    ::= { vtssIpStatisticsGlobalsIpv6 7 }

vtssIpStatisticsGlobalsIpv6InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { vtssIpStatisticsGlobalsIpv6 8 }

vtssIpStatisticsGlobalsIpv6InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime."
    ::= { vtssIpStatisticsGlobalsIpv6 9 }

vtssIpStatisticsGlobalsIpv6InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime."
    ::= { vtssIpStatisticsGlobalsIpv6 10 }

vtssIpStatisticsGlobalsIpv6HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime."
    ::= { vtssIpStatisticsGlobalsIpv6 11 }

vtssIpStatisticsGlobalsIpv6ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime."
    ::= { vtssIpStatisticsGlobalsIpv6 12 }

vtssIpStatisticsGlobalsIpv6ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { vtssIpStatisticsGlobalsIpv6 13 }

vtssIpStatisticsGlobalsIpv6ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime."
    ::= { vtssIpStatisticsGlobalsIpv6 14 }

vtssIpStatisticsGlobalsIpv6InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime."
    ::= { vtssIpStatisticsGlobalsIpv6 15 }

vtssIpStatisticsGlobalsIpv6InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { vtssIpStatisticsGlobalsIpv6 16 }

vtssIpStatisticsGlobalsIpv6HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime."
    ::= { vtssIpStatisticsGlobalsIpv6 17 }

vtssIpStatisticsGlobalsIpv6OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime."
    ::= { vtssIpStatisticsGlobalsIpv6 18 }

vtssIpStatisticsGlobalsIpv6HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime."
    ::= { vtssIpStatisticsGlobalsIpv6 19 }

vtssIpStatisticsGlobalsIpv6OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime."
    ::= { vtssIpStatisticsGlobalsIpv6 20 }

vtssIpStatisticsGlobalsIpv6OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime."
    ::= { vtssIpStatisticsGlobalsIpv6 21 }

vtssIpStatisticsGlobalsIpv6HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime."
    ::= { vtssIpStatisticsGlobalsIpv6 22 }

vtssIpStatisticsGlobalsIpv6OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime."
    ::= { vtssIpStatisticsGlobalsIpv6 23 }

vtssIpStatisticsGlobalsIpv6OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime."
    ::= { vtssIpStatisticsGlobalsIpv6 24 }

vtssIpStatisticsGlobalsIpv6OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime."
    ::= { vtssIpStatisticsGlobalsIpv6 25 }

vtssIpStatisticsGlobalsIpv6OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime."
    ::= { vtssIpStatisticsGlobalsIpv6 26 }

vtssIpStatisticsGlobalsIpv6OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime."
    ::= { vtssIpStatisticsGlobalsIpv6 27 }

vtssIpStatisticsGlobalsIpv6OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime."
    ::= { vtssIpStatisticsGlobalsIpv6 28 }

vtssIpStatisticsGlobalsIpv6HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime."
    ::= { vtssIpStatisticsGlobalsIpv6 29 }

vtssIpStatisticsGlobalsIpv6OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime."
    ::= { vtssIpStatisticsGlobalsIpv6 30 }

vtssIpStatisticsGlobalsIpv6HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime."
    ::= { vtssIpStatisticsGlobalsIpv6 31 }

vtssIpStatisticsGlobalsIpv6InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime."
    ::= { vtssIpStatisticsGlobalsIpv6 32 }

vtssIpStatisticsGlobalsIpv6HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime."
    ::= { vtssIpStatisticsGlobalsIpv6 33 }

vtssIpStatisticsGlobalsIpv6InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime."
    ::= { vtssIpStatisticsGlobalsIpv6 34 }

vtssIpStatisticsGlobalsIpv6HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime."
    ::= { vtssIpStatisticsGlobalsIpv6 35 }

vtssIpStatisticsGlobalsIpv6OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime."
    ::= { vtssIpStatisticsGlobalsIpv6 36 }

vtssIpStatisticsGlobalsIpv6HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime."
    ::= { vtssIpStatisticsGlobalsIpv6 37 }

vtssIpStatisticsGlobalsIpv6OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime."
    ::= { vtssIpStatisticsGlobalsIpv6 38 }

vtssIpStatisticsGlobalsIpv6HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime."
    ::= { vtssIpStatisticsGlobalsIpv6 39 }

vtssIpStatisticsGlobalsIpv6InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime."
    ::= { vtssIpStatisticsGlobalsIpv6 40 }

vtssIpStatisticsGlobalsIpv6HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime."
    ::= { vtssIpStatisticsGlobalsIpv6 41 }

vtssIpStatisticsGlobalsIpv6OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime."
    ::= { vtssIpStatisticsGlobalsIpv6 42 }

vtssIpStatisticsGlobalsIpv6HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime."
    ::= { vtssIpStatisticsGlobalsIpv6 43 }

vtssIpStatisticsGlobalsIpv6DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value."
    ::= { vtssIpStatisticsGlobalsIpv6 44 }

vtssIpStatisticsGlobalsIpv6RefreshRate OBJECT-TYPE
    SYNTAX      Unsigned32
    MAX-ACCESS  read-only
    STATUS      current
    DESCRIPTION
        "The minimum reasonable polling interval for this entry. This object
         provides an indication of the minimum amount of time required to update
         the counters in this entry."
    ::= { vtssIpStatisticsGlobalsIpv6 45 }

vtssIpStatisticsInterfaces OBJECT IDENTIFIER
    ::= { vtssIpStatistics 2 }

vtssIpStatisticsInterfacesLinkTable OBJECT-TYPE
    SYNTAX      SEQUENCE OF VTSSIpStatisticsInterfacesLinkEntry
    MAX-ACCESS  not-accessible
    STATUS      current
    DESCRIPTION
        "This table provides interface link statistics for a given IP interface."
    ::= { vtssIpStatisticsInterfaces 1 }

vtssIpStatisticsInterfacesLinkEntry OBJECT-TYPE
    SYNTAX      VTSSIpStatisticsInterfacesLinkEntry
    MAX-ACCESS  not-accessible
    STATUS      current
    DESCRIPTION
        "Each entry in this table represents an IP interface."
    INDEX       { vtssIpStatisticsInterfacesLinkIfIndex }
    ::= { vtssIpStatisticsInterfacesLinkTable 1 }

VTSSIpStatisticsInterfacesLinkEntry ::= SEQUENCE {
    vtssIpStatisticsInterfacesLinkIfIndex        VTSSInterfaceIndex,
    vtssIpStatisticsInterfacesLinkInPackets      Counter64,
    vtssIpStatisticsInterfacesLinkOutPackets     Counter64,
    vtssIpStatisticsInterfacesLinkInBytes        Counter64,
    vtssIpStatisticsInterfacesLinkOutBytes       Counter64,
    vtssIpStatisticsInterfacesLinkInMulticasts   Counter64,
    vtssIpStatisticsInterfacesLinkOutMulticasts  Counter64,
    vtssIpStatisticsInterfacesLinkInBroadcasts   Counter64,
    vtssIpStatisticsInterfacesLinkOutBroadcasts  Counter64
}

vtssIpStatisticsInterfacesLinkIfIndex OBJECT-TYPE
    SYNTAX      VTSSInterfaceIndex
    MAX-ACCESS  accessible-for-notify
    STATUS      current
    DESCRIPTION
        "Interface index number."
    ::= { vtssIpStatisticsInterfacesLinkEntry 1 }

vtssIpStatisticsInterfacesLinkInPackets OBJECT-TYPE
    SYNTAX      Counter64
    MAX-ACCESS  read-only
    STATUS      current
    DESCRIPTION
        "Number of packets delivered by MAC layer to IP layer."
    ::= { vtssIpStatisticsInterfacesLinkEntry 2 }

vtssIpStatisticsInterfacesLinkOutPackets OBJECT-TYPE
    SYNTAX      Counter64
    MAX-ACCESS  read-only
    STATUS      current
    DESCRIPTION
        "Number of packets IP protocols requested be transmitted, including
         those that were discarded or not sent."
    ::= { vtssIpStatisticsInterfacesLinkEntry 3 }

vtssIpStatisticsInterfacesLinkInBytes OBJECT-TYPE
    SYNTAX      Counter64
    MAX-ACCESS  read-only
    STATUS      current
    DESCRIPTION
        "Number of octets received on the interface, including framing
         characters."
    ::= { vtssIpStatisticsInterfacesLinkEntry 4 }

vtssIpStatisticsInterfacesLinkOutBytes OBJECT-TYPE
    SYNTAX      Counter64
    MAX-ACCESS  read-only
    STATUS      current
    DESCRIPTION
        "Number of octets transmitted out of the interface, including framing
         characters."
    ::= { vtssIpStatisticsInterfacesLinkEntry 5 }

vtssIpStatisticsInterfacesLinkInMulticasts OBJECT-TYPE
    SYNTAX      Counter64
    MAX-ACCESS  read-only
    STATUS      current
    DESCRIPTION
        "Number of packets delivered by MAC layer to IP layer that were
         addressed to a MAC multicast address.
         
         For a MAC layer protocol, this includes both Group and Functional
         addresses."
    ::= { vtssIpStatisticsInterfacesLinkEntry 6 }

vtssIpStatisticsInterfacesLinkOutMulticasts OBJECT-TYPE
    SYNTAX      Counter64
    MAX-ACCESS  read-only
    STATUS      current
    DESCRIPTION
        "Number of packets addressed to a multicast MAC address that IP
         protocols requested be transmitted, including those that were discarded
         or not sent.
         
         For a MAC layer protocol, this includes both Group and Functional
         addresses."
    ::= { vtssIpStatisticsInterfacesLinkEntry 7 }

vtssIpStatisticsInterfacesLinkInBroadcasts OBJECT-TYPE
    SYNTAX      Counter64
    MAX-ACCESS  read-only
    STATUS      current
    DESCRIPTION
        "Number of packets delivered by MAC layer to IP layer that were
         addressed to a MAC broadcast address."
    ::= { vtssIpStatisticsInterfacesLinkEntry 8 }

vtssIpStatisticsInterfacesLinkOutBroadcasts OBJECT-TYPE
    SYNTAX      Counter64
    MAX-ACCESS  read-only
    STATUS      current
    DESCRIPTION
        "Number of packets addressed to a broadcast MAC address that IP
         protocols requested be transmitted, including those that were discarded
         or not sent."
    ::= { vtssIpStatisticsInterfacesLinkEntry 9 }

vtssIpStatisticsInterfacesIpv4Table OBJECT-TYPE
    SYNTAX      SEQUENCE OF VTSSIpStatisticsInterfacesIpv4Entry
    MAX-ACCESS  not-accessible
    STATUS      current
    DESCRIPTION
        "This table provides IPv4 related statitics for a given IP interface."
    ::= { vtssIpStatisticsInterfaces 2 }

vtssIpStatisticsInterfacesIpv4Entry OBJECT-TYPE
    SYNTAX      VTSSIpStatisticsInterfacesIpv4Entry
    MAX-ACCESS  not-accessible
    STATUS      current
    DESCRIPTION
        "Each entry in this table represents an IP interface."
    INDEX       { vtssIpStatisticsInterfacesIpv4IfIndex }
    ::= { vtssIpStatisticsInterfacesIpv4Table 1 }

VTSSIpStatisticsInterfacesIpv4Entry ::= SEQUENCE {
    vtssIpStatisticsInterfacesIpv4IfIndex             VTSSInterfaceIndex,
    vtssIpStatisticsInterfacesIpv4InReceives          Unsigned32,
    vtssIpStatisticsInterfacesIpv4HCInReceives        Counter64,
    vtssIpStatisticsInterfacesIpv4InOctets            Unsigned32,
    vtssIpStatisticsInterfacesIpv4HCInOctets          Counter64,
    vtssIpStatisticsInterfacesIpv4InHdrErrors         Unsigned32,
    vtssIpStatisticsInterfacesIpv4InNoRoutes          Unsigned32,
    vtssIpStatisticsInterfacesIpv4InAddrErrors        Unsigned32,
    vtssIpStatisticsInterfacesIpv4InUnknownProtos     Unsigned32,
    vtssIpStatisticsInterfacesIpv4InTruncatedPkts     Unsigned32,
    vtssIpStatisticsInterfacesIpv4InForwDatagrams     Unsigned32,
    vtssIpStatisticsInterfacesIpv4HCInForwDatagrams   Counter64,
    vtssIpStatisticsInterfacesIpv4ReasmReqds          Unsigned32,
    vtssIpStatisticsInterfacesIpv4ReasmOKs            Unsigned32,
    vtssIpStatisticsInterfacesIpv4ReasmFails          Unsigned32,
    vtssIpStatisticsInterfacesIpv4InDiscards          Unsigned32,
    vtssIpStatisticsInterfacesIpv4InDelivers          Unsigned32,
    vtssIpStatisticsInterfacesIpv4HCInDelivers        Counter64,
    vtssIpStatisticsInterfacesIpv4OutRequests         Unsigned32,
    vtssIpStatisticsInterfacesIpv4HCOutRequests       Counter64,
    vtssIpStatisticsInterfacesIpv4OutNoRoutes         Unsigned32,
    vtssIpStatisticsInterfacesIpv4OutForwDatagrams    Unsigned32,
    vtssIpStatisticsInterfacesIpv4HCOutForwDatagrams  Counter64,
    vtssIpStatisticsInterfacesIpv4OutDiscards         Unsigned32,
    vtssIpStatisticsInterfacesIpv4OutFragReqds        Unsigned32,
    vtssIpStatisticsInterfacesIpv4OutFragOKs          Unsigned32,
    vtssIpStatisticsInterfacesIpv4OutFragFails        Unsigned32,
    vtssIpStatisticsInterfacesIpv4OutFragCreates      Unsigned32,
    vtssIpStatisticsInterfacesIpv4OutTransmits        Unsigned32,
    vtssIpStatisticsInterfacesIpv4HCOutTransmits      Counter64,
    vtssIpStatisticsInterfacesIpv4OutOctets           Unsigned32,
    vtssIpStatisticsInterfacesIpv4HCOutOctets         Counter64,
    vtssIpStatisticsInterfacesIpv4InMcastPkts         Unsigned32,
    vtssIpStatisticsInterfacesIpv4HCInMcastPkts       Counter64,
    vtssIpStatisticsInterfacesIpv4InMcastOctets       Unsigned32,
    vtssIpStatisticsInterfacesIpv4HCInMcastOctets     Counter64,
    vtssIpStatisticsInterfacesIpv4OutMcastPkts        Unsigned32,
    vtssIpStatisticsInterfacesIpv4HCOutMcastPkts      Counter64,
    vtssIpStatisticsInterfacesIpv4OutMcastOctets      Unsigned32,
    vtssIpStatisticsInterfacesIpv4HCOutMcastOctets    Counter64,
    vtssIpStatisticsInterfacesIpv4InBcastPkts         Unsigned32,
    vtssIpStatisticsInterfacesIpv4HCInBcastPkts       Counter64,
    vtssIpStatisticsInterfacesIpv4OutBcastPkts        Unsigned32,
    vtssIpStatisticsInterfacesIpv4HCOutBcastPkts      Counter64,
    vtssIpStatisticsInterfacesIpv4DiscontinuityTime   Counter64,
    vtssIpStatisticsInterfacesIpv4RefreshRate         Unsigned32
}

vtssIpStatisticsInterfacesIpv4IfIndex OBJECT-TYPE
    SYNTAX      VTSSInterfaceIndex
    MAX-ACCESS  accessible-for-notify
    STATUS      current
    DESCRIPTION
        "Interface index number.
         
         This object is only available if the capability object
         'vtssIpCapabilitiesHasPerInterfaceIpv4Statistics' is True."
    ::= { vtssIpStatisticsInterfacesIpv4Entry 1 }

vtssIpStatisticsInterfacesIpv4InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 2 }

vtssIpStatisticsInterfacesIpv4HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 3 }

vtssIpStatisticsInterfacesIpv4InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 4 }

vtssIpStatisticsInterfacesIpv4HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 5 }

vtssIpStatisticsInterfacesIpv4InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 6 }

vtssIpStatisticsInterfacesIpv4InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 7 }

vtssIpStatisticsInterfacesIpv4InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 8 }

vtssIpStatisticsInterfacesIpv4InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 9 }

vtssIpStatisticsInterfacesIpv4InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 10 }

vtssIpStatisticsInterfacesIpv4InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 11 }

vtssIpStatisticsInterfacesIpv4HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 12 }

vtssIpStatisticsInterfacesIpv4ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 13 }

vtssIpStatisticsInterfacesIpv4ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 14 }

vtssIpStatisticsInterfacesIpv4ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 15 }

vtssIpStatisticsInterfacesIpv4InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 16 }

vtssIpStatisticsInterfacesIpv4InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 17 }

vtssIpStatisticsInterfacesIpv4HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 18 }

vtssIpStatisticsInterfacesIpv4OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 19 }

vtssIpStatisticsInterfacesIpv4HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 20 }

vtssIpStatisticsInterfacesIpv4OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 21 }

vtssIpStatisticsInterfacesIpv4OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 22 }

vtssIpStatisticsInterfacesIpv4HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 23 }

vtssIpStatisticsInterfacesIpv4OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 24 }

vtssIpStatisticsInterfacesIpv4OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 25 }

vtssIpStatisticsInterfacesIpv4OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 26 }

vtssIpStatisticsInterfacesIpv4OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 27 }

vtssIpStatisticsInterfacesIpv4OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 28 }

vtssIpStatisticsInterfacesIpv4OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 29 }

vtssIpStatisticsInterfacesIpv4HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 30 }

vtssIpStatisticsInterfacesIpv4OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 31 }

vtssIpStatisticsInterfacesIpv4HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 32 }

vtssIpStatisticsInterfacesIpv4InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 33 }

vtssIpStatisticsInterfacesIpv4HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 34 }

vtssIpStatisticsInterfacesIpv4InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 35 }

vtssIpStatisticsInterfacesIpv4HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 36 }

vtssIpStatisticsInterfacesIpv4OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 37 }

vtssIpStatisticsInterfacesIpv4HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 38 }

vtssIpStatisticsInterfacesIpv4OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 39 }

vtssIpStatisticsInterfacesIpv4HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 40 }

vtssIpStatisticsInterfacesIpv4InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 41 }

vtssIpStatisticsInterfacesIpv4HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 42 }

vtssIpStatisticsInterfacesIpv4OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 43 }

vtssIpStatisticsInterfacesIpv4HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime.
         
         This object is only available if the capability object
         'vtssIpCapabilitiesHasPerInterfaceIpv4Statistics' is True."
    ::= { vtssIpStatisticsInterfacesIpv4Entry 44 }

vtssIpStatisticsInterfacesIpv4DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value.
         
         This object is only available if the capability object
         'vtssIpCapabilitiesHasPerInterfaceIpv4Statistics' is True."
    ::= { vtssIpStatisticsInterfacesIpv4Entry 45 }

vtssIpStatisticsInterfacesIpv4RefreshRate OBJECT-TYPE
    SYNTAX      Unsigned32
    MAX-ACCESS  read-only
    STATUS      current
    DESCRIPTION
        "The minimum reasonable polling interval for this entry. This object
         provides an indication of the minimum amount of time required to update
         the counters in this entry.
         
         This object is only available if the capability object
         'vtssIpCapabilitiesHasPerInterfaceIpv4Statistics' is True."
    ::= { vtssIpStatisticsInterfacesIpv4Entry 46 }

vtssIpStatisticsInterfacesIpv6Table OBJECT-TYPE
    SYNTAX      SEQUENCE OF VTSSIpStatisticsInterfacesIpv6Entry
    MAX-ACCESS  not-accessible
    STATUS      current
    DESCRIPTION
        "This table provides IPv6 related statitics for a given IP interface."
    ::= { vtssIpStatisticsInterfaces 3 }

vtssIpStatisticsInterfacesIpv6Entry OBJECT-TYPE
    SYNTAX      VTSSIpStatisticsInterfacesIpv6Entry
    MAX-ACCESS  not-accessible
    STATUS      current
    DESCRIPTION
        "Each entry in this table represents an IP interface."
    INDEX       { vtssIpStatisticsInterfacesIpv6IfIndex }
    ::= { vtssIpStatisticsInterfacesIpv6Table 1 }

VTSSIpStatisticsInterfacesIpv6Entry ::= SEQUENCE {
    vtssIpStatisticsInterfacesIpv6IfIndex             VTSSInterfaceIndex,
    vtssIpStatisticsInterfacesIpv6InReceives          Unsigned32,
    vtssIpStatisticsInterfacesIpv6HCInReceives        Counter64,
    vtssIpStatisticsInterfacesIpv6InOctets            Unsigned32,
    vtssIpStatisticsInterfacesIpv6HCInOctets          Counter64,
    vtssIpStatisticsInterfacesIpv6InHdrErrors         Unsigned32,
    vtssIpStatisticsInterfacesIpv6InNoRoutes          Unsigned32,
    vtssIpStatisticsInterfacesIpv6InAddrErrors        Unsigned32,
    vtssIpStatisticsInterfacesIpv6InUnknownProtos     Unsigned32,
    vtssIpStatisticsInterfacesIpv6InTruncatedPkts     Unsigned32,
    vtssIpStatisticsInterfacesIpv6InForwDatagrams     Unsigned32,
    vtssIpStatisticsInterfacesIpv6HCInForwDatagrams   Counter64,
    vtssIpStatisticsInterfacesIpv6ReasmReqds          Unsigned32,
    vtssIpStatisticsInterfacesIpv6ReasmOKs            Unsigned32,
    vtssIpStatisticsInterfacesIpv6ReasmFails          Unsigned32,
    vtssIpStatisticsInterfacesIpv6InDiscards          Unsigned32,
    vtssIpStatisticsInterfacesIpv6InDelivers          Unsigned32,
    vtssIpStatisticsInterfacesIpv6HCInDelivers        Counter64,
    vtssIpStatisticsInterfacesIpv6OutRequests         Unsigned32,
    vtssIpStatisticsInterfacesIpv6HCOutRequests       Counter64,
    vtssIpStatisticsInterfacesIpv6OutNoRoutes         Unsigned32,
    vtssIpStatisticsInterfacesIpv6OutForwDatagrams    Unsigned32,
    vtssIpStatisticsInterfacesIpv6HCOutForwDatagrams  Counter64,
    vtssIpStatisticsInterfacesIpv6OutDiscards         Unsigned32,
    vtssIpStatisticsInterfacesIpv6OutFragReqds        Unsigned32,
    vtssIpStatisticsInterfacesIpv6OutFragOKs          Unsigned32,
    vtssIpStatisticsInterfacesIpv6OutFragFails        Unsigned32,
    vtssIpStatisticsInterfacesIpv6OutFragCreates      Unsigned32,
    vtssIpStatisticsInterfacesIpv6OutTransmits        Unsigned32,
    vtssIpStatisticsInterfacesIpv6HCOutTransmits      Counter64,
    vtssIpStatisticsInterfacesIpv6OutOctets           Unsigned32,
    vtssIpStatisticsInterfacesIpv6HCOutOctets         Counter64,
    vtssIpStatisticsInterfacesIpv6InMcastPkts         Unsigned32,
    vtssIpStatisticsInterfacesIpv6HCInMcastPkts       Counter64,
    vtssIpStatisticsInterfacesIpv6InMcastOctets       Unsigned32,
    vtssIpStatisticsInterfacesIpv6HCInMcastOctets     Counter64,
    vtssIpStatisticsInterfacesIpv6OutMcastPkts        Unsigned32,
    vtssIpStatisticsInterfacesIpv6HCOutMcastPkts      Counter64,
    vtssIpStatisticsInterfacesIpv6OutMcastOctets      Unsigned32,
    vtssIpStatisticsInterfacesIpv6HCOutMcastOctets    Counter64,
    vtssIpStatisticsInterfacesIpv6InBcastPkts         Unsigned32,
    vtssIpStatisticsInterfacesIpv6HCInBcastPkts       Counter64,
    vtssIpStatisticsInterfacesIpv6OutBcastPkts        Unsigned32,
    vtssIpStatisticsInterfacesIpv6HCOutBcastPkts      Counter64,
    vtssIpStatisticsInterfacesIpv6DiscontinuityTime   Counter64,
    vtssIpStatisticsInterfacesIpv6RefreshRate         Unsigned32
}

vtssIpStatisticsInterfacesIpv6IfIndex OBJECT-TYPE
    SYNTAX      VTSSInterfaceIndex
    MAX-ACCESS  accessible-for-notify
    STATUS      current
    DESCRIPTION
        "Interface index number.
         
         This object is only available if the capability object
         'vtssIpCapabilitiesHasPerInterfaceIpv6Statistics' is True."
    ::= { vtssIpStatisticsInterfacesIpv6Entry 1 }

vtssIpStatisticsInterfacesIpv6InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 2 }

vtssIpStatisticsInterfacesIpv6HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 3 }

vtssIpStatisticsInterfacesIpv6InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 4 }

vtssIpStatisticsInterfacesIpv6HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 5 }

vtssIpStatisticsInterfacesIpv6InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 6 }

vtssIpStatisticsInterfacesIpv6InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 7 }

vtssIpStatisticsInterfacesIpv6InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 8 }

vtssIpStatisticsInterfacesIpv6InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 9 }

vtssIpStatisticsInterfacesIpv6InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 10 }

vtssIpStatisticsInterfacesIpv6InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 11 }

vtssIpStatisticsInterfacesIpv6HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 12 }

vtssIpStatisticsInterfacesIpv6ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 13 }

vtssIpStatisticsInterfacesIpv6ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 14 }

vtssIpStatisticsInterfacesIpv6ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 15 }

vtssIpStatisticsInterfacesIpv6InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 16 }

vtssIpStatisticsInterfacesIpv6InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 17 }

vtssIpStatisticsInterfacesIpv6HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 18 }

vtssIpStatisticsInterfacesIpv6OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 19 }

vtssIpStatisticsInterfacesIpv6HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 20 }

vtssIpStatisticsInterfacesIpv6OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 21 }

vtssIpStatisticsInterfacesIpv6OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 22 }

vtssIpStatisticsInterfacesIpv6HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 23 }

vtssIpStatisticsInterfacesIpv6OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 24 }

vtssIpStatisticsInterfacesIpv6OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 25 }

vtssIpStatisticsInterfacesIpv6OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 26 }

vtssIpStatisticsInterfacesIpv6OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 27 }

vtssIpStatisticsInterfacesIpv6OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 28 }

vtssIpStatisticsInterfacesIpv6OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 29 }

vtssIpStatisticsInterfacesIpv6HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 30 }

vtssIpStatisticsInterfacesIpv6OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 31 }

vtssIpStatisticsInterfacesIpv6HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 32 }

vtssIpStatisticsInterfacesIpv6InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 33 }

vtssIpStatisticsInterfacesIpv6HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 34 }

vtssIpStatisticsInterfacesIpv6InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 35 }

vtssIpStatisticsInterfacesIpv6HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 36 }

vtssIpStatisticsInterfacesIpv6OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 37 }

vtssIpStatisticsInterfacesIpv6HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 38 }

vtssIpStatisticsInterfacesIpv6OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 39 }

vtssIpStatisticsInterfacesIpv6HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 40 }

vtssIpStatisticsInterfacesIpv6InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 41 }

vtssIpStatisticsInterfacesIpv6HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 42 }

vtssIpStatisticsInterfacesIpv6OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 43 }

vtssIpStatisticsInterfacesIpv6HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime.
         
         This object is only available if the capability object
         'vtssIpCapabilitiesHasPerInterfaceIpv6Statistics' is True."
    ::= { vtssIpStatisticsInterfacesIpv6Entry 44 }

vtssIpStatisticsInterfacesIpv6DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value.
         
         This object is only available if the capability object
         'vtssIpCapabilitiesHasPerInterfaceIpv6Statistics' is True."
    ::= { vtssIpStatisticsInterfacesIpv6Entry 45 }

vtssIpStatisticsInterfacesIpv6RefreshRate OBJECT-TYPE
    SYNTAX      Unsigned32
    MAX-ACCESS  read-only
    STATUS      current
    DESCRIPTION
        "The minimum reasonable polling interval for this entry. This object
         provides an indication of the minimum amount of time required to update
         the counters in this entry.
         
         This object is only available if the capability object
         'vtssIpCapabilitiesHasPerInterfaceIpv6Statistics' is True."
    ::= { vtssIpStatisticsInterfacesIpv6Entry 46 }

vtssIpTrap OBJECT IDENTIFIER
    ::= { vtssIpMibObjects 6 }

vtssIpTrapInterfacesLinkAdd NOTIFICATION-TYPE
    OBJECTS     { vtssIpStatusInterfacesLinkIfIndex,
                  vtssIpStatusInterfacesLinkOsInterfaceIndex,
                  vtssIpStatusInterfacesLinkMtu,
                  vtssIpStatusInterfacesLinkMacAddress,
                  vtssIpStatusInterfacesLinkUp,
                  vtssIpStatusInterfacesLinkBroadcast,
                  vtssIpStatusInterfacesLinkLoopback,
                  vtssIpStatusInterfacesLinkRunning,
                  vtssIpStatusInterfacesLinkNoarp,
                  vtssIpStatusInterfacesLinkPromisc,
                  vtssIpStatusInterfacesLinkMulticast }
    STATUS      current
    DESCRIPTION
        "This trap signals that a row has been added. The index(es) and value(s)
         of the row is included in the trap."

    ::= { vtssIpTrap 1 }

vtssIpTrapInterfacesLinkMod NOTIFICATION-TYPE
    OBJECTS     { vtssIpStatusInterfacesLinkIfIndex,
                  vtssIpStatusInterfacesLinkOsInterfaceIndex,
                  vtssIpStatusInterfacesLinkMtu,
                  vtssIpStatusInterfacesLinkMacAddress,
                  vtssIpStatusInterfacesLinkUp,
                  vtssIpStatusInterfacesLinkBroadcast,
                  vtssIpStatusInterfacesLinkLoopback,
                  vtssIpStatusInterfacesLinkRunning,
                  vtssIpStatusInterfacesLinkNoarp,
                  vtssIpStatusInterfacesLinkPromisc,
                  vtssIpStatusInterfacesLinkMulticast }
    STATUS      current
    DESCRIPTION
        "This trap signals that one or more of the objects included in the trap
          has been updated."

    ::= { vtssIpTrap 2 }

vtssIpTrapInterfacesLinkDel NOTIFICATION-TYPE
    OBJECTS     { vtssIpStatusInterfacesLinkIfIndex }
    STATUS      current
    DESCRIPTION
        "This trap signals that a row has been deleted. The index(es) of the
         row is included in the trap."

    ::= { vtssIpTrap 3 }

vtssIpTrapGlobalsMain NOTIFICATION-TYPE
    OBJECTS     {                   vtssIpStatusGlobalsNotificationHwRoutingTableDepleted }
    STATUS      current
    DESCRIPTION
        "This trap signals that one or more of the objects included in the trap
         has been updated."

    ::= { vtssIpTrap 4 }

vtssIpMibConformance OBJECT IDENTIFIER
    ::= { vtssIpMib 2 }

vtssIpMibCompliances OBJECT IDENTIFIER
    ::= { vtssIpMibConformance 1 }

vtssIpMibGroups OBJECT IDENTIFIER
    ::= { vtssIpMibConformance 2 }

vtssIpCapabilitiesInfoGroup OBJECT-GROUP
    OBJECTS     { vtssIpCapabilitiesHasIpv4HostCapabilities,
                  vtssIpCapabilitiesHasIpv6HostCapabilities,
                  vtssIpCapabilitiesHasIpv4UnicastRoutingCapabilities,
                  vtssIpCapabilitiesHasIpv4UnicastHwRoutingCapabilities,
                  vtssIpCapabilitiesHasIpv6UnicastRoutingCapabilities,
                  vtssIpCapabilitiesHasIpv6UnicastHwRoutingCapabilities,
                  vtssIpCapabilitiesMaxNumberOfIpInterfaces,
                  vtssIpCapabilitiesMaxNumberOfStaticRoutes,
                  vtssIpCapabilitiesNumberOfLpmHardwareEntries,
                  vtssIpCapabilitiesHasPerInterfaceIpv4Statistics,
                  vtssIpCapabilitiesHasPerInterfaceIpv6Statistics }
    STATUS      current
    DESCRIPTION
        "A collection of objects."
    ::= { vtssIpMibGroups 1 }

vtssIpConfigGlobalsMainInfoGroup OBJECT-GROUP
    OBJECTS     { vtssIpConfigGlobalsMainEnableRouting }
    STATUS      current
    DESCRIPTION
        "A collection of objects."
    ::= { vtssIpMibGroups 2 }

vtssIpConfigInterfacesTableInfoGroup OBJECT-GROUP
    OBJECTS     { vtssIpConfigInterfacesIfIndex,
                  vtssIpConfigInterfacesMtu,
                  vtssIpConfigInterfacesAction }
    STATUS      current
    DESCRIPTION
        "A collection of objects."
    ::= { vtssIpMibGroups 3 }

vtssIpConfigInterfacesTableRowEditorInfoGroup OBJECT-GROUP
    OBJECTS     { vtssIpConfigInterfacesTableRowEditorIfIndex,
                  vtssIpConfigInterfacesTableRowEditorMtu,
                  vtssIpConfigInterfacesTableRowEditorAction }
    STATUS      current
    DESCRIPTION
        "A collection of objects."
    ::= { vtssIpMibGroups 4 }

vtssIpConfigInterfacesIpv4TableInfoGroup OBJECT-GROUP
    OBJECTS     { vtssIpConfigInterfacesIpv4IfIndex,
                  vtssIpConfigInterfacesIpv4Active,
                  vtssIpConfigInterfacesIpv4EnableDhcpClient,
                  vtssIpConfigInterfacesIpv4Ipv4Address,
                  vtssIpConfigInterfacesIpv4PrefixSize,
                  vtssIpConfigInterfacesIpv4DhcpClientFallbackTimeout,
                  vtssIpConfigInterfacesIpv4DhcpClientHostname,
                  vtssIpConfigInterfacesIpv4DhcpClientIdType,
                  vtssIpConfigInterfacesIpv4DhcpClientIdIfMac,
                  vtssIpConfigInterfacesIpv4DhcpClientIdAscii,
                  vtssIpConfigInterfacesIpv4DhcpClientIdHex }
    STATUS      current
    DESCRIPTION
        "A collection of objects."
    ::= { vtssIpMibGroups 5 }

vtssIpConfigInterfacesIpv6TableInfoGroup OBJECT-GROUP
    OBJECTS     { vtssIpConfigInterfacesIpv6IfIndex,
                  vtssIpConfigInterfacesIpv6Active,
                  vtssIpConfigInterfacesIpv6Ipv6Address,
                  vtssIpConfigInterfacesIpv6PrefixSize }
    STATUS      current
    DESCRIPTION
        "A collection of objects."
    ::= { vtssIpMibGroups 6 }

vtssIpConfigRoutesIpv4TableInfoGroup OBJECT-GROUP
    OBJECTS     { vtssIpConfigRoutesIpv4NetworkAddress,
                  vtssIpConfigRoutesIpv4NetworkPrefixSize,
                  vtssIpConfigRoutesIpv4NextHop,
                  vtssIpConfigRoutesIpv4Distance,
                  vtssIpConfigRoutesIpv4Action }
    STATUS      current
    DESCRIPTION
        "A collection of objects."
    ::= { vtssIpMibGroups 7 }

vtssIpConfigRoutesIpv4RowEditorInfoGroup OBJECT-GROUP
    OBJECTS     { vtssIpConfigRoutesIpv4RowEditorNetworkAddress,
                  vtssIpConfigRoutesIpv4RowEditorNetworkPrefixSize,
                  vtssIpConfigRoutesIpv4RowEditorNextHop,
                  vtssIpConfigRoutesIpv4RowEditorDistance,
                  vtssIpConfigRoutesIpv4RowEditorAction }
    STATUS      current
    DESCRIPTION
        "A collection of objects."
    ::= { vtssIpMibGroups 8 }

vtssIpConfigRoutesIpv6TableInfoGroup OBJECT-GROUP
    OBJECTS     { vtssIpConfigRoutesIpv6NetworkAddress,
                  vtssIpConfigRoutesIpv6NetworkPrefixSize,
                  vtssIpConfigRoutesIpv6NextHop,
                  vtssIpConfigRoutesIpv6NextHopInterface,
                  vtssIpConfigRoutesIpv6Distance,
                  vtssIpConfigRoutesIpv6Action }
    STATUS      current
    DESCRIPTION
        "A collection of objects."
    ::= { vtssIpMibGroups 9 }

vtssIpConfigRoutesIpv6RowEditorInfoGroup OBJECT-GROUP
    OBJECTS     { vtssIpConfigRoutesIpv6RowEditorNetworkAddress,
                  vtssIpConfigRoutesIpv6RowEditorNetworkPrefixSize,
                  vtssIpConfigRoutesIpv6RowEditorNextHop,
                  vtssIpConfigRoutesIpv6RowEditorNextHopInterface,
                  vtssIpConfigRoutesIpv6RowEditorDistance,
                  vtssIpConfigRoutesIpv6RowEditorAction }
    STATUS      current
    DESCRIPTION
        "A collection of objects."
    ::= { vtssIpMibGroups 10 }

vtssIpStatusGlobalsIpv4NeighborInfoGroup OBJECT-GROUP
    OBJECTS     { vtssIpStatusGlobalsIpv4NeighborIpv4,
                  vtssIpStatusGlobalsIpv4NeighborMacAddress,
                  vtssIpStatusGlobalsIpv4NeighborInterface }
    STATUS      current
    DESCRIPTION
        "A collection of objects."
    ::= { vtssIpMibGroups 11 }

vtssIpStatusGlobalsIpv6NeighborInfoGroup OBJECT-GROUP
    OBJECTS     { vtssIpStatusGlobalsIpv6NeighborIpv6,
                  vtssIpStatusGlobalsIpv6NeighborIfindex,
                  vtssIpStatusGlobalsIpv6NeighborMacAddress,
                  vtssIpStatusGlobalsIpv6NeighborInterface }
    STATUS      current
    DESCRIPTION
        "A collection of objects."
    ::= { vtssIpMibGroups 12 }

vtssIpStatusGlobalsNotificationInfoGroup OBJECT-GROUP
    OBJECTS     {                   vtssIpStatusGlobalsNotificationHwRoutingTableDepleted }
    STATUS      current
    DESCRIPTION
        "A collection of objects."
    ::= { vtssIpMibGroups 13 }

vtssIpStatusInterfacesLinkInfoGroup OBJECT-GROUP
    OBJECTS     { vtssIpStatusInterfacesLinkIfIndex,
                  vtssIpStatusInterfacesLinkOsInterfaceIndex,
                  vtssIpStatusInterfacesLinkMtu,
                  vtssIpStatusInterfacesLinkMacAddress,
                  vtssIpStatusInterfacesLinkUp,
                  vtssIpStatusInterfacesLinkBroadcast,
                  vtssIpStatusInterfacesLinkLoopback,
                  vtssIpStatusInterfacesLinkRunning,
                  vtssIpStatusInterfacesLinkNoarp,
                  vtssIpStatusInterfacesLinkPromisc,
                  vtssIpStatusInterfacesLinkMulticast }
    STATUS      current
    DESCRIPTION
        "A collection of objects."
    ::= { vtssIpMibGroups 14 }

vtssIpStatusInterfacesIpv4InfoGroup OBJECT-GROUP
    OBJECTS     { vtssIpStatusInterfacesIpv4IfIndex,
                  vtssIpStatusInterfacesIpv4NetworkAddress,
                  vtssIpStatusInterfacesIpv4NetworkMaskLength,
                  vtssIpStatusInterfacesIpv4Broadcast }
    STATUS      current
    DESCRIPTION
        "A collection of objects."
    ::= { vtssIpMibGroups 15 }

vtssIpStatusInterfacesDhcpClientV4InfoGroup OBJECT-GROUP
    OBJECTS     { vtssIpStatusInterfacesDhcpClientV4IfIndex,
                  vtssIpStatusInterfacesDhcpClientV4State,
                  vtssIpStatusInterfacesDhcpClientV4ServerIp }
    STATUS      current
    DESCRIPTION
        "A collection of objects."
    ::= { vtssIpMibGroups 16 }

vtssIpStatusInterfacesIpv6InfoGroup OBJECT-GROUP
    OBJECTS     { vtssIpStatusInterfacesIpv6IfIndex,
                  vtssIpStatusInterfacesIpv6NetworkAddress,
                  vtssIpStatusInterfacesIpv6NetworkMaskLength,
                  vtssIpStatusInterfacesIpv6Tentative,
                  vtssIpStatusInterfacesIpv6Duplicated,
                  vtssIpStatusInterfacesIpv6Detached,
                  vtssIpStatusInterfacesIpv6Nodad,
                  vtssIpStatusInterfacesIpv6Autoconf }
    STATUS      current
    DESCRIPTION
        "A collection of objects."
    ::= { vtssIpMibGroups 17 }

vtssIpStatusRoutesIpv4InfoGroup OBJECT-GROUP
    OBJECTS     { vtssIpStatusRoutesIpv4NetworkAddress,
                  vtssIpStatusRoutesIpv4NetworkPrefixSize,
                  vtssIpStatusRoutesIpv4Protocol,
                  vtssIpStatusRoutesIpv4NextHop,
                  vtssIpStatusRoutesIpv4NextHopInterface,
                  vtssIpStatusRoutesIpv4Selected,
                  vtssIpStatusRoutesIpv4Active,
                  vtssIpStatusRoutesIpv4Fib,
                  vtssIpStatusRoutesIpv4DirectlyConnected,
                  vtssIpStatusRoutesIpv4Onlink,
                  vtssIpStatusRoutesIpv4Duplicate,
                  vtssIpStatusRoutesIpv4Recursive,
                  vtssIpStatusRoutesIpv4Unreachable,
                  vtssIpStatusRoutesIpv4Reject,
                  vtssIpStatusRoutesIpv4AdminProhib,
                  vtssIpStatusRoutesIpv4Blackhole,
                  vtssIpStatusRoutesIpv4Metric,
                  vtssIpStatusRoutesIpv4Distance,
                  vtssIpStatusRoutesIpv4Uptime }
    STATUS      current
    DESCRIPTION
        "A collection of objects."
    ::= { vtssIpMibGroups 18 }

vtssIpStatusRoutesIpv6InfoGroup OBJECT-GROUP
    OBJECTS     { vtssIpStatusRoutesIpv6NetworkAddress,
                  vtssIpStatusRoutesIpv6NetworkPrefixSize,
                  vtssIpStatusRoutesIpv6Protocol,
                  vtssIpStatusRoutesIpv6NextHop,
                  vtssIpStatusRoutesIpv6NextHopInterface,
                  vtssIpStatusRoutesIpv6Selected,
                  vtssIpStatusRoutesIpv6Active,
                  vtssIpStatusRoutesIpv6Fib,
                  vtssIpStatusRoutesIpv6DirectlyConnected,
                  vtssIpStatusRoutesIpv6Onlink,
                  vtssIpStatusRoutesIpv6Duplicate,
                  vtssIpStatusRoutesIpv6Recursive,
                  vtssIpStatusRoutesIpv6Unreachable,
                  vtssIpStatusRoutesIpv6Reject,
                  vtssIpStatusRoutesIpv6AdminProhib,
                  vtssIpStatusRoutesIpv6Blackhole,
                  vtssIpStatusRoutesIpv6Metric,
                  vtssIpStatusRoutesIpv6Distance,
                  vtssIpStatusRoutesIpv6Uptime }
    STATUS      current
    DESCRIPTION
        "A collection of objects."
    ::= { vtssIpMibGroups 19 }

vtssIpControlGlobalsInfoGroup OBJECT-GROUP
    OBJECTS     { vtssIpControlGlobalsIpv4NeighborTableClear,
                  vtssIpControlGlobalsIpv6NeighborTableClear,
                  vtssIpControlGlobalsIpv4SystemStatisticsClear,
                  vtssIpControlGlobalsIpv6SystemStatisticsClear,
                  vtssIpControlGlobalsIpv4AcdStatusClear }
    STATUS      current
    DESCRIPTION
        "A collection of objects."
    ::= { vtssIpMibGroups 20 }

vtssIpControlInterfaceDhcpClientInfoGroup OBJECT-GROUP
    OBJECTS     { vtssIpControlInterfaceDhcpClientIfIndex,
                  vtssIpControlInterfaceDhcpClientRestart }
    STATUS      current
    DESCRIPTION
        "A collection of objects."
    ::= { vtssIpMibGroups 21 }

vtssIpStatisticsGlobalsIpv4InfoGroup OBJECT-GROUP
    OBJECTS     { vtssIpStatisticsGlobalsIpv4InReceives,
                  vtssIpStatisticsGlobalsIpv4HCInReceives,
                  vtssIpStatisticsGlobalsIpv4InOctets,
                  vtssIpStatisticsGlobalsIpv4HCInOctets,
                  vtssIpStatisticsGlobalsIpv4InHdrErrors,
                  vtssIpStatisticsGlobalsIpv4InNoRoutes,
                  vtssIpStatisticsGlobalsIpv4InAddrErrors,
                  vtssIpStatisticsGlobalsIpv4InUnknownProtos,
                  vtssIpStatisticsGlobalsIpv4InTruncatedPkts,
                  vtssIpStatisticsGlobalsIpv4InForwDatagrams,
                  vtssIpStatisticsGlobalsIpv4HCInForwDatagrams,
                  vtssIpStatisticsGlobalsIpv4ReasmReqds,
                  vtssIpStatisticsGlobalsIpv4ReasmOKs,
                  vtssIpStatisticsGlobalsIpv4ReasmFails,
                  vtssIpStatisticsGlobalsIpv4InDiscards,
                  vtssIpStatisticsGlobalsIpv4InDelivers,
                  vtssIpStatisticsGlobalsIpv4HCInDelivers,
                  vtssIpStatisticsGlobalsIpv4OutRequests,
                  vtssIpStatisticsGlobalsIpv4HCOutRequests,
                  vtssIpStatisticsGlobalsIpv4OutNoRoutes,
                  vtssIpStatisticsGlobalsIpv4OutForwDatagrams,
                  vtssIpStatisticsGlobalsIpv4HCOutForwDatagrams,
                  vtssIpStatisticsGlobalsIpv4OutDiscards,
                  vtssIpStatisticsGlobalsIpv4OutFragReqds,
                  vtssIpStatisticsGlobalsIpv4OutFragOKs,
                  vtssIpStatisticsGlobalsIpv4OutFragFails,
                  vtssIpStatisticsGlobalsIpv4OutFragCreates,
                  vtssIpStatisticsGlobalsIpv4OutTransmits,
                  vtssIpStatisticsGlobalsIpv4HCOutTransmits,
                  vtssIpStatisticsGlobalsIpv4OutOctets,
                  vtssIpStatisticsGlobalsIpv4HCOutOctets,
                  vtssIpStatisticsGlobalsIpv4InMcastPkts,
                  vtssIpStatisticsGlobalsIpv4HCInMcastPkts,
                  vtssIpStatisticsGlobalsIpv4InMcastOctets,
                  vtssIpStatisticsGlobalsIpv4HCInMcastOctets,
                  vtssIpStatisticsGlobalsIpv4OutMcastPkts,
                  vtssIpStatisticsGlobalsIpv4HCOutMcastPkts,
                  vtssIpStatisticsGlobalsIpv4OutMcastOctets,
                  vtssIpStatisticsGlobalsIpv4HCOutMcastOctets,
                  vtssIpStatisticsGlobalsIpv4InBcastPkts,
                  vtssIpStatisticsGlobalsIpv4HCInBcastPkts,
                  vtssIpStatisticsGlobalsIpv4OutBcastPkts,
                  vtssIpStatisticsGlobalsIpv4HCOutBcastPkts,
                  vtssIpStatisticsGlobalsIpv4DiscontinuityTime,
                  vtssIpStatisticsGlobalsIpv4RefreshRate }
    STATUS      current
    DESCRIPTION
        "A collection of objects."
    ::= { vtssIpMibGroups 22 }

vtssIpStatisticsGlobalsIpv6InfoGroup OBJECT-GROUP
    OBJECTS     { vtssIpStatisticsGlobalsIpv6InReceives,
                  vtssIpStatisticsGlobalsIpv6HCInReceives,
                  vtssIpStatisticsGlobalsIpv6InOctets,
                  vtssIpStatisticsGlobalsIpv6HCInOctets,
                  vtssIpStatisticsGlobalsIpv6InHdrErrors,
                  vtssIpStatisticsGlobalsIpv6InNoRoutes,
                  vtssIpStatisticsGlobalsIpv6InAddrErrors,
                  vtssIpStatisticsGlobalsIpv6InUnknownProtos,
                  vtssIpStatisticsGlobalsIpv6InTruncatedPkts,
                  vtssIpStatisticsGlobalsIpv6InForwDatagrams,
                  vtssIpStatisticsGlobalsIpv6HCInForwDatagrams,
                  vtssIpStatisticsGlobalsIpv6ReasmReqds,
                  vtssIpStatisticsGlobalsIpv6ReasmOKs,
                  vtssIpStatisticsGlobalsIpv6ReasmFails,
                  vtssIpStatisticsGlobalsIpv6InDiscards,
                  vtssIpStatisticsGlobalsIpv6InDelivers,
                  vtssIpStatisticsGlobalsIpv6HCInDelivers,
                  vtssIpStatisticsGlobalsIpv6OutRequests,
                  vtssIpStatisticsGlobalsIpv6HCOutRequests,
                  vtssIpStatisticsGlobalsIpv6OutNoRoutes,
                  vtssIpStatisticsGlobalsIpv6OutForwDatagrams,
                  vtssIpStatisticsGlobalsIpv6HCOutForwDatagrams,
                  vtssIpStatisticsGlobalsIpv6OutDiscards,
                  vtssIpStatisticsGlobalsIpv6OutFragReqds,
                  vtssIpStatisticsGlobalsIpv6OutFragOKs,
                  vtssIpStatisticsGlobalsIpv6OutFragFails,
                  vtssIpStatisticsGlobalsIpv6OutFragCreates,
                  vtssIpStatisticsGlobalsIpv6OutTransmits,
                  vtssIpStatisticsGlobalsIpv6HCOutTransmits,
                  vtssIpStatisticsGlobalsIpv6OutOctets,
                  vtssIpStatisticsGlobalsIpv6HCOutOctets,
                  vtssIpStatisticsGlobalsIpv6InMcastPkts,
                  vtssIpStatisticsGlobalsIpv6HCInMcastPkts,
                  vtssIpStatisticsGlobalsIpv6InMcastOctets,
                  vtssIpStatisticsGlobalsIpv6HCInMcastOctets,
                  vtssIpStatisticsGlobalsIpv6OutMcastPkts,
                  vtssIpStatisticsGlobalsIpv6HCOutMcastPkts,
                  vtssIpStatisticsGlobalsIpv6OutMcastOctets,
                  vtssIpStatisticsGlobalsIpv6HCOutMcastOctets,
                  vtssIpStatisticsGlobalsIpv6InBcastPkts,
                  vtssIpStatisticsGlobalsIpv6HCInBcastPkts,
                  vtssIpStatisticsGlobalsIpv6OutBcastPkts,
                  vtssIpStatisticsGlobalsIpv6HCOutBcastPkts,
                  vtssIpStatisticsGlobalsIpv6DiscontinuityTime,
                  vtssIpStatisticsGlobalsIpv6RefreshRate }
    STATUS      current
    DESCRIPTION
        "A collection of objects."
    ::= { vtssIpMibGroups 23 }

vtssIpStatisticsInterfacesLinkInfoGroup OBJECT-GROUP
    OBJECTS     { vtssIpStatisticsInterfacesLinkIfIndex,
                  vtssIpStatisticsInterfacesLinkInPackets,
                  vtssIpStatisticsInterfacesLinkOutPackets,
                  vtssIpStatisticsInterfacesLinkInBytes,
                  vtssIpStatisticsInterfacesLinkOutBytes,
                  vtssIpStatisticsInterfacesLinkInMulticasts,
                  vtssIpStatisticsInterfacesLinkOutMulticasts,
                  vtssIpStatisticsInterfacesLinkInBroadcasts,
                  vtssIpStatisticsInterfacesLinkOutBroadcasts }
    STATUS      current
    DESCRIPTION
        "A collection of objects."
    ::= { vtssIpMibGroups 24 }

vtssIpStatisticsInterfacesIpv4InfoGroup OBJECT-GROUP
    OBJECTS     { vtssIpStatisticsInterfacesIpv4IfIndex,
                  vtssIpStatisticsInterfacesIpv4InReceives,
                  vtssIpStatisticsInterfacesIpv4HCInReceives,
                  vtssIpStatisticsInterfacesIpv4InOctets,
                  vtssIpStatisticsInterfacesIpv4HCInOctets,
                  vtssIpStatisticsInterfacesIpv4InHdrErrors,
                  vtssIpStatisticsInterfacesIpv4InNoRoutes,
                  vtssIpStatisticsInterfacesIpv4InAddrErrors,
                  vtssIpStatisticsInterfacesIpv4InUnknownProtos,
                  vtssIpStatisticsInterfacesIpv4InTruncatedPkts,
                  vtssIpStatisticsInterfacesIpv4InForwDatagrams,
                  vtssIpStatisticsInterfacesIpv4HCInForwDatagrams,
                  vtssIpStatisticsInterfacesIpv4ReasmReqds,
                  vtssIpStatisticsInterfacesIpv4ReasmOKs,
                  vtssIpStatisticsInterfacesIpv4ReasmFails,
                  vtssIpStatisticsInterfacesIpv4InDiscards,
                  vtssIpStatisticsInterfacesIpv4InDelivers,
                  vtssIpStatisticsInterfacesIpv4HCInDelivers,
                  vtssIpStatisticsInterfacesIpv4OutRequests,
                  vtssIpStatisticsInterfacesIpv4HCOutRequests,
                  vtssIpStatisticsInterfacesIpv4OutNoRoutes,
                  vtssIpStatisticsInterfacesIpv4OutForwDatagrams,
                  vtssIpStatisticsInterfacesIpv4HCOutForwDatagrams,
                  vtssIpStatisticsInterfacesIpv4OutDiscards,
                  vtssIpStatisticsInterfacesIpv4OutFragReqds,
                  vtssIpStatisticsInterfacesIpv4OutFragOKs,
                  vtssIpStatisticsInterfacesIpv4OutFragFails,
                  vtssIpStatisticsInterfacesIpv4OutFragCreates,
                  vtssIpStatisticsInterfacesIpv4OutTransmits,
                  vtssIpStatisticsInterfacesIpv4HCOutTransmits,
                  vtssIpStatisticsInterfacesIpv4OutOctets,
                  vtssIpStatisticsInterfacesIpv4HCOutOctets,
                  vtssIpStatisticsInterfacesIpv4InMcastPkts,
                  vtssIpStatisticsInterfacesIpv4HCInMcastPkts,
                  vtssIpStatisticsInterfacesIpv4InMcastOctets,
                  vtssIpStatisticsInterfacesIpv4HCInMcastOctets,
                  vtssIpStatisticsInterfacesIpv4OutMcastPkts,
                  vtssIpStatisticsInterfacesIpv4HCOutMcastPkts,
                  vtssIpStatisticsInterfacesIpv4OutMcastOctets,
                  vtssIpStatisticsInterfacesIpv4HCOutMcastOctets,
                  vtssIpStatisticsInterfacesIpv4InBcastPkts,
                  vtssIpStatisticsInterfacesIpv4HCInBcastPkts,
                  vtssIpStatisticsInterfacesIpv4OutBcastPkts,
                  vtssIpStatisticsInterfacesIpv4HCOutBcastPkts,
                  vtssIpStatisticsInterfacesIpv4DiscontinuityTime,
                  vtssIpStatisticsInterfacesIpv4RefreshRate }
    STATUS      current
    DESCRIPTION
        "A collection of objects."
    ::= { vtssIpMibGroups 25 }

vtssIpStatisticsInterfacesIpv6InfoGroup OBJECT-GROUP
    OBJECTS     { vtssIpStatisticsInterfacesIpv6IfIndex,
                  vtssIpStatisticsInterfacesIpv6InReceives,
                  vtssIpStatisticsInterfacesIpv6HCInReceives,
                  vtssIpStatisticsInterfacesIpv6InOctets,
                  vtssIpStatisticsInterfacesIpv6HCInOctets,
                  vtssIpStatisticsInterfacesIpv6InHdrErrors,
                  vtssIpStatisticsInterfacesIpv6InNoRoutes,
                  vtssIpStatisticsInterfacesIpv6InAddrErrors,
                  vtssIpStatisticsInterfacesIpv6InUnknownProtos,
                  vtssIpStatisticsInterfacesIpv6InTruncatedPkts,
                  vtssIpStatisticsInterfacesIpv6InForwDatagrams,
                  vtssIpStatisticsInterfacesIpv6HCInForwDatagrams,
                  vtssIpStatisticsInterfacesIpv6ReasmReqds,
                  vtssIpStatisticsInterfacesIpv6ReasmOKs,
                  vtssIpStatisticsInterfacesIpv6ReasmFails,
                  vtssIpStatisticsInterfacesIpv6InDiscards,
                  vtssIpStatisticsInterfacesIpv6InDelivers,
                  vtssIpStatisticsInterfacesIpv6HCInDelivers,
                  vtssIpStatisticsInterfacesIpv6OutRequests,
                  vtssIpStatisticsInterfacesIpv6HCOutRequests,
                  vtssIpStatisticsInterfacesIpv6OutNoRoutes,
                  vtssIpStatisticsInterfacesIpv6OutForwDatagrams,
                  vtssIpStatisticsInterfacesIpv6HCOutForwDatagrams,
                  vtssIpStatisticsInterfacesIpv6OutDiscards,
                  vtssIpStatisticsInterfacesIpv6OutFragReqds,
                  vtssIpStatisticsInterfacesIpv6OutFragOKs,
                  vtssIpStatisticsInterfacesIpv6OutFragFails,
                  vtssIpStatisticsInterfacesIpv6OutFragCreates,
                  vtssIpStatisticsInterfacesIpv6OutTransmits,
                  vtssIpStatisticsInterfacesIpv6HCOutTransmits,
                  vtssIpStatisticsInterfacesIpv6OutOctets,
                  vtssIpStatisticsInterfacesIpv6HCOutOctets,
                  vtssIpStatisticsInterfacesIpv6InMcastPkts,
                  vtssIpStatisticsInterfacesIpv6HCInMcastPkts,
                  vtssIpStatisticsInterfacesIpv6InMcastOctets,
                  vtssIpStatisticsInterfacesIpv6HCInMcastOctets,
                  vtssIpStatisticsInterfacesIpv6OutMcastPkts,
                  vtssIpStatisticsInterfacesIpv6HCOutMcastPkts,
                  vtssIpStatisticsInterfacesIpv6OutMcastOctets,
                  vtssIpStatisticsInterfacesIpv6HCOutMcastOctets,
                  vtssIpStatisticsInterfacesIpv6InBcastPkts,
                  vtssIpStatisticsInterfacesIpv6HCInBcastPkts,
                  vtssIpStatisticsInterfacesIpv6OutBcastPkts,
                  vtssIpStatisticsInterfacesIpv6HCOutBcastPkts,
                  vtssIpStatisticsInterfacesIpv6DiscontinuityTime,
                  vtssIpStatisticsInterfacesIpv6RefreshRate }
    STATUS      current
    DESCRIPTION
        "A collection of objects."
    ::= { vtssIpMibGroups 26 }

vtssIpTrapInterfacesLinkAddInfoGroup NOTIFICATION-GROUP
    NOTIFICATIONS { vtssIpTrapInterfacesLinkAdd }
    STATUS      current
    DESCRIPTION
        "Information group containing a trap."
    ::= { vtssIpMibGroups 27 }

vtssIpTrapInterfacesLinkModInfoGroup NOTIFICATION-GROUP
    NOTIFICATIONS { vtssIpTrapInterfacesLinkMod }
    STATUS      current
    DESCRIPTION
        "Information group containing a trap."
    ::= { vtssIpMibGroups 28 }

vtssIpTrapInterfacesLinkDelInfoGroup NOTIFICATION-GROUP
    NOTIFICATIONS { vtssIpTrapInterfacesLinkDel }
    STATUS      current
    DESCRIPTION
        "Information group containing a trap."
    ::= { vtssIpMibGroups 29 }

vtssIpTrapGlobalsMainInfoGroup NOTIFICATION-GROUP
    NOTIFICATIONS { vtssIpTrapGlobalsMain }
    STATUS      current
    DESCRIPTION
        "Information group containing a trap."
    ::= { vtssIpMibGroups 30 }

vtssIpMibCompliance MODULE-COMPLIANCE
    STATUS      current
    DESCRIPTION
        "The compliance statement for the implementation."

    MODULE      -- this module

    MANDATORY-GROUPS { vtssIpCapabilitiesInfoGroup,
                       vtssIpConfigGlobalsMainInfoGroup,
                       vtssIpConfigInterfacesTableInfoGroup,
                       vtssIpConfigInterfacesTableRowEditorInfoGroup,
                       vtssIpConfigInterfacesIpv4TableInfoGroup,
                       vtssIpConfigInterfacesIpv6TableInfoGroup,
                       vtssIpConfigRoutesIpv4TableInfoGroup,
                       vtssIpConfigRoutesIpv4RowEditorInfoGroup,
                       vtssIpConfigRoutesIpv6TableInfoGroup,
                       vtssIpConfigRoutesIpv6RowEditorInfoGroup,
                       vtssIpStatusGlobalsIpv4NeighborInfoGroup,
                       vtssIpStatusGlobalsIpv6NeighborInfoGroup,
                       vtssIpStatusGlobalsNotificationInfoGroup,
                       vtssIpStatusInterfacesLinkInfoGroup,
                       vtssIpStatusInterfacesIpv4InfoGroup,
                       vtssIpStatusInterfacesDhcpClientV4InfoGroup,
                       vtssIpStatusInterfacesIpv6InfoGroup,
                       vtssIpStatusRoutesIpv4InfoGroup,
                       vtssIpStatusRoutesIpv6InfoGroup,
                       vtssIpControlGlobalsInfoGroup,
                       vtssIpControlInterfaceDhcpClientInfoGroup,
                       vtssIpStatisticsGlobalsIpv4InfoGroup,
                       vtssIpStatisticsGlobalsIpv6InfoGroup,
                       vtssIpStatisticsInterfacesLinkInfoGroup,
                       vtssIpStatisticsInterfacesIpv4InfoGroup,
                       vtssIpStatisticsInterfacesIpv6InfoGroup,
                       vtssIpTrapInterfacesLinkAddInfoGroup,
                       vtssIpTrapInterfacesLinkModInfoGroup,
                       vtssIpTrapInterfacesLinkDelInfoGroup,
                       vtssIpTrapGlobalsMainInfoGroup }

    ::= { vtssIpMibCompliances 1 }

END
