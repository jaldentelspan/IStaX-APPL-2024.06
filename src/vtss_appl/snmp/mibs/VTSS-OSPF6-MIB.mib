-- *****************************************************************
-- OSPF6-MIB:  Microsemi ENT private MIB
-- ****************************************************************

VTSS-OSPF6-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    Counter64 FROM SNMPv2-SMI
    Integer32 FROM SNMPv2-SMI
    IpAddress FROM SNMPv2-SMI
    Unsigned32 FROM SNMPv2-SMI
    TruthValue FROM SNMPv2-TC
    VTSSInterfaceIndex FROM VTSS-TC
    VTSSRowEditorState FROM VTSS-TC
    VTSSUnsigned8 FROM VTSS-TC
    ;

vtssOspf6Mib MODULE-IDENTITY
    LAST-UPDATED "202402090000Z"
    ORGANIZATION
        "Microsemi Corporation"
    CONTACT-INFO
        "Application support: http://www.microchip.com/support"
    DESCRIPTION
        "This is a private version of the OSPF6 MIB."
    REVISION    "202402090000Z"
    DESCRIPTION
        "Add MtuIgnore"
    REVISION    "202008030000Z"
    DESCRIPTION
        "Initial version."
    ::= { vtssSwitchMgmt 156 }


VTSSOspf6AreaType ::= TEXTUAL-CONVENTION
    STATUS      current
    DESCRIPTION
        "The area type."
    SYNTAX      INTEGER { normalArea(0), stubArea(1),
                          totallyStubArea(2), areaUnknown(3) }

VTSSOspf6BorderRouterType ::= TEXTUAL-CONVENTION
    STATUS      current
    DESCRIPTION
        "The border router type of the OSPF6 route entry."
    SYNTAX      INTEGER { abr(0), asbrIntra(1), asbrInter(2),
                          abrAsbr(3), none(4) }

VTSSOspf6InterfaceState ::= TEXTUAL-CONVENTION
    STATUS      current
    DESCRIPTION
        "The state of the link."
    SYNTAX      INTEGER { down(1), loopback(2), waiting(3),
                          pointToPoint(4), drOther(5), bdr(6), dr(7),
                          unknown(8) }

VTSSOspf6LsdbType ::= TEXTUAL-CONVENTION
    STATUS      current
    DESCRIPTION
        "The type of the link state advertisement."
    SYNTAX      INTEGER { none(0), link(1), router(2), network(3),
                          interAreaPrefix(4), interAreaRouter(5),
                          nssa(6), intraAreaPrefix(7), external(8) }

VTSSOspf6NeighborState ::= TEXTUAL-CONVENTION
    STATUS      current
    DESCRIPTION
        "The state of the neighbor node."
    SYNTAX      INTEGER { dependupon(0), deleted(1), down(2),
                          attempt(3), init(4), twoWay(5), exstart(6),
                          exchange(7), loading(8), full(9),
                          unknown(10) }

VTSSOspf6RouteType ::= TEXTUAL-CONVENTION
    STATUS      current
    DESCRIPTION
        "The OSPF6 route type."
    SYNTAX      INTEGER { intraArea(0), interArea(1), borderRouter(2),
                          externalType1(3), externalType2(4),
                          unknown(5) }

vtssOspf6MibObjects OBJECT IDENTIFIER
    ::= { vtssOspf6Mib 1 }

vtssOspf6Capabilities OBJECT IDENTIFIER
    ::= { vtssOspf6MibObjects 1 }

vtssOspf6CapabilitiesMinInstanceId OBJECT-TYPE
    SYNTAX      Unsigned32
    MAX-ACCESS  read-only
    STATUS      current
    DESCRIPTION
        "OSPF6 minimum instance ID"
    ::= { vtssOspf6Capabilities 1 }

vtssOspf6CapabilitiesMaxInstanceId OBJECT-TYPE
    SYNTAX      Unsigned32
    MAX-ACCESS  read-only
    STATUS      current
    DESCRIPTION
        "OSPF6 maximum instance ID"
    ::= { vtssOspf6Capabilities 2 }

vtssOspf6CapabilitiesMinRouterId OBJECT-TYPE
    SYNTAX      Unsigned32
    MAX-ACCESS  read-only
    STATUS      current
    DESCRIPTION
        "The minimum value of OSPF6 router ID"
    ::= { vtssOspf6Capabilities 3 }

vtssOspf6CapabilitiesMaxRouterId OBJECT-TYPE
    SYNTAX      Unsigned32
    MAX-ACCESS  read-only
    STATUS      current
    DESCRIPTION
        "The maximum value of OSPF6 router ID"
    ::= { vtssOspf6Capabilities 4 }

vtssOspf6CapabilitiesMinPriority OBJECT-TYPE
    SYNTAX      Unsigned32
    MAX-ACCESS  read-only
    STATUS      current
    DESCRIPTION
        "The minimum value of OSPF6 priority"
    ::= { vtssOspf6Capabilities 5 }

vtssOspf6CapabilitiesMaxPriority OBJECT-TYPE
    SYNTAX      Unsigned32
    MAX-ACCESS  read-only
    STATUS      current
    DESCRIPTION
        "The maximum value of OSPF6 priority"
    ::= { vtssOspf6Capabilities 6 }

vtssOspf6CapabilitiesMinGeneralCost OBJECT-TYPE
    SYNTAX      Unsigned32
    MAX-ACCESS  read-only
    STATUS      current
    DESCRIPTION
        "The minimum value of OSPF6 interface cost"
    ::= { vtssOspf6Capabilities 7 }

vtssOspf6CapabilitiesMaxGeneralCost OBJECT-TYPE
    SYNTAX      Unsigned32
    MAX-ACCESS  read-only
    STATUS      current
    DESCRIPTION
        "The maximum value of OSPF6 interface cost"
    ::= { vtssOspf6Capabilities 8 }

vtssOspf6CapabilitiesMinInterfaceCost OBJECT-TYPE
    SYNTAX      Unsigned32
    MAX-ACCESS  read-only
    STATUS      current
    DESCRIPTION
        "The minimum value of OSPF6 interface cost"
    ::= { vtssOspf6Capabilities 9 }

vtssOspf6CapabilitiesMaxInterfaceCost OBJECT-TYPE
    SYNTAX      Unsigned32
    MAX-ACCESS  read-only
    STATUS      current
    DESCRIPTION
        "The maximum value of OSPF6 interface cost"
    ::= { vtssOspf6Capabilities 10 }

vtssOspf6CapabilitiesMinHelloInterval OBJECT-TYPE
    SYNTAX      Unsigned32
    MAX-ACCESS  read-only
    STATUS      current
    DESCRIPTION
        "The minimum value of OSPF6 hello interval"
    ::= { vtssOspf6Capabilities 11 }

vtssOspf6CapabilitiesMaxHelloInterval OBJECT-TYPE
    SYNTAX      Unsigned32
    MAX-ACCESS  read-only
    STATUS      current
    DESCRIPTION
        "The maximum value of OSPF6 hello interval"
    ::= { vtssOspf6Capabilities 12 }

vtssOspf6CapabilitiesMinRetransmitInterval OBJECT-TYPE
    SYNTAX      Unsigned32
    MAX-ACCESS  read-only
    STATUS      current
    DESCRIPTION
        "The minimum value of OSPF6 retransmit interval"
    ::= { vtssOspf6Capabilities 13 }

vtssOspf6CapabilitiesMaxRetransmitInterval OBJECT-TYPE
    SYNTAX      Unsigned32
    MAX-ACCESS  read-only
    STATUS      current
    DESCRIPTION
        "The maximum value of OSPF6 retransmit interval"
    ::= { vtssOspf6Capabilities 14 }

vtssOspf6CapabilitiesMinDeadInterval OBJECT-TYPE
    SYNTAX      Unsigned32
    MAX-ACCESS  read-only
    STATUS      current
    DESCRIPTION
        "The minimum value of OSPF6 dead interval"
    ::= { vtssOspf6Capabilities 15 }

vtssOspf6CapabilitiesMaxDeadInterval OBJECT-TYPE
    SYNTAX      Unsigned32
    MAX-ACCESS  read-only
    STATUS      current
    DESCRIPTION
        "The maximum value of OSPF6 dead interval"
    ::= { vtssOspf6Capabilities 16 }

vtssOspf6CapabilitiesIsRipngRedistributedSupported OBJECT-TYPE
    SYNTAX      TruthValue
    MAX-ACCESS  read-only
    STATUS      current
    DESCRIPTION
        "Indicate if RIPNG redistributed is supported or not"
    ::= { vtssOspf6Capabilities 17 }

vtssOspf6CapabilitiesMinAdminDistance OBJECT-TYPE
    SYNTAX      VTSSUnsigned8
    MAX-ACCESS  read-only
    STATUS      current
    DESCRIPTION
        "The minimum value of OSPF6 administrative distance value"
    ::= { vtssOspf6Capabilities 18 }

vtssOspf6CapabilitiesMaxAdminDistance OBJECT-TYPE
    SYNTAX      VTSSUnsigned8
    MAX-ACCESS  read-only
    STATUS      current
    DESCRIPTION
        "The maximum value of OSPF6 administrative distance value"
    ::= { vtssOspf6Capabilities 19 }

vtssOspf6Config OBJECT IDENTIFIER
    ::= { vtssOspf6MibObjects 2 }

vtssOspf6ConfigProcessTable OBJECT-TYPE
    SYNTAX      SEQUENCE OF VTSSOspf6ConfigProcessEntry
    MAX-ACCESS  not-accessible
    STATUS      current
    DESCRIPTION
        "This is OSPF6 process configuration table. It is used to enable or
         disable the routing process on a specific process ID."
    ::= { vtssOspf6Config 1 }

vtssOspf6ConfigProcessEntry OBJECT-TYPE
    SYNTAX      VTSSOspf6ConfigProcessEntry
    MAX-ACCESS  not-accessible
    STATUS      current
    DESCRIPTION
        "Each entry in this table represents OSPF6 routing process."
    INDEX       { vtssOspf6ConfigProcessInstanceId }
    ::= { vtssOspf6ConfigProcessTable 1 }

VTSSOspf6ConfigProcessEntry ::= SEQUENCE {
    vtssOspf6ConfigProcessInstanceId  Integer32,
    vtssOspf6ConfigProcessAction      VTSSRowEditorState
}

vtssOspf6ConfigProcessInstanceId OBJECT-TYPE
    SYNTAX      Integer32 (1..1)
    MAX-ACCESS  accessible-for-notify
    STATUS      current
    DESCRIPTION
        "The OSPF6 process instance ID."
    ::= { vtssOspf6ConfigProcessEntry 1 }

vtssOspf6ConfigProcessAction OBJECT-TYPE
    SYNTAX      VTSSRowEditorState
    MAX-ACCESS  read-write
    STATUS      current
    DESCRIPTION
        "Action"
    ::= { vtssOspf6ConfigProcessEntry 100 }

vtssOspf6ConfigProcessTableRowEditor OBJECT IDENTIFIER
    ::= { vtssOspf6Config 2 }

vtssOspf6ConfigProcessTableRowEditorInstanceId OBJECT-TYPE
    SYNTAX      Integer32 (1..1)
    MAX-ACCESS  read-write
    STATUS      current
    DESCRIPTION
        "The OSPF6 process instance ID."
    ::= { vtssOspf6ConfigProcessTableRowEditor 1 }

vtssOspf6ConfigProcessTableRowEditorAction OBJECT-TYPE
    SYNTAX      VTSSRowEditorState
    MAX-ACCESS  read-write
    STATUS      current
    DESCRIPTION
        "Action"
    ::= { vtssOspf6ConfigProcessTableRowEditor 100 }

vtssOspf6ConfigRouterTable OBJECT-TYPE
    SYNTAX      SEQUENCE OF VTSSOspf6ConfigRouterEntry
    MAX-ACCESS  not-accessible
    STATUS      current
    DESCRIPTION
        "This is OSPF6 router configuration table. It is a general group to
         configure the OSPF6 common router parameters."
    ::= { vtssOspf6Config 3 }

vtssOspf6ConfigRouterEntry OBJECT-TYPE
    SYNTAX      VTSSOspf6ConfigRouterEntry
    MAX-ACCESS  not-accessible
    STATUS      current
    DESCRIPTION
        "Each entry in this table represents the OSPF6 router interface
         configuration."
    INDEX       { vtssOspf6ConfigRouterInstanceId }
    ::= { vtssOspf6ConfigRouterTable 1 }

VTSSOspf6ConfigRouterEntry ::= SEQUENCE {
    vtssOspf6ConfigRouterInstanceId             Integer32,
    vtssOspf6ConfigRouterIsSpecificRouterId     TruthValue,
    vtssOspf6ConfigRouterRouterId               IpAddress,
    vtssOspf6ConfigRouterConnectedRedistEnable  VTSSUnsigned8,
    vtssOspf6ConfigRouterStaticRedistEnable     VTSSUnsigned8,
    vtssOspf6ConfigRouterAdminDistance          VTSSUnsigned8
}

vtssOspf6ConfigRouterInstanceId OBJECT-TYPE
    SYNTAX      Integer32 (1..1)
    MAX-ACCESS  accessible-for-notify
    STATUS      current
    DESCRIPTION
        "The OSPF6 process instance ID."
    ::= { vtssOspf6ConfigRouterEntry 1 }

vtssOspf6ConfigRouterIsSpecificRouterId OBJECT-TYPE
    SYNTAX      TruthValue
    MAX-ACCESS  read-write
    STATUS      current
    DESCRIPTION
        "Indicate the 'RouterId' argument is a specific configured value or not."
    ::= { vtssOspf6ConfigRouterEntry 2 }

vtssOspf6ConfigRouterRouterId OBJECT-TYPE
    SYNTAX      IpAddress
    MAX-ACCESS  read-write
    STATUS      current
    DESCRIPTION
        "The OSPF6 router ID"
    ::= { vtssOspf6ConfigRouterEntry 3 }

vtssOspf6ConfigRouterConnectedRedistEnable OBJECT-TYPE
    SYNTAX      VTSSUnsigned8
    MAX-ACCESS  read-write
    STATUS      current
    DESCRIPTION
        "The OSPF redistribute enabled for connected route or not."
    ::= { vtssOspf6ConfigRouterEntry 4 }

vtssOspf6ConfigRouterStaticRedistEnable OBJECT-TYPE
    SYNTAX      VTSSUnsigned8
    MAX-ACCESS  read-write
    STATUS      current
    DESCRIPTION
        "The OSPF redistributeenabled for the static routes or not."
    ::= { vtssOspf6ConfigRouterEntry 5 }

vtssOspf6ConfigRouterAdminDistance OBJECT-TYPE
    SYNTAX      VTSSUnsigned8 (1..255)
    MAX-ACCESS  read-write
    STATUS      current
    DESCRIPTION
        "The OSPF6 administrative distance."
    ::= { vtssOspf6ConfigRouterEntry 6 }

vtssOspf6ConfigRouterInterfaceTable OBJECT-TYPE
    SYNTAX      SEQUENCE OF VTSSOspf6ConfigRouterInterfaceEntry
    MAX-ACCESS  not-accessible
    STATUS      current
    DESCRIPTION
        "This is OSPF6 router interface configuration table."
    ::= { vtssOspf6Config 4 }

vtssOspf6ConfigRouterInterfaceEntry OBJECT-TYPE
    SYNTAX      VTSSOspf6ConfigRouterInterfaceEntry
    MAX-ACCESS  not-accessible
    STATUS      current
    DESCRIPTION
        "Each router interface has a set of parameters."
    INDEX       { vtssOspf6ConfigRouterInterfaceInstanceId,
                  vtssOspf6ConfigRouterInterfaceIfIndex }
    ::= { vtssOspf6ConfigRouterInterfaceTable 1 }

VTSSOspf6ConfigRouterInterfaceEntry ::= SEQUENCE {
    vtssOspf6ConfigRouterInterfaceInstanceId        Integer32,
    vtssOspf6ConfigRouterInterfaceIfIndex           VTSSInterfaceIndex,
    vtssOspf6ConfigRouterInterfaceIsSpecificAreaId  TruthValue,
    vtssOspf6ConfigRouterInterfaceAreaId            IpAddress
}

vtssOspf6ConfigRouterInterfaceInstanceId OBJECT-TYPE
    SYNTAX      Integer32 (1..1)
    MAX-ACCESS  accessible-for-notify
    STATUS      current
    DESCRIPTION
        "The OSPF6 process instance ID."
    ::= { vtssOspf6ConfigRouterInterfaceEntry 1 }

vtssOspf6ConfigRouterInterfaceIfIndex OBJECT-TYPE
    SYNTAX      VTSSInterfaceIndex
    MAX-ACCESS  accessible-for-notify
    STATUS      current
    DESCRIPTION
        "Logical interface number."
    ::= { vtssOspf6ConfigRouterInterfaceEntry 2 }

vtssOspf6ConfigRouterInterfaceIsSpecificAreaId OBJECT-TYPE
    SYNTAX      TruthValue
    MAX-ACCESS  read-write
    STATUS      current
    DESCRIPTION
        "Indicates whether the AreaId is valid or not."
    ::= { vtssOspf6ConfigRouterInterfaceEntry 3 }

vtssOspf6ConfigRouterInterfaceAreaId OBJECT-TYPE
    SYNTAX      IpAddress
    MAX-ACCESS  read-write
    STATUS      current
    DESCRIPTION
        "The OSPF6 interface Area ID.Only valid if 'is_specific_id' is true"
    ::= { vtssOspf6ConfigRouterInterfaceEntry 4 }

vtssOspf6ConfigAreaRangeTable OBJECT-TYPE
    SYNTAX      SEQUENCE OF VTSSOspf6ConfigAreaRangeEntry
    MAX-ACCESS  not-accessible
    STATUS      current
    DESCRIPTION
        "This is OSPF6 area range configuration table. It is used to summarize
         the intra area paths from a specific address range in one
         summary-LSA(Type-0x2003) and advertised to other areas or configure the
         address range status as 'DoNotAdvertise' which the
         summary-LSA(Type-0x2003) is suppressed.
         
         The area range configuration is used for Area Border Routers (ABRs) and
         only router-LSAs(Type-0x2001) and network-LSAs (Type-0x2002) can be
         summarized. The AS-external-LSAs(Type-0x4005) cannot be summarized
         because the scope is OSPF6 autonomous system (AS). The
         AS-external-LSAs(Type-0x4007) cannot be summarized because the feature
         is not supported yet."
    ::= { vtssOspf6Config 5 }

vtssOspf6ConfigAreaRangeEntry OBJECT-TYPE
    SYNTAX      VTSSOspf6ConfigAreaRangeEntry
    MAX-ACCESS  not-accessible
    STATUS      current
    DESCRIPTION
        "Each entry in this table represents OSPF6 area range configuration. The
         overlap configuration of address range is not allowed in order to avoid
         the conflict."
    INDEX       { vtssOspf6ConfigAreaRangeInstanceId,
                  vtssOspf6ConfigAreaRangeAreaId,
                  vtssOspf6ConfigAreaRangeNetwork,
                  vtssOspf6ConfigAreaRangeIpSubnetMaskLength }
    ::= { vtssOspf6ConfigAreaRangeTable 1 }

VTSSOspf6ConfigAreaRangeEntry ::= SEQUENCE {
    vtssOspf6ConfigAreaRangeInstanceId          Integer32,
    vtssOspf6ConfigAreaRangeAreaId              IpAddress,
    vtssOspf6ConfigAreaRangeNetwork             InetAddressIPv6,
    vtssOspf6ConfigAreaRangeIpSubnetMaskLength  Integer32,
    vtssOspf6ConfigAreaRangeAdvertised          TruthValue,
    vtssOspf6ConfigAreaRangeIsSpecificCost      TruthValue,
    vtssOspf6ConfigAreaRangeCost                Unsigned32,
    vtssOspf6ConfigAreaRangeAction              VTSSRowEditorState
}

vtssOspf6ConfigAreaRangeInstanceId OBJECT-TYPE
    SYNTAX      Integer32 (1..1)
    MAX-ACCESS  accessible-for-notify
    STATUS      current
    DESCRIPTION
        "The OSPF6 process instance ID."
    ::= { vtssOspf6ConfigAreaRangeEntry 1 }

vtssOspf6ConfigAreaRangeAreaId OBJECT-TYPE
    SYNTAX      IpAddress
    MAX-ACCESS  accessible-for-notify
    STATUS      current
    DESCRIPTION
        "The OSPF6 area ID."
    ::= { vtssOspf6ConfigAreaRangeEntry 2 }

vtssOspf6ConfigAreaRangeNetwork OBJECT-TYPE
    SYNTAX      InetAddressIPv6
    MAX-ACCESS  accessible-for-notify
    STATUS      current
    DESCRIPTION
        "IPv6 network address."
    ::= { vtssOspf6ConfigAreaRangeEntry 3 }

vtssOspf6ConfigAreaRangeIpSubnetMaskLength OBJECT-TYPE
    SYNTAX      Integer32 (0..128)
    MAX-ACCESS  accessible-for-notify
    STATUS      current
    DESCRIPTION
        "IPv6 network mask length."
    ::= { vtssOspf6ConfigAreaRangeEntry 4 }

vtssOspf6ConfigAreaRangeAdvertised OBJECT-TYPE
    SYNTAX      TruthValue
    MAX-ACCESS  read-write
    STATUS      current
    DESCRIPTION
        "When the value is true, it summarizes intra area paths from the address
         range in one Inter-Area Prefix LSA(Type-0x2003) and advertised to other
         areas.
         
         Otherwise, the intra area paths from the address range are not
         advertised to other areas."
    ::= { vtssOspf6ConfigAreaRangeEntry 5 }

vtssOspf6ConfigAreaRangeIsSpecificCost OBJECT-TYPE
    SYNTAX      TruthValue
    MAX-ACCESS  read-write
    STATUS      current
    DESCRIPTION
        "Indicate the 'cost' argument is a specific configured value or not."
    ::= { vtssOspf6ConfigAreaRangeEntry 6 }

vtssOspf6ConfigAreaRangeCost OBJECT-TYPE
    SYNTAX      Unsigned32 (0..16777215)
    MAX-ACCESS  read-write
    STATUS      current
    DESCRIPTION
        "User specified cost (or metric) for this summary route. The field is
         significant only when 'IsSpecificCost' is TRUE."
    ::= { vtssOspf6ConfigAreaRangeEntry 7 }

vtssOspf6ConfigAreaRangeAction OBJECT-TYPE
    SYNTAX      VTSSRowEditorState
    MAX-ACCESS  read-write
    STATUS      current
    DESCRIPTION
        "Action"
    ::= { vtssOspf6ConfigAreaRangeEntry 100 }

vtssOspf6ConfigAreaRangeTableRowEditor OBJECT IDENTIFIER
    ::= { vtssOspf6Config 6 }

vtssOspf6ConfigAreaRangeTableRowEditorInstanceId OBJECT-TYPE
    SYNTAX      Integer32 (1..1)
    MAX-ACCESS  read-write
    STATUS      current
    DESCRIPTION
        "The OSPF6 process instance ID."
    ::= { vtssOspf6ConfigAreaRangeTableRowEditor 1 }

vtssOspf6ConfigAreaRangeTableRowEditorAreaId OBJECT-TYPE
    SYNTAX      IpAddress
    MAX-ACCESS  read-write
    STATUS      current
    DESCRIPTION
        "The OSPF6 area ID."
    ::= { vtssOspf6ConfigAreaRangeTableRowEditor 2 }

vtssOspf6ConfigAreaRangeTableRowEditorNetwork OBJECT-TYPE
    SYNTAX      InetAddressIPv6
    MAX-ACCESS  read-write
    STATUS      current
    DESCRIPTION
        "IPv6 network address."
    ::= { vtssOspf6ConfigAreaRangeTableRowEditor 3 }

vtssOspf6ConfigAreaRangeTableRowEditorIpSubnetMaskLength OBJECT-TYPE
    SYNTAX      Integer32 (0..128)
    MAX-ACCESS  read-write
    STATUS      current
    DESCRIPTION
        "IPv6 network mask length."
    ::= { vtssOspf6ConfigAreaRangeTableRowEditor 4 }

vtssOspf6ConfigAreaRangeTableRowEditorAdvertised OBJECT-TYPE
    SYNTAX      TruthValue
    MAX-ACCESS  read-write
    STATUS      current
    DESCRIPTION
        "When the value is true, it summarizes intra area paths from the address
         range in one Inter-Area Prefix LSA(Type-0x2003) and advertised to other
         areas.
         
         Otherwise, the intra area paths from the address range are not
         advertised to other areas."
    ::= { vtssOspf6ConfigAreaRangeTableRowEditor 5 }

vtssOspf6ConfigAreaRangeTableRowEditorIsSpecificCost OBJECT-TYPE
    SYNTAX      TruthValue
    MAX-ACCESS  read-write
    STATUS      current
    DESCRIPTION
        "Indicate the 'cost' argument is a specific configured value or not."
    ::= { vtssOspf6ConfigAreaRangeTableRowEditor 6 }

vtssOspf6ConfigAreaRangeTableRowEditorCost OBJECT-TYPE
    SYNTAX      Unsigned32 (0..16777215)
    MAX-ACCESS  read-write
    STATUS      current
    DESCRIPTION
        "User specified cost (or metric) for this summary route. The field is
         significant only when 'IsSpecificCost' is TRUE."
    ::= { vtssOspf6ConfigAreaRangeTableRowEditor 7 }

vtssOspf6ConfigAreaRangeTableRowEditorAction OBJECT-TYPE
    SYNTAX      VTSSRowEditorState
    MAX-ACCESS  read-write
    STATUS      current
    DESCRIPTION
        "Action"
    ::= { vtssOspf6ConfigAreaRangeTableRowEditor 100 }

vtssOspf6ConfigStubAreaTable OBJECT-TYPE
    SYNTAX      SEQUENCE OF VTSSOspf6ConfigStubAreaEntry
    MAX-ACCESS  not-accessible
    STATUS      current
    DESCRIPTION
        "This is OSPF6 stub area configuration table. The configuration is used
         to reduce the link-state database size and therefore the memory and CPU
         requirement by forbidding some LSAs."
    ::= { vtssOspf6Config 7 }

vtssOspf6ConfigStubAreaEntry OBJECT-TYPE
    SYNTAX      VTSSOspf6ConfigStubAreaEntry
    MAX-ACCESS  not-accessible
    STATUS      current
    DESCRIPTION
        "Each entry in this table represents OSPF6 stub area configuration."
    INDEX       { vtssOspf6ConfigStubAreaInstanceId,
                  vtssOspf6ConfigStubAreaAreaId }
    ::= { vtssOspf6ConfigStubAreaTable 1 }

VTSSOspf6ConfigStubAreaEntry ::= SEQUENCE {
    vtssOspf6ConfigStubAreaInstanceId  Integer32,
    vtssOspf6ConfigStubAreaAreaId      IpAddress,
    vtssOspf6ConfigStubAreaNoSummary   TruthValue,
    vtssOspf6ConfigStubAreaAction      VTSSRowEditorState
}

vtssOspf6ConfigStubAreaInstanceId OBJECT-TYPE
    SYNTAX      Integer32 (1..1)
    MAX-ACCESS  accessible-for-notify
    STATUS      current
    DESCRIPTION
        "The OSPF6 process instance ID."
    ::= { vtssOspf6ConfigStubAreaEntry 1 }

vtssOspf6ConfigStubAreaAreaId OBJECT-TYPE
    SYNTAX      IpAddress
    MAX-ACCESS  accessible-for-notify
    STATUS      current
    DESCRIPTION
        "The OSPF6 area ID."
    ::= { vtssOspf6ConfigStubAreaEntry 2 }

vtssOspf6ConfigStubAreaNoSummary OBJECT-TYPE
    SYNTAX      TruthValue
    MAX-ACCESS  read-write
    STATUS      current
    DESCRIPTION
        "The value is true to configure the inter-area routes do not inject into
         this stub area."
    ::= { vtssOspf6ConfigStubAreaEntry 3 }

vtssOspf6ConfigStubAreaAction OBJECT-TYPE
    SYNTAX      VTSSRowEditorState
    MAX-ACCESS  read-write
    STATUS      current
    DESCRIPTION
        "Action"
    ::= { vtssOspf6ConfigStubAreaEntry 100 }

vtssOspf6ConfigStubAreaTableRowEditor OBJECT IDENTIFIER
    ::= { vtssOspf6Config 8 }

vtssOspf6ConfigStubAreaTableRowEditorInstanceId OBJECT-TYPE
    SYNTAX      Integer32 (1..1)
    MAX-ACCESS  read-write
    STATUS      current
    DESCRIPTION
        "The OSPF6 process instance ID."
    ::= { vtssOspf6ConfigStubAreaTableRowEditor 1 }

vtssOspf6ConfigStubAreaTableRowEditorAreaId OBJECT-TYPE
    SYNTAX      IpAddress
    MAX-ACCESS  read-write
    STATUS      current
    DESCRIPTION
        "The OSPF6 area ID."
    ::= { vtssOspf6ConfigStubAreaTableRowEditor 2 }

vtssOspf6ConfigStubAreaTableRowEditorNoSummary OBJECT-TYPE
    SYNTAX      TruthValue
    MAX-ACCESS  read-write
    STATUS      current
    DESCRIPTION
        "The value is true to configure the inter-area routes do not inject into
         this stub area."
    ::= { vtssOspf6ConfigStubAreaTableRowEditor 3 }

vtssOspf6ConfigStubAreaTableRowEditorAction OBJECT-TYPE
    SYNTAX      VTSSRowEditorState
    MAX-ACCESS  read-write
    STATUS      current
    DESCRIPTION
        "Action"
    ::= { vtssOspf6ConfigStubAreaTableRowEditor 100 }

vtssOspf6ConfigInterfaceTable OBJECT-TYPE
    SYNTAX      SEQUENCE OF VTSSOspf6ConfigInterfaceEntry
    MAX-ACCESS  not-accessible
    STATUS      current
    DESCRIPTION
        "This is interface configuration parameter table."
    ::= { vtssOspf6Config 9 }

vtssOspf6ConfigInterfaceEntry OBJECT-TYPE
    SYNTAX      VTSSOspf6ConfigInterfaceEntry
    MAX-ACCESS  not-accessible
    STATUS      current
    DESCRIPTION
        "Each interface has a set of parameters."
    INDEX       { vtssOspf6ConfigInterfaceIfIndex }
    ::= { vtssOspf6ConfigInterfaceTable 1 }

VTSSOspf6ConfigInterfaceEntry ::= SEQUENCE {
    vtssOspf6ConfigInterfaceIfIndex             VTSSInterfaceIndex,
    vtssOspf6ConfigInterfacePriority            Unsigned32,
    vtssOspf6ConfigInterfaceIsSpecificCost      TruthValue,
    vtssOspf6ConfigInterfaceCost                Unsigned32,
    vtssOspf6ConfigInterfaceDeadInterval        Unsigned32,
    vtssOspf6ConfigInterfaceHelloInterval       Unsigned32,
    vtssOspf6ConfigInterfaceRetransmitInterval  Unsigned32,
    vtssOspf6ConfigInterfaceIsPassiveInterface  TruthValue,
    vtssOspf6ConfigInterfaceTransmitDelay       Unsigned32,
    vtssOspf6ConfigInterfaceMtuIgnore           TruthValue
}

vtssOspf6ConfigInterfaceIfIndex OBJECT-TYPE
    SYNTAX      VTSSInterfaceIndex
    MAX-ACCESS  accessible-for-notify
    STATUS      current
    DESCRIPTION
        "Logical interface number."
    ::= { vtssOspf6ConfigInterfaceEntry 1 }

vtssOspf6ConfigInterfacePriority OBJECT-TYPE
    SYNTAX      Unsigned32 (0..255)
    MAX-ACCESS  read-write
    STATUS      current
    DESCRIPTION
        "User specified router priority for the interface."
    ::= { vtssOspf6ConfigInterfaceEntry 2 }

vtssOspf6ConfigInterfaceIsSpecificCost OBJECT-TYPE
    SYNTAX      TruthValue
    MAX-ACCESS  read-write
    STATUS      current
    DESCRIPTION
        "Indicate the 'cost' argument is a specific configured value or not."
    ::= { vtssOspf6ConfigInterfaceEntry 3 }

vtssOspf6ConfigInterfaceCost OBJECT-TYPE
    SYNTAX      Unsigned32 (1..65535)
    MAX-ACCESS  read-write
    STATUS      current
    DESCRIPTION
        "User specified cost for this interface. It's link state metric for the
         interface. The field is significant only when 'IsSpecificCost' is TRUE."
    ::= { vtssOspf6ConfigInterfaceEntry 4 }

vtssOspf6ConfigInterfaceDeadInterval OBJECT-TYPE
    SYNTAX      Unsigned32 (1..65535)
    MAX-ACCESS  read-write
    STATUS      current
    DESCRIPTION
        "The time interval (in seconds) between hello packets."
    ::= { vtssOspf6ConfigInterfaceEntry 5 }

vtssOspf6ConfigInterfaceHelloInterval OBJECT-TYPE
    SYNTAX      Unsigned32 (1..65535)
    MAX-ACCESS  read-write
    STATUS      current
    DESCRIPTION
        "How many Hello packets will be sent per second."
    ::= { vtssOspf6ConfigInterfaceEntry 6 }

vtssOspf6ConfigInterfaceRetransmitInterval OBJECT-TYPE
    SYNTAX      Unsigned32 (3..65535)
    MAX-ACCESS  read-write
    STATUS      current
    DESCRIPTION
        "The time interval (in seconds) between link-state advertisement(LSA)
         retransmissions for adjacencies."
    ::= { vtssOspf6ConfigInterfaceEntry 7 }

vtssOspf6ConfigInterfaceIsPassiveInterface OBJECT-TYPE
    SYNTAX      TruthValue
    MAX-ACCESS  read-write
    STATUS      current
    DESCRIPTION
        "Indicates whether the interface is passive or not"
    ::= { vtssOspf6ConfigInterfaceEntry 8 }

vtssOspf6ConfigInterfaceTransmitDelay OBJECT-TYPE
    SYNTAX      Unsigned32 (1..3600)
    MAX-ACCESS  read-write
    STATUS      current
    DESCRIPTION
        "The time (in seconds) taken to transmit a packet."
    ::= { vtssOspf6ConfigInterfaceEntry 9 }

vtssOspf6ConfigInterfaceMtuIgnore OBJECT-TYPE
    SYNTAX      TruthValue
    MAX-ACCESS  read-write
    STATUS      current
    DESCRIPTION
        "When false (default), the interface MTU of received OSPFv3 database
         description (DBD) packets will be checked against our own MTU, and if
         the remote MTU differs from our own, the DBD will be ignored. When
         true, the interface MTU of the received OSPFv3 DBD packets will be
         ignored."
    ::= { vtssOspf6ConfigInterfaceEntry 10 }

vtssOspf6ConfigInterface OBJECT IDENTIFIER
    ::= { vtssOspf6Config 100 }

vtssOspf6Status OBJECT IDENTIFIER
    ::= { vtssOspf6MibObjects 3 }

vtssOspf6StatusRouterTable OBJECT-TYPE
    SYNTAX      SEQUENCE OF VTSSOspf6StatusRouterEntry
    MAX-ACCESS  not-accessible
    STATUS      current
    DESCRIPTION
        "This is OSPF6 router status table. It is used to provide the OSPF6
         router status information."
    ::= { vtssOspf6Status 1 }

vtssOspf6StatusRouterEntry OBJECT-TYPE
    SYNTAX      VTSSOspf6StatusRouterEntry
    MAX-ACCESS  not-accessible
    STATUS      current
    DESCRIPTION
        "Each entry in this table represents OSPF6 router status information."
    INDEX       { vtssOspf6StatusRouterInstanceId }
    ::= { vtssOspf6StatusRouterTable 1 }

VTSSOspf6StatusRouterEntry ::= SEQUENCE {
    vtssOspf6StatusRouterInstanceId         Integer32,
    vtssOspf6StatusRouterRouterId           IpAddress,
    vtssOspf6StatusRouterSpfDelay           Unsigned32,
    vtssOspf6StatusRouterSpfHoldTime        Unsigned32,
    vtssOspf6StatusRouterSpfMaxWaitTime     Unsigned32,
    vtssOspf6StatusRouterLastExcutedSpfTs   Counter64,
    vtssOspf6StatusRouterAttachedAreaCount  Unsigned32
}

vtssOspf6StatusRouterInstanceId OBJECT-TYPE
    SYNTAX      Integer32 (1..1)
    MAX-ACCESS  accessible-for-notify
    STATUS      current
    DESCRIPTION
        "The OSPF6 process instance ID."
    ::= { vtssOspf6StatusRouterEntry 1 }

vtssOspf6StatusRouterRouterId OBJECT-TYPE
    SYNTAX      IpAddress
    MAX-ACCESS  read-only
    STATUS      current
    DESCRIPTION
        "OSPF6 router ID"
    ::= { vtssOspf6StatusRouterEntry 2 }

vtssOspf6StatusRouterSpfDelay OBJECT-TYPE
    SYNTAX      Unsigned32
    MAX-ACCESS  read-only
    STATUS      current
    DESCRIPTION
        "Delay time (in seconds)of SPF calculations."
    ::= { vtssOspf6StatusRouterEntry 3 }

vtssOspf6StatusRouterSpfHoldTime OBJECT-TYPE
    SYNTAX      Unsigned32
    MAX-ACCESS  read-only
    STATUS      current
    DESCRIPTION
        "Minimum hold time (in milliseconds) between consecutive SPF
         calculations."
    ::= { vtssOspf6StatusRouterEntry 4 }

vtssOspf6StatusRouterSpfMaxWaitTime OBJECT-TYPE
    SYNTAX      Unsigned32
    MAX-ACCESS  read-only
    STATUS      current
    DESCRIPTION
        "Maximum wait time (in milliseconds) between consecutive SPF
         calculations."
    ::= { vtssOspf6StatusRouterEntry 5 }

vtssOspf6StatusRouterLastExcutedSpfTs OBJECT-TYPE
    SYNTAX      Counter64
    MAX-ACCESS  read-only
    STATUS      current
    DESCRIPTION
        "Time (in milliseconds) that has passed between the start of the SPF
         algorithm execution and the current time."
    ::= { vtssOspf6StatusRouterEntry 6 }

vtssOspf6StatusRouterAttachedAreaCount OBJECT-TYPE
    SYNTAX      Unsigned32
    MAX-ACCESS  read-only
    STATUS      current
    DESCRIPTION
        "Number of areas attached for the router."
    ::= { vtssOspf6StatusRouterEntry 7 }

vtssOspf6StatusRouteAreaTable OBJECT-TYPE
    SYNTAX      SEQUENCE OF VTSSOspf6StatusRouteAreaEntry
    MAX-ACCESS  not-accessible
    STATUS      current
    DESCRIPTION
        "This is OSPF6 network area status table. It is used to provide the
         OSPF6 network area status information."
    ::= { vtssOspf6Status 2 }

vtssOspf6StatusRouteAreaEntry OBJECT-TYPE
    SYNTAX      VTSSOspf6StatusRouteAreaEntry
    MAX-ACCESS  not-accessible
    STATUS      current
    DESCRIPTION
        "Each entry in this table represents OSPF6 network area status
         information."
    INDEX       { vtssOspf6StatusRouteAreaInstanceId,
                  vtssOspf6StatusRouteAreaAreaId }
    ::= { vtssOspf6StatusRouteAreaTable 1 }

VTSSOspf6StatusRouteAreaEntry ::= SEQUENCE {
    vtssOspf6StatusRouteAreaInstanceId         Integer32,
    vtssOspf6StatusRouteAreaAreaId             IpAddress,
    vtssOspf6StatusRouteAreaIsBackbone         TruthValue,
    vtssOspf6StatusRouteAreaAreaType           VTSSOspf6AreaType,
    vtssOspf6StatusRouteAreaAttachedIntfCount  Unsigned32,
    vtssOspf6StatusRouteAreaSpfExecutedCount   Unsigned32,
    vtssOspf6StatusRouteAreaLsaCount           Unsigned32
}

vtssOspf6StatusRouteAreaInstanceId OBJECT-TYPE
    SYNTAX      Integer32 (1..1)
    MAX-ACCESS  accessible-for-notify
    STATUS      current
    DESCRIPTION
        "The OSPF6 process instance ID."
    ::= { vtssOspf6StatusRouteAreaEntry 1 }

vtssOspf6StatusRouteAreaAreaId OBJECT-TYPE
    SYNTAX      IpAddress
    MAX-ACCESS  accessible-for-notify
    STATUS      current
    DESCRIPTION
        "The OSPF6 area ID."
    ::= { vtssOspf6StatusRouteAreaEntry 2 }

vtssOspf6StatusRouteAreaIsBackbone OBJECT-TYPE
    SYNTAX      TruthValue
    MAX-ACCESS  read-only
    STATUS      current
    DESCRIPTION
        "Indicate if it's backbone area or not."
    ::= { vtssOspf6StatusRouteAreaEntry 3 }

vtssOspf6StatusRouteAreaAreaType OBJECT-TYPE
    SYNTAX      VTSSOspf6AreaType
    MAX-ACCESS  read-only
    STATUS      current
    DESCRIPTION
        "The area type."
    ::= { vtssOspf6StatusRouteAreaEntry 4 }

vtssOspf6StatusRouteAreaAttachedIntfCount OBJECT-TYPE
    SYNTAX      Unsigned32
    MAX-ACCESS  read-only
    STATUS      current
    DESCRIPTION
        "Number of active interfaces attached in the area."
    ::= { vtssOspf6StatusRouteAreaEntry 5 }

vtssOspf6StatusRouteAreaSpfExecutedCount OBJECT-TYPE
    SYNTAX      Unsigned32
    MAX-ACCESS  read-only
    STATUS      current
    DESCRIPTION
        "Number of times SPF algorithm has been executed for the particular
         area."
    ::= { vtssOspf6StatusRouteAreaEntry 6 }

vtssOspf6StatusRouteAreaLsaCount OBJECT-TYPE
    SYNTAX      Unsigned32
    MAX-ACCESS  read-only
    STATUS      current
    DESCRIPTION
        "Number of the total LSAs for the particular area."
    ::= { vtssOspf6StatusRouteAreaEntry 7 }

vtssOspf6StatusInterfaceTable OBJECT-TYPE
    SYNTAX      SEQUENCE OF VTSSOspf6StatusInterfaceEntry
    MAX-ACCESS  not-accessible
    STATUS      current
    DESCRIPTION
        "This is OSPF6 interface status table. It is used to provide the OSPF6
         interface status information."
    ::= { vtssOspf6Status 5 }

vtssOspf6StatusInterfaceEntry OBJECT-TYPE
    SYNTAX      VTSSOspf6StatusInterfaceEntry
    MAX-ACCESS  not-accessible
    STATUS      current
    DESCRIPTION
        "Each entry in this table represents OSPF6 interface status information."
    INDEX       { vtssOspf6StatusInterfaceIfIndex }
    ::= { vtssOspf6StatusInterfaceTable 1 }

VTSSOspf6StatusInterfaceEntry ::= SEQUENCE {
    vtssOspf6StatusInterfaceIfIndex             VTSSInterfaceIndex,
    vtssOspf6StatusInterfaceStatus              TruthValue,
    vtssOspf6StatusInterfacePassive             TruthValue,
    vtssOspf6StatusInterfaceNetwork             InetAddressIPv6,
    vtssOspf6StatusInterfaceIpSubnetMaskLength  Integer32,
    vtssOspf6StatusInterfaceAreaId              IpAddress,
    vtssOspf6StatusInterfaceRouterId            IpAddress,
    vtssOspf6StatusInterfaceCost                Integer32,
    vtssOspf6StatusInterfaceState               VTSSOspf6InterfaceState,
    vtssOspf6StatusInterfacePriority            Integer32,
    vtssOspf6StatusInterfaceDrId                IpAddress,
    vtssOspf6StatusInterfaceBdrId               IpAddress,
    vtssOspf6StatusInterfaceHelloTime           Unsigned32,
    vtssOspf6StatusInterfaceDeadTime            Unsigned32,
    vtssOspf6StatusInterfaceRetransmitTime      Unsigned32,
    vtssOspf6StatusInterfaceTransmitDelay       Unsigned32
}

vtssOspf6StatusInterfaceIfIndex OBJECT-TYPE
    SYNTAX      VTSSInterfaceIndex
    MAX-ACCESS  accessible-for-notify
    STATUS      current
    DESCRIPTION
        "Logical interface number."
    ::= { vtssOspf6StatusInterfaceEntry 1 }

vtssOspf6StatusInterfaceStatus OBJECT-TYPE
    SYNTAX      TruthValue
    MAX-ACCESS  read-only
    STATUS      current
    DESCRIPTION
        "It's used to indicate if the interface is up or down."
    ::= { vtssOspf6StatusInterfaceEntry 2 }

vtssOspf6StatusInterfacePassive OBJECT-TYPE
    SYNTAX      TruthValue
    MAX-ACCESS  read-only
    STATUS      current
    DESCRIPTION
        "Indicate if the interface is passive interface."
    ::= { vtssOspf6StatusInterfaceEntry 3 }

vtssOspf6StatusInterfaceNetwork OBJECT-TYPE
    SYNTAX      InetAddressIPv6
    MAX-ACCESS  read-only
    STATUS      current
    DESCRIPTION
        "IPv6 network address."
    ::= { vtssOspf6StatusInterfaceEntry 4 }

vtssOspf6StatusInterfaceIpSubnetMaskLength OBJECT-TYPE
    SYNTAX      Integer32 (0..128)
    MAX-ACCESS  read-only
    STATUS      current
    DESCRIPTION
        "IPv6 network mask length."
    ::= { vtssOspf6StatusInterfaceEntry 5 }

vtssOspf6StatusInterfaceAreaId OBJECT-TYPE
    SYNTAX      IpAddress
    MAX-ACCESS  read-only
    STATUS      current
    DESCRIPTION
        "The OSPF6 area ID."
    ::= { vtssOspf6StatusInterfaceEntry 6 }

vtssOspf6StatusInterfaceRouterId OBJECT-TYPE
    SYNTAX      IpAddress
    MAX-ACCESS  read-only
    STATUS      current
    DESCRIPTION
        "The OSPF6 router ID."
    ::= { vtssOspf6StatusInterfaceEntry 7 }

vtssOspf6StatusInterfaceCost OBJECT-TYPE
    SYNTAX      Integer32 (1..65535)
    MAX-ACCESS  read-only
    STATUS      current
    DESCRIPTION
        "The cost of the interface."
    ::= { vtssOspf6StatusInterfaceEntry 8 }

vtssOspf6StatusInterfaceState OBJECT-TYPE
    SYNTAX      VTSSOspf6InterfaceState
    MAX-ACCESS  read-only
    STATUS      current
    DESCRIPTION
        "The state of the link."
    ::= { vtssOspf6StatusInterfaceEntry 9 }

vtssOspf6StatusInterfacePriority OBJECT-TYPE
    SYNTAX      Integer32 (0..255)
    MAX-ACCESS  read-only
    STATUS      current
    DESCRIPTION
        "The OSPF6 priority. It helps determine the DR and BDR on the network to
         which this interface is connected."
    ::= { vtssOspf6StatusInterfaceEntry 10 }

vtssOspf6StatusInterfaceDrId OBJECT-TYPE
    SYNTAX      IpAddress
    MAX-ACCESS  read-only
    STATUS      current
    DESCRIPTION
        "The router ID of DR."
    ::= { vtssOspf6StatusInterfaceEntry 11 }

vtssOspf6StatusInterfaceBdrId OBJECT-TYPE
    SYNTAX      IpAddress
    MAX-ACCESS  read-only
    STATUS      current
    DESCRIPTION
        "The router ID of BDR."
    ::= { vtssOspf6StatusInterfaceEntry 12 }

vtssOspf6StatusInterfaceHelloTime OBJECT-TYPE
    SYNTAX      Unsigned32
    MAX-ACCESS  read-only
    STATUS      current
    DESCRIPTION
        "Hello timer. A time interval that a router sends an OSPF6 hello packet."
    ::= { vtssOspf6StatusInterfaceEntry 13 }

vtssOspf6StatusInterfaceDeadTime OBJECT-TYPE
    SYNTAX      Unsigned32
    MAX-ACCESS  read-only
    STATUS      current
    DESCRIPTION
        "Dead timer. Dead timer is a time interval to wait before declaring a
         neighbor dead. The unit of time is the second."
    ::= { vtssOspf6StatusInterfaceEntry 14 }

vtssOspf6StatusInterfaceRetransmitTime OBJECT-TYPE
    SYNTAX      Unsigned32
    MAX-ACCESS  read-only
    STATUS      current
    DESCRIPTION
        "Retransmit timer. A time interval to wait before retransmitting a
         database description packet when it has not been acknowledged."
    ::= { vtssOspf6StatusInterfaceEntry 15 }

vtssOspf6StatusInterfaceTransmitDelay OBJECT-TYPE
    SYNTAX      Unsigned32
    MAX-ACCESS  read-only
    STATUS      current
    DESCRIPTION
        "The estimated time to transmit a link-state update packet on the
         interface."
    ::= { vtssOspf6StatusInterfaceEntry 16 }

vtssOspf6StatusNeighborIpv6Table OBJECT-TYPE
    SYNTAX      SEQUENCE OF VTSSOspf6StatusNeighborIpv6Entry
    MAX-ACCESS  not-accessible
    STATUS      current
    DESCRIPTION
        "This is OSPF6 IPv6 neighbor status table. It is used to provide the
         OSPF6 neighbor status information."
    ::= { vtssOspf6Status 6 }

vtssOspf6StatusNeighborIpv6Entry OBJECT-TYPE
    SYNTAX      VTSSOspf6StatusNeighborIpv6Entry
    MAX-ACCESS  not-accessible
    STATUS      current
    DESCRIPTION
        "Each entry in this table represents OSPF6 IPv6 neighbor status
         information."
    INDEX       { vtssOspf6StatusNeighborIpv6InstanceId,
                  vtssOspf6StatusNeighborIpv6RouterId,
                  vtssOspf6StatusNeighborIpv6Ipv6Addr,
                  vtssOspf6StatusNeighborIpv6IfIndex }
    ::= { vtssOspf6StatusNeighborIpv6Table 1 }

VTSSOspf6StatusNeighborIpv6Entry ::= SEQUENCE {
    vtssOspf6StatusNeighborIpv6InstanceId     Integer32,
    vtssOspf6StatusNeighborIpv6RouterId       IpAddress,
    vtssOspf6StatusNeighborIpv6Ipv6Addr       InetAddressIPv6,
    vtssOspf6StatusNeighborIpv6IfIndex        VTSSInterfaceIndex,
    vtssOspf6StatusNeighborIpv6IpAddr         InetAddressIPv6,
    vtssOspf6StatusNeighborIpv6AreaId         IpAddress,
    vtssOspf6StatusNeighborIpv6NeighborId     IpAddress,
    vtssOspf6StatusNeighborIpv6Priority       Integer32,
    vtssOspf6StatusNeighborIpv6State          VTSSOspf6NeighborState,
    vtssOspf6StatusNeighborIpv6DrId           IpAddress,
    vtssOspf6StatusNeighborIpv6BdrId          IpAddress,
    vtssOspf6StatusNeighborIpv6DeadTime       Unsigned32,
    vtssOspf6StatusNeighborIpv6TransitAreaId  IpAddress
}

vtssOspf6StatusNeighborIpv6InstanceId OBJECT-TYPE
    SYNTAX      Integer32 (1..1)
    MAX-ACCESS  accessible-for-notify
    STATUS      current
    DESCRIPTION
        "The OSPF6 process instance ID."
    ::= { vtssOspf6StatusNeighborIpv6Entry 1 }

vtssOspf6StatusNeighborIpv6RouterId OBJECT-TYPE
    SYNTAX      IpAddress
    MAX-ACCESS  accessible-for-notify
    STATUS      current
    DESCRIPTION
        "The OSPF6 router ID."
    ::= { vtssOspf6StatusNeighborIpv6Entry 2 }

vtssOspf6StatusNeighborIpv6Ipv6Addr OBJECT-TYPE
    SYNTAX      InetAddressIPv6
    MAX-ACCESS  accessible-for-notify
    STATUS      current
    DESCRIPTION
        "The IPv6 address."
    ::= { vtssOspf6StatusNeighborIpv6Entry 3 }

vtssOspf6StatusNeighborIpv6IfIndex OBJECT-TYPE
    SYNTAX      VTSSInterfaceIndex
    MAX-ACCESS  accessible-for-notify
    STATUS      current
    DESCRIPTION
        "Logical interface number."
    ::= { vtssOspf6StatusNeighborIpv6Entry 4 }

vtssOspf6StatusNeighborIpv6IpAddr OBJECT-TYPE
    SYNTAX      InetAddressIPv6
    MAX-ACCESS  read-only
    STATUS      current
    DESCRIPTION
        "The IP address."
    ::= { vtssOspf6StatusNeighborIpv6Entry 5 }

vtssOspf6StatusNeighborIpv6AreaId OBJECT-TYPE
    SYNTAX      IpAddress
    MAX-ACCESS  read-only
    STATUS      current
    DESCRIPTION
        "The OSPF6 area ID."
    ::= { vtssOspf6StatusNeighborIpv6Entry 6 }

vtssOspf6StatusNeighborIpv6NeighborId OBJECT-TYPE
    SYNTAX      IpAddress
    MAX-ACCESS  read-only
    STATUS      current
    DESCRIPTION
        "The router ID of Neighbor."
    ::= { vtssOspf6StatusNeighborIpv6Entry 7 }

vtssOspf6StatusNeighborIpv6Priority OBJECT-TYPE
    SYNTAX      Integer32 (0..255)
    MAX-ACCESS  read-only
    STATUS      current
    DESCRIPTION
        "The priority of OSPF6 neighbor. It indicates the priority of the
         neighbor router. This item is used when selecting the DR for the
         network. The router with the highest priority becomes the DR."
    ::= { vtssOspf6StatusNeighborIpv6Entry 8 }

vtssOspf6StatusNeighborIpv6State OBJECT-TYPE
    SYNTAX      VTSSOspf6NeighborState
    MAX-ACCESS  read-only
    STATUS      current
    DESCRIPTION
        "The state of OSPF6 neighbor. It indicates the functional state of the
         neighbor router."
    ::= { vtssOspf6StatusNeighborIpv6Entry 9 }

vtssOspf6StatusNeighborIpv6DrId OBJECT-TYPE
    SYNTAX      IpAddress
    MAX-ACCESS  read-only
    STATUS      current
    DESCRIPTION
        "The router ID of DR."
    ::= { vtssOspf6StatusNeighborIpv6Entry 10 }

vtssOspf6StatusNeighborIpv6BdrId OBJECT-TYPE
    SYNTAX      IpAddress
    MAX-ACCESS  read-only
    STATUS      current
    DESCRIPTION
        "The router ID of BDR."
    ::= { vtssOspf6StatusNeighborIpv6Entry 11 }

vtssOspf6StatusNeighborIpv6DeadTime OBJECT-TYPE
    SYNTAX      Unsigned32
    MAX-ACCESS  read-only
    STATUS      current
    DESCRIPTION
        "Dead timer. It indicates the amount of time remaining that the router
         waits to receive an OSPF6 hello packet from the neighbor before
         declaring the neighbor down."
    ::= { vtssOspf6StatusNeighborIpv6Entry 12 }

vtssOspf6StatusNeighborIpv6TransitAreaId OBJECT-TYPE
    SYNTAX      IpAddress
    MAX-ACCESS  read-only
    STATUS      current
    DESCRIPTION
        "The OSPF6 transit area ID for the neighbor on virtual link interface."
    ::= { vtssOspf6StatusNeighborIpv6Entry 13 }

vtssOspf6StatusRouteIpv6Table OBJECT-TYPE
    SYNTAX      SEQUENCE OF VTSSOspf6StatusRouteIpv6Entry
    MAX-ACCESS  not-accessible
    STATUS      current
    DESCRIPTION
        "This is OSPF6 routing status table. It is used to provide the OSPF6
         routing status information."
    ::= { vtssOspf6Status 10 }

vtssOspf6StatusRouteIpv6Entry OBJECT-TYPE
    SYNTAX      VTSSOspf6StatusRouteIpv6Entry
    MAX-ACCESS  not-accessible
    STATUS      current
    DESCRIPTION
        "Each entry in this table represents OSPF6 routing status information."
    INDEX       { vtssOspf6StatusRouteIpv6InstanceId,
                  vtssOspf6StatusRouteIpv6RouteType,
                  vtssOspf6StatusRouteIpv6Network,
                  vtssOspf6StatusRouteIpv6IpSubnetMaskLength,
                  vtssOspf6StatusRouteIpv6AreaId,
                  vtssOspf6StatusRouteIpv6NextHop }
    ::= { vtssOspf6StatusRouteIpv6Table 1 }

VTSSOspf6StatusRouteIpv6Entry ::= SEQUENCE {
    vtssOspf6StatusRouteIpv6InstanceId          Integer32,
    vtssOspf6StatusRouteIpv6RouteType           VTSSOspf6RouteType,
    vtssOspf6StatusRouteIpv6Network             InetAddressIPv6,
    vtssOspf6StatusRouteIpv6IpSubnetMaskLength  Integer32,
    vtssOspf6StatusRouteIpv6AreaId              IpAddress,
    vtssOspf6StatusRouteIpv6NextHop             InetAddressIPv6,
    vtssOspf6StatusRouteIpv6Cost                Unsigned32,
    vtssOspf6StatusRouteIpv6AsCost              Unsigned32,
    vtssOspf6StatusRouteIpv6BorderRouterType    VTSSOspf6BorderRouterType,
    vtssOspf6StatusRouteIpv6Ifindex             VTSSInterfaceIndex,
    vtssOspf6StatusRouteIpv6IsConnected         TruthValue
}

vtssOspf6StatusRouteIpv6InstanceId OBJECT-TYPE
    SYNTAX      Integer32 (1..1)
    MAX-ACCESS  accessible-for-notify
    STATUS      current
    DESCRIPTION
        "The OSPF6 process instance ID."
    ::= { vtssOspf6StatusRouteIpv6Entry 1 }

vtssOspf6StatusRouteIpv6RouteType OBJECT-TYPE
    SYNTAX      VTSSOspf6RouteType
    MAX-ACCESS  accessible-for-notify
    STATUS      current
    DESCRIPTION
        "The OSPF6 route type."
    ::= { vtssOspf6StatusRouteIpv6Entry 2 }

vtssOspf6StatusRouteIpv6Network OBJECT-TYPE
    SYNTAX      InetAddressIPv6
    MAX-ACCESS  accessible-for-notify
    STATUS      current
    DESCRIPTION
        "IPv6 network address."
    ::= { vtssOspf6StatusRouteIpv6Entry 3 }

vtssOspf6StatusRouteIpv6IpSubnetMaskLength OBJECT-TYPE
    SYNTAX      Integer32 (0..128)
    MAX-ACCESS  accessible-for-notify
    STATUS      current
    DESCRIPTION
        "IPv6 network mask length."
    ::= { vtssOspf6StatusRouteIpv6Entry 4 }

vtssOspf6StatusRouteIpv6AreaId OBJECT-TYPE
    SYNTAX      IpAddress
    MAX-ACCESS  accessible-for-notify
    STATUS      current
    DESCRIPTION
        "It indicates which area the route or router can be reached via/to."
    ::= { vtssOspf6StatusRouteIpv6Entry 5 }

vtssOspf6StatusRouteIpv6NextHop OBJECT-TYPE
    SYNTAX      InetAddressIPv6
    MAX-ACCESS  accessible-for-notify
    STATUS      current
    DESCRIPTION
        "The nexthop to the route."
    ::= { vtssOspf6StatusRouteIpv6Entry 6 }

vtssOspf6StatusRouteIpv6Cost OBJECT-TYPE
    SYNTAX      Unsigned32
    MAX-ACCESS  read-only
    STATUS      current
    DESCRIPTION
        "The cost of the route."
    ::= { vtssOspf6StatusRouteIpv6Entry 7 }

vtssOspf6StatusRouteIpv6AsCost OBJECT-TYPE
    SYNTAX      Unsigned32
    MAX-ACCESS  read-only
    STATUS      current
    DESCRIPTION
        "The cost of the route within the OSPF6 network. It is valid for
         external Type-2 route and always '0' for other route type."
    ::= { vtssOspf6StatusRouteIpv6Entry 8 }

vtssOspf6StatusRouteIpv6BorderRouterType OBJECT-TYPE
    SYNTAX      VTSSOspf6BorderRouterType
    MAX-ACCESS  read-only
    STATUS      current
    DESCRIPTION
        "The border router type of the OSPF6 route entry."
    ::= { vtssOspf6StatusRouteIpv6Entry 9 }

vtssOspf6StatusRouteIpv6Ifindex OBJECT-TYPE
    SYNTAX      VTSSInterfaceIndex
    MAX-ACCESS  read-only
    STATUS      current
    DESCRIPTION
        "The interface where the ip packet is outgoing."
    ::= { vtssOspf6StatusRouteIpv6Entry 10 }

vtssOspf6StatusRouteIpv6IsConnected OBJECT-TYPE
    SYNTAX      TruthValue
    MAX-ACCESS  read-only
    STATUS      current
    DESCRIPTION
        "The destination is connected directly or not."
    ::= { vtssOspf6StatusRouteIpv6Entry 11 }

vtssOspf6StatusDbTable OBJECT-TYPE
    SYNTAX      SEQUENCE OF VTSSOspf6StatusDbEntry
    MAX-ACCESS  not-accessible
    STATUS      current
    DESCRIPTION
        "The OSPF6 LSA link state database information table."
    ::= { vtssOspf6Status 11 }

vtssOspf6StatusDbEntry OBJECT-TYPE
    SYNTAX      VTSSOspf6StatusDbEntry
    MAX-ACCESS  not-accessible
    STATUS      current
    DESCRIPTION
        "Each row contains the corresponding information of a single link state
         advertisement."
    INDEX       { vtssOspf6StatusDbInstanceId,
                  vtssOspf6StatusDbAreaId, vtssOspf6StatusDbLsdbType,
                  vtssOspf6StatusDbLinkStateId,
                  vtssOspf6StatusDbAdvRouterId }
    ::= { vtssOspf6StatusDbTable 1 }

VTSSOspf6StatusDbEntry ::= SEQUENCE {
    vtssOspf6StatusDbInstanceId       Integer32,
    vtssOspf6StatusDbAreaId           IpAddress,
    vtssOspf6StatusDbLsdbType         VTSSOspf6LsdbType,
    vtssOspf6StatusDbLinkStateId      IpAddress,
    vtssOspf6StatusDbAdvRouterId      IpAddress,
    vtssOspf6StatusDbAge              Unsigned32,
    vtssOspf6StatusDbSequence         Unsigned32,
    vtssOspf6StatusDbRouterLinkCount  Unsigned32
}

vtssOspf6StatusDbInstanceId OBJECT-TYPE
    SYNTAX      Integer32 (1..1)
    MAX-ACCESS  accessible-for-notify
    STATUS      current
    DESCRIPTION
        "The OSPF6 process instance ID."
    ::= { vtssOspf6StatusDbEntry 1 }

vtssOspf6StatusDbAreaId OBJECT-TYPE
    SYNTAX      IpAddress
    MAX-ACCESS  accessible-for-notify
    STATUS      current
    DESCRIPTION
        "The OSPF6 area ID."
    ::= { vtssOspf6StatusDbEntry 2 }

vtssOspf6StatusDbLsdbType OBJECT-TYPE
    SYNTAX      VTSSOspf6LsdbType
    MAX-ACCESS  accessible-for-notify
    STATUS      current
    DESCRIPTION
        "The type of the link state advertisement."
    ::= { vtssOspf6StatusDbEntry 3 }

vtssOspf6StatusDbLinkStateId OBJECT-TYPE
    SYNTAX      IpAddress
    MAX-ACCESS  accessible-for-notify
    STATUS      current
    DESCRIPTION
        "The OSPF6 link state ID."
    ::= { vtssOspf6StatusDbEntry 4 }

vtssOspf6StatusDbAdvRouterId OBJECT-TYPE
    SYNTAX      IpAddress
    MAX-ACCESS  accessible-for-notify
    STATUS      current
    DESCRIPTION
        "The advertising router ID which originated the LSA."
    ::= { vtssOspf6StatusDbEntry 5 }

vtssOspf6StatusDbAge OBJECT-TYPE
    SYNTAX      Unsigned32
    MAX-ACCESS  read-only
    STATUS      current
    DESCRIPTION
        "The time in seconds since the LSA was originated."
    ::= { vtssOspf6StatusDbEntry 6 }

vtssOspf6StatusDbSequence OBJECT-TYPE
    SYNTAX      Unsigned32
    MAX-ACCESS  read-only
    STATUS      current
    DESCRIPTION
        "The LS sequence number of the LSA."
    ::= { vtssOspf6StatusDbEntry 7 }

vtssOspf6StatusDbRouterLinkCount OBJECT-TYPE
    SYNTAX      Unsigned32
    MAX-ACCESS  read-only
    STATUS      current
    DESCRIPTION
        "The link count of the LSA. The field is significant only when the link
         state type is 'Router Link State' (Type 1)."
    ::= { vtssOspf6StatusDbEntry 8 }

vtssOspf6StatusDbRouterTable OBJECT-TYPE
    SYNTAX      SEQUENCE OF VTSSOspf6StatusDbRouterEntry
    MAX-ACCESS  not-accessible
    STATUS      current
    DESCRIPTION
        "The OSPF6 LSA Router link state database information table."
    ::= { vtssOspf6Status 12 }

vtssOspf6StatusDbRouterEntry OBJECT-TYPE
    SYNTAX      VTSSOspf6StatusDbRouterEntry
    MAX-ACCESS  not-accessible
    STATUS      current
    DESCRIPTION
        "Each row contains the corresponding information of a single link state
         advertisement."
    INDEX       { vtssOspf6StatusDbRouterInstanceId,
                  vtssOspf6StatusDbRouterAreaId,
                  vtssOspf6StatusDbRouterLsdbType,
                  vtssOspf6StatusDbRouterLinkStateId,
                  vtssOspf6StatusDbRouterAdvRouterId }
    ::= { vtssOspf6StatusDbRouterTable 1 }

VTSSOspf6StatusDbRouterEntry ::= SEQUENCE {
    vtssOspf6StatusDbRouterInstanceId       Integer32,
    vtssOspf6StatusDbRouterAreaId           IpAddress,
    vtssOspf6StatusDbRouterLsdbType         VTSSOspf6LsdbType,
    vtssOspf6StatusDbRouterLinkStateId      IpAddress,
    vtssOspf6StatusDbRouterAdvRouterId      IpAddress,
    vtssOspf6StatusDbRouterAge              Unsigned32,
    vtssOspf6StatusDbRouterOptions          Unsigned32,
    vtssOspf6StatusDbRouterSequence         Unsigned32,
    vtssOspf6StatusDbRouterChecksum         Unsigned32,
    vtssOspf6StatusDbRouterLength           Unsigned32,
    vtssOspf6StatusDbRouterRouterLinkCount  Unsigned32
}

vtssOspf6StatusDbRouterInstanceId OBJECT-TYPE
    SYNTAX      Integer32 (1..1)
    MAX-ACCESS  accessible-for-notify
    STATUS      current
    DESCRIPTION
        "The OSPF6 process instance ID."
    ::= { vtssOspf6StatusDbRouterEntry 1 }

vtssOspf6StatusDbRouterAreaId OBJECT-TYPE
    SYNTAX      IpAddress
    MAX-ACCESS  accessible-for-notify
    STATUS      current
    DESCRIPTION
        "The OSPF6 area ID."
    ::= { vtssOspf6StatusDbRouterEntry 2 }

vtssOspf6StatusDbRouterLsdbType OBJECT-TYPE
    SYNTAX      VTSSOspf6LsdbType
    MAX-ACCESS  accessible-for-notify
    STATUS      current
    DESCRIPTION
        "The type of the link state advertisement."
    ::= { vtssOspf6StatusDbRouterEntry 3 }

vtssOspf6StatusDbRouterLinkStateId OBJECT-TYPE
    SYNTAX      IpAddress
    MAX-ACCESS  accessible-for-notify
    STATUS      current
    DESCRIPTION
        "The OSPF6 link state ID."
    ::= { vtssOspf6StatusDbRouterEntry 4 }

vtssOspf6StatusDbRouterAdvRouterId OBJECT-TYPE
    SYNTAX      IpAddress
    MAX-ACCESS  accessible-for-notify
    STATUS      current
    DESCRIPTION
        "The advertising router ID which originated the LSA."
    ::= { vtssOspf6StatusDbRouterEntry 5 }

vtssOspf6StatusDbRouterAge OBJECT-TYPE
    SYNTAX      Unsigned32
    MAX-ACCESS  read-only
    STATUS      current
    DESCRIPTION
        "The time in seconds since the LSA was originated."
    ::= { vtssOspf6StatusDbRouterEntry 6 }

vtssOspf6StatusDbRouterOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbRouterEntry 7 }

vtssOspf6StatusDbRouterSequence OBJECT-TYPE
    SYNTAX      Unsigned32
    MAX-ACCESS  read-only
    STATUS      current
    DESCRIPTION
        "The LS sequence number of the LSA."
    ::= { vtssOspf6StatusDbRouterEntry 8 }

vtssOspf6StatusDbRouterChecksum OBJECT-TYPE
    SYNTAX      Unsigned32
    MAX-ACCESS  read-only
    STATUS      current
    DESCRIPTION
        "The checksum of the LSA contents."
    ::= { vtssOspf6StatusDbRouterEntry 9 }

vtssOspf6StatusDbRouterLength OBJECT-TYPE
    SYNTAX      Unsigned32
    MAX-ACCESS  read-only
    STATUS      current
    DESCRIPTION
        "The Length in bytes of the LSA."
    ::= { vtssOspf6StatusDbRouterEntry 10 }

vtssOspf6StatusDbRouterRouterLinkCount OBJECT-TYPE
    SYNTAX      Unsigned32
    MAX-ACCESS  read-only
    STATUS      current
    DESCRIPTION
        "The link count of the LSA. The field is significant only when the link
         state type is 'Router Link State' (Type 1)."
    ::= { vtssOspf6StatusDbRouterEntry 11 }

vtssOspf6StatusDbNetworkTable OBJECT-TYPE
    SYNTAX      SEQUENCE OF VTSSOspf6StatusDbNetworkEntry
    MAX-ACCESS  not-accessible
    STATUS      current
    DESCRIPTION
        "The OSPF6 LSA Network link state database information table."
    ::= { vtssOspf6Status 13 }

vtssOspf6StatusDbNetworkEntry OBJECT-TYPE
    SYNTAX      VTSSOspf6StatusDbNetworkEntry
    MAX-ACCESS  not-accessible
    STATUS      current
    DESCRIPTION
        "Each row contains the corresponding information of a single link state
         advertisement."
    INDEX       { vtssOspf6StatusDbNetworkInstanceId,
                  vtssOspf6StatusDbNetworkAreaId,
                  vtssOspf6StatusDbNetworkLsdbType,
                  vtssOspf6StatusDbNetworkLinkStateId,
                  vtssOspf6StatusDbNetworkAdvRouterId }
    ::= { vtssOspf6StatusDbNetworkTable 1 }

VTSSOspf6StatusDbNetworkEntry ::= SEQUENCE {
    vtssOspf6StatusDbNetworkInstanceId           Integer32,
    vtssOspf6StatusDbNetworkAreaId               IpAddress,
    vtssOspf6StatusDbNetworkLsdbType             VTSSOspf6LsdbType,
    vtssOspf6StatusDbNetworkLinkStateId          IpAddress,
    vtssOspf6StatusDbNetworkAdvRouterId          IpAddress,
    vtssOspf6StatusDbNetworkAge                  Unsigned32,
    vtssOspf6StatusDbNetworkOptions              Unsigned32,
    vtssOspf6StatusDbNetworkSequence             Unsigned32,
    vtssOspf6StatusDbNetworkChecksum             Unsigned32,
    vtssOspf6StatusDbNetworkLength               Unsigned32,
    vtssOspf6StatusDbNetworkAttachedRouterCount  Unsigned32
}

vtssOspf6StatusDbNetworkInstanceId OBJECT-TYPE
    SYNTAX      Integer32 (1..1)
    MAX-ACCESS  accessible-for-notify
    STATUS      current
    DESCRIPTION
        "The OSPF6 process instance ID."
    ::= { vtssOspf6StatusDbNetworkEntry 1 }

vtssOspf6StatusDbNetworkAreaId OBJECT-TYPE
    SYNTAX      IpAddress
    MAX-ACCESS  accessible-for-notify
    STATUS      current
    DESCRIPTION
        "The OSPF6 area ID."
    ::= { vtssOspf6StatusDbNetworkEntry 2 }

vtssOspf6StatusDbNetworkLsdbType OBJECT-TYPE
    SYNTAX      VTSSOspf6LsdbType
    MAX-ACCESS  accessible-for-notify
    STATUS      current
    DESCRIPTION
        "The type of the link state advertisement."
    ::= { vtssOspf6StatusDbNetworkEntry 3 }

vtssOspf6StatusDbNetworkLinkStateId OBJECT-TYPE
    SYNTAX      IpAddress
    MAX-ACCESS  accessible-for-notify
    STATUS      current
    DESCRIPTION
        "The OSPF6 link state ID."
    ::= { vtssOspf6StatusDbNetworkEntry 4 }

vtssOspf6StatusDbNetworkAdvRouterId OBJECT-TYPE
    SYNTAX      IpAddress
    MAX-ACCESS  accessible-for-notify
    STATUS      current
    DESCRIPTION
        "The advertising router ID which originated the LSA."
    ::= { vtssOspf6StatusDbNetworkEntry 5 }

vtssOspf6StatusDbNetworkAge OBJECT-TYPE
    SYNTAX      Unsigned32
    MAX-ACCESS  read-only
    STATUS      current
    DESCRIPTION
        "The time in seconds since the LSA was originated."
    ::= { vtssOspf6StatusDbNetworkEntry 6 }

vtssOspf6StatusDbNetworkOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbNetworkEntry 7 }

vtssOspf6StatusDbNetworkSequence OBJECT-TYPE
    SYNTAX      Unsigned32
    MAX-ACCESS  read-only
    STATUS      current
    DESCRIPTION
        "The LS sequence number of the LSA."
    ::= { vtssOspf6StatusDbNetworkEntry 8 }

vtssOspf6StatusDbNetworkChecksum OBJECT-TYPE
    SYNTAX      Unsigned32
    MAX-ACCESS  read-only
    STATUS      current
    DESCRIPTION
        "The checksum of the LSA contents."
    ::= { vtssOspf6StatusDbNetworkEntry 9 }

vtssOspf6StatusDbNetworkLength OBJECT-TYPE
    SYNTAX      Unsigned32
    MAX-ACCESS  read-only
    STATUS      current
    DESCRIPTION
        "The Length in bytes of the LSA."
    ::= { vtssOspf6StatusDbNetworkEntry 10 }

vtssOspf6StatusDbNetworkAttachedRouterCount OBJECT-TYPE
    SYNTAX      Unsigned32
    MAX-ACCESS  read-only
    STATUS      current
    DESCRIPTION
        "The attached router count of the LSA. The field is significant only
         when the link state type is 'Network Link State' (Type 2)."
    ::= { vtssOspf6StatusDbNetworkEntry 11 }

vtssOspf6StatusDbInterAreaPrefixTable OBJECT-TYPE
    SYNTAX      SEQUENCE OF VTSSOspf6StatusDbInterAreaPrefixEntry
    MAX-ACCESS  not-accessible
    STATUS      current
    DESCRIPTION
        "The OSPF6 LSA Summary link state database information table."
    ::= { vtssOspf6Status 14 }

vtssOspf6StatusDbInterAreaPrefixEntry OBJECT-TYPE
    SYNTAX      VTSSOspf6StatusDbInterAreaPrefixEntry
    MAX-ACCESS  not-accessible
    STATUS      current
    DESCRIPTION
        "Each row contains the corresponding information of a single link state
         advertisement."
    INDEX       { vtssOspf6StatusDbInterAreaPrefixInstanceId,
                  vtssOspf6StatusDbInterAreaPrefixAreaId,
                  vtssOspf6StatusDbInterAreaPrefixLsdbType,
                  vtssOspf6StatusDbInterAreaPrefixLinkStateId,
                  vtssOspf6StatusDbInterAreaPrefixAdvRouterId }
    ::= { vtssOspf6StatusDbInterAreaPrefixTable 1 }

VTSSOspf6StatusDbInterAreaPrefixEntry ::= SEQUENCE {
    vtssOspf6StatusDbInterAreaPrefixInstanceId          Integer32,
    vtssOspf6StatusDbInterAreaPrefixAreaId              IpAddress,
    vtssOspf6StatusDbInterAreaPrefixLsdbType            VTSSOspf6LsdbType,
    vtssOspf6StatusDbInterAreaPrefixLinkStateId         IpAddress,
    vtssOspf6StatusDbInterAreaPrefixAdvRouterId         IpAddress,
    vtssOspf6StatusDbInterAreaPrefixAge                 Unsigned32,
    vtssOspf6StatusDbInterAreaPrefixOptions             Unsigned32,
    vtssOspf6StatusDbInterAreaPrefixSequence            Unsigned32,
    vtssOspf6StatusDbInterAreaPrefixChecksum            Unsigned32,
    vtssOspf6StatusDbInterAreaPrefixLength              Unsigned32,
    vtssOspf6StatusDbInterAreaPrefixPrefixAddress       InetAddressIPv6,
    vtssOspf6StatusDbInterAreaPrefixIpSubnetMaskLength  Integer32,
    vtssOspf6StatusDbInterAreaPrefixMetric              Unsigned32
}

vtssOspf6StatusDbInterAreaPrefixInstanceId OBJECT-TYPE
    SYNTAX      Integer32 (1..1)
    MAX-ACCESS  accessible-for-notify
    STATUS      current
    DESCRIPTION
        "The OSPF6 process instance ID."
    ::= { vtssOspf6StatusDbInterAreaPrefixEntry 1 }

vtssOspf6StatusDbInterAreaPrefixAreaId OBJECT-TYPE
    SYNTAX      IpAddress
    MAX-ACCESS  accessible-for-notify
    STATUS      current
    DESCRIPTION
        "The OSPF6 area ID."
    ::= { vtssOspf6StatusDbInterAreaPrefixEntry 2 }

vtssOspf6StatusDbInterAreaPrefixLsdbType OBJECT-TYPE
    SYNTAX      VTSSOspf6LsdbType
    MAX-ACCESS  accessible-for-notify
    STATUS      current
    DESCRIPTION
        "The type of the link state advertisement."
    ::= { vtssOspf6StatusDbInterAreaPrefixEntry 3 }

vtssOspf6StatusDbInterAreaPrefixLinkStateId OBJECT-TYPE
    SYNTAX      IpAddress
    MAX-ACCESS  accessible-for-notify
    STATUS      current
    DESCRIPTION
        "The OSPF6 link state ID."
    ::= { vtssOspf6StatusDbInterAreaPrefixEntry 4 }

vtssOspf6StatusDbInterAreaPrefixAdvRouterId OBJECT-TYPE
    SYNTAX      IpAddress
    MAX-ACCESS  accessible-for-notify
    STATUS      current
    DESCRIPTION
        "The advertising router ID which originated the LSA."
    ::= { vtssOspf6StatusDbInterAreaPrefixEntry 5 }

vtssOspf6StatusDbInterAreaPrefixAge OBJECT-TYPE
    SYNTAX      Unsigned32
    MAX-ACCESS  read-only
    STATUS      current
    DESCRIPTION
        "The time in seconds since the LSA was originated."
    ::= { vtssOspf6StatusDbInterAreaPrefixEntry 6 }

vtssOspf6StatusDbInterAreaPrefixOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbInterAreaPrefixEntry 7 }

vtssOspf6StatusDbInterAreaPrefixSequence OBJECT-TYPE
    SYNTAX      Unsigned32
    MAX-ACCESS  read-only
    STATUS      current
    DESCRIPTION
        "The LS sequence number of the LSA."
    ::= { vtssOspf6StatusDbInterAreaPrefixEntry 8 }

vtssOspf6StatusDbInterAreaPrefixChecksum OBJECT-TYPE
    SYNTAX      Unsigned32
    MAX-ACCESS  read-only
    STATUS      current
    DESCRIPTION
        "The checksum of the LSA contents."
    ::= { vtssOspf6StatusDbInterAreaPrefixEntry 9 }

vtssOspf6StatusDbInterAreaPrefixLength OBJECT-TYPE
    SYNTAX      Unsigned32
    MAX-ACCESS  read-only
    STATUS      current
    DESCRIPTION
        "The Length in bytes of the LSA."
    ::= { vtssOspf6StatusDbInterAreaPrefixEntry 10 }

vtssOspf6StatusDbInterAreaPrefixPrefixAddress OBJECT-TYPE
    SYNTAX      InetAddressIPv6
    MAX-ACCESS  read-only
    STATUS      current
    DESCRIPTION
        "IPv6 network address."
    ::= { vtssOspf6StatusDbInterAreaPrefixEntry 11 }

vtssOspf6StatusDbInterAreaPrefixIpSubnetMaskLength OBJECT-TYPE
    SYNTAX      Integer32 (0..128)
    MAX-ACCESS  read-only
    STATUS      current
    DESCRIPTION
        "IPv6 network mask length."
    ::= { vtssOspf6StatusDbInterAreaPrefixEntry 12 }

vtssOspf6StatusDbInterAreaPrefixMetric OBJECT-TYPE
    SYNTAX      Unsigned32 (0..16777215)
    MAX-ACCESS  read-only
    STATUS      current
    DESCRIPTION
        "User specified metric for this summary route. The field is significant
         only when the link state type is 'Inter_Area Prefix/Router Link State'
         (Type 3, 4)."
    ::= { vtssOspf6StatusDbInterAreaPrefixEntry 13 }

vtssOspf6StatusDbInterAreaRouterTable OBJECT-TYPE
    SYNTAX      SEQUENCE OF VTSSOspf6StatusDbInterAreaRouterEntry
    MAX-ACCESS  not-accessible
    STATUS      current
    DESCRIPTION
        "The OSPF6 LSA ASBR Summary link state database information table."
    ::= { vtssOspf6Status 15 }

vtssOspf6StatusDbInterAreaRouterEntry OBJECT-TYPE
    SYNTAX      VTSSOspf6StatusDbInterAreaRouterEntry
    MAX-ACCESS  not-accessible
    STATUS      current
    DESCRIPTION
        "Each row contains the corresponding information of a single link state
         advertisement."
    INDEX       { vtssOspf6StatusDbInterAreaRouterInstanceId,
                  vtssOspf6StatusDbInterAreaRouterAreaId,
                  vtssOspf6StatusDbInterAreaRouterLsdbType,
                  vtssOspf6StatusDbInterAreaRouterLinkStateId,
                  vtssOspf6StatusDbInterAreaRouterAdvRouterId }
    ::= { vtssOspf6StatusDbInterAreaRouterTable 1 }

VTSSOspf6StatusDbInterAreaRouterEntry ::= SEQUENCE {
    vtssOspf6StatusDbInterAreaRouterInstanceId   Integer32,
    vtssOspf6StatusDbInterAreaRouterAreaId       IpAddress,
    vtssOspf6StatusDbInterAreaRouterLsdbType     VTSSOspf6LsdbType,
    vtssOspf6StatusDbInterAreaRouterLinkStateId  IpAddress,
    vtssOspf6StatusDbInterAreaRouterAdvRouterId  IpAddress,
    vtssOspf6StatusDbInterAreaRouterAge          Unsigned32,
    vtssOspf6StatusDbInterAreaRouterOptions      Unsigned32,
    vtssOspf6StatusDbInterAreaRouterSequence     Unsigned32,
    vtssOspf6StatusDbInterAreaRouterChecksum     Unsigned32,
    vtssOspf6StatusDbInterAreaRouterLength       Unsigned32,
    vtssOspf6StatusDbInterAreaRouterMetric       Unsigned32
}

vtssOspf6StatusDbInterAreaRouterInstanceId OBJECT-TYPE
    SYNTAX      Integer32 (1..1)
    MAX-ACCESS  accessible-for-notify
    STATUS      current
    DESCRIPTION
        "The OSPF6 process instance ID."
    ::= { vtssOspf6StatusDbInterAreaRouterEntry 1 }

vtssOspf6StatusDbInterAreaRouterAreaId OBJECT-TYPE
    SYNTAX      IpAddress
    MAX-ACCESS  accessible-for-notify
    STATUS      current
    DESCRIPTION
        "The OSPF6 area ID."
    ::= { vtssOspf6StatusDbInterAreaRouterEntry 2 }

vtssOspf6StatusDbInterAreaRouterLsdbType OBJECT-TYPE
    SYNTAX      VTSSOspf6LsdbType
    MAX-ACCESS  accessible-for-notify
    STATUS      current
    DESCRIPTION
        "The type of the link state advertisement."
    ::= { vtssOspf6StatusDbInterAreaRouterEntry 3 }

vtssOspf6StatusDbInterAreaRouterLinkStateId OBJECT-TYPE
    SYNTAX      IpAddress
    MAX-ACCESS  accessible-for-notify
    STATUS      current
    DESCRIPTION
        "The OSPF6 link state ID."
    ::= { vtssOspf6StatusDbInterAreaRouterEntry 4 }

vtssOspf6StatusDbInterAreaRouterAdvRouterId OBJECT-TYPE
    SYNTAX      IpAddress
    MAX-ACCESS  accessible-for-notify
    STATUS      current
    DESCRIPTION
        "The advertising router ID which originated the LSA."
    ::= { vtssOspf6StatusDbInterAreaRouterEntry 5 }

vtssOspf6StatusDbInterAreaRouterAge OBJECT-TYPE
    SYNTAX      Unsigned32
    MAX-ACCESS  read-only
    STATUS      current
    DESCRIPTION
        "The time in seconds since the LSA was originated."
    ::= { vtssOspf6StatusDbInterAreaRouterEntry 6 }

vtssOspf6StatusDbInterAreaRouterOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbInterAreaRouterEntry 7 }

vtssOspf6StatusDbInterAreaRouterSequence OBJECT-TYPE
    SYNTAX      Unsigned32
    MAX-ACCESS  read-only
    STATUS      current
    DESCRIPTION
        "The LS sequence number of the LSA."
    ::= { vtssOspf6StatusDbInterAreaRouterEntry 8 }

vtssOspf6StatusDbInterAreaRouterChecksum OBJECT-TYPE
    SYNTAX      Unsigned32
    MAX-ACCESS  read-only
    STATUS      current
    DESCRIPTION
        "The checksum of the LSA contents."
    ::= { vtssOspf6StatusDbInterAreaRouterEntry 9 }

vtssOspf6StatusDbInterAreaRouterLength OBJECT-TYPE
    SYNTAX      Unsigned32
    MAX-ACCESS  read-only
    STATUS      current
    DESCRIPTION
        "The Length in bytes of the LSA."
    ::= { vtssOspf6StatusDbInterAreaRouterEntry 10 }

vtssOspf6StatusDbInterAreaRouterMetric OBJECT-TYPE
    SYNTAX      Unsigned32 (0..16777215)
    MAX-ACCESS  read-only
    STATUS      current
    DESCRIPTION
        "User specified metric for this summary route. The field is significant
         only when the link state type is 'Summary/ASBR Summary Link State'
         (Type 3, 4)."
    ::= { vtssOspf6StatusDbInterAreaRouterEntry 11 }

vtssOspf6StatusDbExternalTable OBJECT-TYPE
    SYNTAX      SEQUENCE OF VTSSOspf6StatusDbExternalEntry
    MAX-ACCESS  not-accessible
    STATUS      current
    DESCRIPTION
        "The OSPF6 LSA External link state database information table."
    ::= { vtssOspf6Status 16 }

vtssOspf6StatusDbExternalEntry OBJECT-TYPE
    SYNTAX      VTSSOspf6StatusDbExternalEntry
    MAX-ACCESS  not-accessible
    STATUS      current
    DESCRIPTION
        "Each row contains the corresponding information of a single link state
         advertisement."
    INDEX       { vtssOspf6StatusDbExternalInstanceId,
                  vtssOspf6StatusDbExternalAreaId,
                  vtssOspf6StatusDbExternalLsdbType,
                  vtssOspf6StatusDbExternalLinkStateId,
                  vtssOspf6StatusDbExternalAdvRouterId }
    ::= { vtssOspf6StatusDbExternalTable 1 }

VTSSOspf6StatusDbExternalEntry ::= SEQUENCE {
    vtssOspf6StatusDbExternalInstanceId          Integer32,
    vtssOspf6StatusDbExternalAreaId              IpAddress,
    vtssOspf6StatusDbExternalLsdbType            VTSSOspf6LsdbType,
    vtssOspf6StatusDbExternalLinkStateId         IpAddress,
    vtssOspf6StatusDbExternalAdvRouterId         IpAddress,
    vtssOspf6StatusDbExternalAge                 Unsigned32,
    vtssOspf6StatusDbExternalOptions             Unsigned32,
    vtssOspf6StatusDbExternalSequence            Unsigned32,
    vtssOspf6StatusDbExternalChecksum            Unsigned32,
    vtssOspf6StatusDbExternalLength              Unsigned32,
    vtssOspf6StatusDbExternalPrefixAddress       InetAddressIPv6,
    vtssOspf6StatusDbExternalIpSubnetMaskLength  Integer32,
    vtssOspf6StatusDbExternalMetric              Unsigned32,
    vtssOspf6StatusDbExternalMetricType          Unsigned32,
    vtssOspf6StatusDbExternalForwardAddress      InetAddressIPv6
}

vtssOspf6StatusDbExternalInstanceId OBJECT-TYPE
    SYNTAX      Integer32 (1..1)
    MAX-ACCESS  accessible-for-notify
    STATUS      current
    DESCRIPTION
        "The OSPF6 process instance ID."
    ::= { vtssOspf6StatusDbExternalEntry 1 }

vtssOspf6StatusDbExternalAreaId OBJECT-TYPE
    SYNTAX      IpAddress
    MAX-ACCESS  accessible-for-notify
    STATUS      current
    DESCRIPTION
        "The OSPF6 area ID."
    ::= { vtssOspf6StatusDbExternalEntry 2 }

vtssOspf6StatusDbExternalLsdbType OBJECT-TYPE
    SYNTAX      VTSSOspf6LsdbType
    MAX-ACCESS  accessible-for-notify
    STATUS      current
    DESCRIPTION
        "The type of the link state advertisement."
    ::= { vtssOspf6StatusDbExternalEntry 3 }

vtssOspf6StatusDbExternalLinkStateId OBJECT-TYPE
    SYNTAX      IpAddress
    MAX-ACCESS  accessible-for-notify
    STATUS      current
    DESCRIPTION
        "The OSPF6 link state ID."
    ::= { vtssOspf6StatusDbExternalEntry 4 }

vtssOspf6StatusDbExternalAdvRouterId OBJECT-TYPE
    SYNTAX      IpAddress
    MAX-ACCESS  accessible-for-notify
    STATUS      current
    DESCRIPTION
        "The advertising router ID which originated the LSA."
    ::= { vtssOspf6StatusDbExternalEntry 5 }

vtssOspf6StatusDbExternalAge OBJECT-TYPE
    SYNTAX      Unsigned32
    MAX-ACCESS  read-only
    STATUS      current
    DESCRIPTION
        "The time in seconds since the LSA was originated."
    ::= { vtssOspf6StatusDbExternalEntry 6 }

vtssOspf6StatusDbExternalOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbExternalEntry 7 }

vtssOspf6StatusDbExternalSequence OBJECT-TYPE
    SYNTAX      Unsigned32
    MAX-ACCESS  read-only
    STATUS      current
    DESCRIPTION
        "The LS sequence number of the LSA."
    ::= { vtssOspf6StatusDbExternalEntry 8 }

vtssOspf6StatusDbExternalChecksum OBJECT-TYPE
    SYNTAX      Unsigned32
    MAX-ACCESS  read-only
    STATUS      current
    DESCRIPTION
        "The checksum of the LSA contents."
    ::= { vtssOspf6StatusDbExternalEntry 9 }

vtssOspf6StatusDbExternalLength OBJECT-TYPE
    SYNTAX      Unsigned32
    MAX-ACCESS  read-only
    STATUS      current
    DESCRIPTION
        "The Length in bytes of the LSA."
    ::= { vtssOspf6StatusDbExternalEntry 10 }

vtssOspf6StatusDbExternalPrefixAddress OBJECT-TYPE
    SYNTAX      InetAddressIPv6
    MAX-ACCESS  read-only
    STATUS      current
    DESCRIPTION
        "IPv6 network address."
    ::= { vtssOspf6StatusDbExternalEntry 11 }

vtssOspf6StatusDbExternalIpSubnetMaskLength OBJECT-TYPE
    SYNTAX      Integer32 (0..128)
    MAX-ACCESS  read-only
    STATUS      current
    DESCRIPTION
        "IPv6 network mask length."
    ::= { vtssOspf6StatusDbExternalEntry 12 }

vtssOspf6StatusDbExternalMetric OBJECT-TYPE
    SYNTAX      Unsigned32 (0..16777215)
    MAX-ACCESS  read-only
    STATUS      current
    DESCRIPTION
        "User specified metric for this summary route. The field is significant
         only when the link state type is 'External/NSSA External Link State'
         (Type 5, 7)."
    ::= { vtssOspf6StatusDbExternalEntry 13 }

vtssOspf6StatusDbExternalMetricType OBJECT-TYPE
    SYNTAX      Unsigned32
    MAX-ACCESS  read-only
    STATUS      current
    DESCRIPTION
        "The External type of the LSA. The field is significant only when the
         link state type is 'External/NSSA External Link State' (Type 5, 7)."
    ::= { vtssOspf6StatusDbExternalEntry 14 }

vtssOspf6StatusDbExternalForwardAddress OBJECT-TYPE
    SYNTAX      InetAddressIPv6
    MAX-ACCESS  read-only
    STATUS      current
    DESCRIPTION
        "The IP address of forward address. The field is significant only when
         the link state type is 'External/NSSA External Link State' (Type 5, 7)."
    ::= { vtssOspf6StatusDbExternalEntry 15 }

vtssOspf6StatusDbLinkTable OBJECT-TYPE
    SYNTAX      SEQUENCE OF VTSSOspf6StatusDbLinkEntry
    MAX-ACCESS  not-accessible
    STATUS      current
    DESCRIPTION
        "The OSPF6 LSA Link link state database information table."
    ::= { vtssOspf6Status 17 }

vtssOspf6StatusDbLinkEntry OBJECT-TYPE
    SYNTAX      VTSSOspf6StatusDbLinkEntry
    MAX-ACCESS  not-accessible
    STATUS      current
    DESCRIPTION
        "Each row contains the corresponding information of a single link state
         advertisement."
    INDEX       { vtssOspf6StatusDbLinkInstanceId,
                  vtssOspf6StatusDbLinkAreaId,
                  vtssOspf6StatusDbLinkLsdbType,
                  vtssOspf6StatusDbLinkLinkStateId,
                  vtssOspf6StatusDbLinkAdvRouterId }
    ::= { vtssOspf6StatusDbLinkTable 1 }

VTSSOspf6StatusDbLinkEntry ::= SEQUENCE {
    vtssOspf6StatusDbLinkInstanceId        Integer32,
    vtssOspf6StatusDbLinkAreaId            IpAddress,
    vtssOspf6StatusDbLinkLsdbType          VTSSOspf6LsdbType,
    vtssOspf6StatusDbLinkLinkStateId       IpAddress,
    vtssOspf6StatusDbLinkAdvRouterId       IpAddress,
    vtssOspf6StatusDbLinkAge               Unsigned32,
    vtssOspf6StatusDbLinkOptions           Unsigned32,
    vtssOspf6StatusDbLinkSequence          Unsigned32,
    vtssOspf6StatusDbLinkChecksum          Unsigned32,
    vtssOspf6StatusDbLinkLength            Unsigned32,
    vtssOspf6StatusDbLinkLinkLocalAddress  InetAddressIPv6,
    vtssOspf6StatusDbLinkPrefixCnt         Unsigned32
}

vtssOspf6StatusDbLinkInstanceId OBJECT-TYPE
    SYNTAX      Integer32 (1..1)
    MAX-ACCESS  accessible-for-notify
    STATUS      current
    DESCRIPTION
        "The OSPF6 process instance ID."
    ::= { vtssOspf6StatusDbLinkEntry 1 }

vtssOspf6StatusDbLinkAreaId OBJECT-TYPE
    SYNTAX      IpAddress
    MAX-ACCESS  accessible-for-notify
    STATUS      current
    DESCRIPTION
        "The OSPF6 area ID."
    ::= { vtssOspf6StatusDbLinkEntry 2 }

vtssOspf6StatusDbLinkLsdbType OBJECT-TYPE
    SYNTAX      VTSSOspf6LsdbType
    MAX-ACCESS  accessible-for-notify
    STATUS      current
    DESCRIPTION
        "The type of the link state advertisement."
    ::= { vtssOspf6StatusDbLinkEntry 3 }

vtssOspf6StatusDbLinkLinkStateId OBJECT-TYPE
    SYNTAX      IpAddress
    MAX-ACCESS  accessible-for-notify
    STATUS      current
    DESCRIPTION
        "The OSPF6 link state ID."
    ::= { vtssOspf6StatusDbLinkEntry 4 }

vtssOspf6StatusDbLinkAdvRouterId OBJECT-TYPE
    SYNTAX      IpAddress
    MAX-ACCESS  accessible-for-notify
    STATUS      current
    DESCRIPTION
        "The advertising router ID which originated the LSA."
    ::= { vtssOspf6StatusDbLinkEntry 5 }

vtssOspf6StatusDbLinkAge OBJECT-TYPE
    SYNTAX      Unsigned32
    MAX-ACCESS  read-only
    STATUS      current
    DESCRIPTION
        "The time in seconds since the LSA was originated."
    ::= { vtssOspf6StatusDbLinkEntry 6 }

vtssOspf6StatusDbLinkOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbLinkEntry 7 }

vtssOspf6StatusDbLinkSequence OBJECT-TYPE
    SYNTAX      Unsigned32
    MAX-ACCESS  read-only
    STATUS      current
    DESCRIPTION
        "The LS sequence number of the LSA."
    ::= { vtssOspf6StatusDbLinkEntry 8 }

vtssOspf6StatusDbLinkChecksum OBJECT-TYPE
    SYNTAX      Unsigned32
    MAX-ACCESS  read-only
    STATUS      current
    DESCRIPTION
        "The checksum of the LSA contents."
    ::= { vtssOspf6StatusDbLinkEntry 9 }

vtssOspf6StatusDbLinkLength OBJECT-TYPE
    SYNTAX      Unsigned32
    MAX-ACCESS  read-only
    STATUS      current
    DESCRIPTION
        "The Length in bytes of the LSA."
    ::= { vtssOspf6StatusDbLinkEntry 10 }

vtssOspf6StatusDbLinkLinkLocalAddress OBJECT-TYPE
    SYNTAX      InetAddressIPv6
    MAX-ACCESS  read-only
    STATUS      current
    DESCRIPTION
        "The Link Local Address of the LSA."
    ::= { vtssOspf6StatusDbLinkEntry 11 }

vtssOspf6StatusDbLinkPrefixCnt OBJECT-TYPE
    SYNTAX      Unsigned32
    MAX-ACCESS  read-only
    STATUS      current
    DESCRIPTION
        "The count of the LSA."
    ::= { vtssOspf6StatusDbLinkEntry 12 }

vtssOspf6StatusDbintraAreaPrefixTable OBJECT-TYPE
    SYNTAX      SEQUENCE OF VTSSOspf6StatusDbintraAreaPrefixEntry
    MAX-ACCESS  not-accessible
    STATUS      current
    DESCRIPTION
        "The OSPF6 LSA Link link state database information table."
    ::= { vtssOspf6Status 18 }

vtssOspf6StatusDbintraAreaPrefixEntry OBJECT-TYPE
    SYNTAX      VTSSOspf6StatusDbintraAreaPrefixEntry
    MAX-ACCESS  not-accessible
    STATUS      current
    DESCRIPTION
        "Each row contains the corresponding information of a single link state
         advertisement."
    INDEX       { vtssOspf6StatusDbintraAreaPrefixInstanceId,
                  vtssOspf6StatusDbintraAreaPrefixAreaId,
                  vtssOspf6StatusDbintraAreaPrefixLsdbType,
                  vtssOspf6StatusDbintraAreaPrefixLinkStateId,
                  vtssOspf6StatusDbintraAreaPrefixAdvRouterId }
    ::= { vtssOspf6StatusDbintraAreaPrefixTable 1 }

VTSSOspf6StatusDbintraAreaPrefixEntry ::= SEQUENCE {
    vtssOspf6StatusDbintraAreaPrefixInstanceId        Integer32,
    vtssOspf6StatusDbintraAreaPrefixAreaId            IpAddress,
    vtssOspf6StatusDbintraAreaPrefixLsdbType          VTSSOspf6LsdbType,
    vtssOspf6StatusDbintraAreaPrefixLinkStateId       IpAddress,
    vtssOspf6StatusDbintraAreaPrefixAdvRouterId       IpAddress,
    vtssOspf6StatusDbintraAreaPrefixAge               Unsigned32,
    vtssOspf6StatusDbintraAreaPrefixOptions           Unsigned32,
    vtssOspf6StatusDbintraAreaPrefixSequence          Unsigned32,
    vtssOspf6StatusDbintraAreaPrefixChecksum          Unsigned32,
    vtssOspf6StatusDbintraAreaPrefixLength            Unsigned32,
    vtssOspf6StatusDbintraAreaPrefixLinkLocalAddress  InetAddressIPv6,
    vtssOspf6StatusDbintraAreaPrefixPrefixCnt         Unsigned32
}

vtssOspf6StatusDbintraAreaPrefixInstanceId OBJECT-TYPE
    SYNTAX      Integer32 (1..1)
    MAX-ACCESS  accessible-for-notify
    STATUS      current
    DESCRIPTION
        "The OSPF6 process instance ID."
    ::= { vtssOspf6StatusDbintraAreaPrefixEntry 1 }

vtssOspf6StatusDbintraAreaPrefixAreaId OBJECT-TYPE
    SYNTAX      IpAddress
    MAX-ACCESS  accessible-for-notify
    STATUS      current
    DESCRIPTION
        "The OSPF6 area ID."
    ::= { vtssOspf6StatusDbintraAreaPrefixEntry 2 }

vtssOspf6StatusDbintraAreaPrefixLsdbType OBJECT-TYPE
    SYNTAX      VTSSOspf6LsdbType
    MAX-ACCESS  accessible-for-notify
    STATUS      current
    DESCRIPTION
        "The type of the link state advertisement."
    ::= { vtssOspf6StatusDbintraAreaPrefixEntry 3 }

vtssOspf6StatusDbintraAreaPrefixLinkStateId OBJECT-TYPE
    SYNTAX      IpAddress
    MAX-ACCESS  accessible-for-notify
    STATUS      current
    DESCRIPTION
        "The OSPF6 link state ID."
    ::= { vtssOspf6StatusDbintraAreaPrefixEntry 4 }

vtssOspf6StatusDbintraAreaPrefixAdvRouterId OBJECT-TYPE
    SYNTAX      IpAddress
    MAX-ACCESS  accessible-for-notify
    STATUS      current
    DESCRIPTION
        "The advertising router ID which originated the LSA."
    ::= { vtssOspf6StatusDbintraAreaPrefixEntry 5 }

vtssOspf6StatusDbintraAreaPrefixAge OBJECT-TYPE
    SYNTAX      Unsigned32
    MAX-ACCESS  read-only
    STATUS      current
    DESCRIPTION
        "The time in seconds since the LSA was originated."
    ::= { vtssOspf6StatusDbintraAreaPrefixEntry 6 }

vtssOspf6StatusDbintraAreaPrefixOptions OBJECT-TYPE
    SYNTAX      Unsigned32
    MAX-ACCESS  read-only
    STATUS      current
    DESCRIPTION
        "The OSPF6 option field which is present in OSPF6 hello packets, which
         enables OSPF6 routers to support (or not support) optional
         capabilities, and to communicate their capability level to other OSPF6
         routers."
    ::= { vtssOspf6StatusDbintraAreaPrefixEntry 7 }

vtssOspf6StatusDbintraAreaPrefixSequence OBJECT-TYPE
    SYNTAX      Unsigned32
    MAX-ACCESS  read-only
    STATUS      current
    DESCRIPTION
        "The LS sequence number of the LSA."
    ::= { vtssOspf6StatusDbintraAreaPrefixEntry 8 }

vtssOspf6StatusDbintraAreaPrefixChecksum OBJECT-TYPE
    SYNTAX      Unsigned32
    MAX-ACCESS  read-only
    STATUS      current
    DESCRIPTION
        "The checksum of the LSA contents."
    ::= { vtssOspf6StatusDbintraAreaPrefixEntry 9 }

vtssOspf6StatusDbintraAreaPrefixLength OBJECT-TYPE
    SYNTAX      Unsigned32
    MAX-ACCESS  read-only
    STATUS      current
    DESCRIPTION
        "The Length in bytes of the LSA."
    ::= { vtssOspf6StatusDbintraAreaPrefixEntry 10 }

vtssOspf6StatusDbintraAreaPrefixLinkLocalAddress OBJECT-TYPE
    SYNTAX      InetAddressIPv6
    MAX-ACCESS  read-only
    STATUS      current
    DESCRIPTION
        "The Link Local Address of the LSA."
    ::= { vtssOspf6StatusDbintraAreaPrefixEntry 11 }

vtssOspf6StatusDbintraAreaPrefixPrefixCnt OBJECT-TYPE
    SYNTAX      Unsigned32
    MAX-ACCESS  read-only
    STATUS      current
    DESCRIPTION
        "The count of the LSA."
    ::= { vtssOspf6StatusDbintraAreaPrefixEntry 12 }

vtssOspf6Control OBJECT IDENTIFIER
    ::= { vtssOspf6MibObjects 4 }

vtssOspf6ControlGlobals OBJECT IDENTIFIER
    ::= { vtssOspf6Control 4 }

vtssOspf6ControlGlobalsReloadProcess OBJECT-TYPE
    SYNTAX      TruthValue
    MAX-ACCESS  read-write
    STATUS      current
    DESCRIPTION
        "Set true to reload OSPF6 process."
    ::= { vtssOspf6ControlGlobals 1 }

vtssOspf6MibConformance OBJECT IDENTIFIER
    ::= { vtssOspf6Mib 2 }

vtssOspf6MibCompliances OBJECT IDENTIFIER
    ::= { vtssOspf6MibConformance 1 }

vtssOspf6MibGroups OBJECT IDENTIFIER
    ::= { vtssOspf6MibConformance 2 }

vtssOspf6CapabilitiesInfoGroup OBJECT-GROUP
    OBJECTS     { vtssOspf6CapabilitiesMinInstanceId,
                  vtssOspf6CapabilitiesMaxInstanceId,
                  vtssOspf6CapabilitiesMinRouterId,
                  vtssOspf6CapabilitiesMaxRouterId,
                  vtssOspf6CapabilitiesMinPriority,
                  vtssOspf6CapabilitiesMaxPriority,
                  vtssOspf6CapabilitiesMinGeneralCost,
                  vtssOspf6CapabilitiesMaxGeneralCost,
                  vtssOspf6CapabilitiesMinInterfaceCost,
                  vtssOspf6CapabilitiesMaxInterfaceCost,
                  vtssOspf6CapabilitiesMinHelloInterval,
                  vtssOspf6CapabilitiesMaxHelloInterval,
                  vtssOspf6CapabilitiesMinRetransmitInterval,
                  vtssOspf6CapabilitiesMaxRetransmitInterval,
                  vtssOspf6CapabilitiesMinDeadInterval,
                  vtssOspf6CapabilitiesMaxDeadInterval,
                  vtssOspf6CapabilitiesIsRipngRedistributedSupported,
                  vtssOspf6CapabilitiesMinAdminDistance,
                  vtssOspf6CapabilitiesMaxAdminDistance }
    STATUS      current
    DESCRIPTION
        "A collection of objects."
    ::= { vtssOspf6MibGroups 1 }

vtssOspf6ConfigProcessTableInfoGroup OBJECT-GROUP
    OBJECTS     { vtssOspf6ConfigProcessInstanceId,
                  vtssOspf6ConfigProcessAction }
    STATUS      current
    DESCRIPTION
        "A collection of objects."
    ::= { vtssOspf6MibGroups 2 }

vtssOspf6ConfigProcessTableRowEditorInfoGroup OBJECT-GROUP
    OBJECTS     { vtssOspf6ConfigProcessTableRowEditorInstanceId,
                  vtssOspf6ConfigProcessTableRowEditorAction }
    STATUS      current
    DESCRIPTION
        "A collection of objects."
    ::= { vtssOspf6MibGroups 3 }

vtssOspf6ConfigRouterTableInfoGroup OBJECT-GROUP
    OBJECTS     { vtssOspf6ConfigRouterInstanceId,
                  vtssOspf6ConfigRouterIsSpecificRouterId,
                  vtssOspf6ConfigRouterRouterId,
                  vtssOspf6ConfigRouterConnectedRedistEnable,
                  vtssOspf6ConfigRouterStaticRedistEnable,
                  vtssOspf6ConfigRouterAdminDistance }
    STATUS      current
    DESCRIPTION
        "A collection of objects."
    ::= { vtssOspf6MibGroups 4 }

vtssOspf6ConfigRouterInterfaceTableInfoGroup OBJECT-GROUP
    OBJECTS     { vtssOspf6ConfigRouterInterfaceInstanceId,
                  vtssOspf6ConfigRouterInterfaceIfIndex,
                  vtssOspf6ConfigRouterInterfaceIsSpecificAreaId,
                  vtssOspf6ConfigRouterInterfaceAreaId }
    STATUS      current
    DESCRIPTION
        "A collection of objects."
    ::= { vtssOspf6MibGroups 5 }

vtssOspf6ConfigAreaRangeTableInfoGroup OBJECT-GROUP
    OBJECTS     { vtssOspf6ConfigAreaRangeInstanceId,
                  vtssOspf6ConfigAreaRangeAreaId,
                  vtssOspf6ConfigAreaRangeNetwork,
                  vtssOspf6ConfigAreaRangeIpSubnetMaskLength,
                  vtssOspf6ConfigAreaRangeAdvertised,
                  vtssOspf6ConfigAreaRangeIsSpecificCost,
                  vtssOspf6ConfigAreaRangeCost,
                  vtssOspf6ConfigAreaRangeAction }
    STATUS      current
    DESCRIPTION
        "A collection of objects."
    ::= { vtssOspf6MibGroups 6 }

vtssOspf6ConfigAreaRangeTableRowEditorInfoGroup OBJECT-GROUP
    OBJECTS     { vtssOspf6ConfigAreaRangeTableRowEditorInstanceId,
                  vtssOspf6ConfigAreaRangeTableRowEditorAreaId,
                  vtssOspf6ConfigAreaRangeTableRowEditorNetwork,
                  vtssOspf6ConfigAreaRangeTableRowEditorIpSubnetMaskLength,
                  vtssOspf6ConfigAreaRangeTableRowEditorAdvertised,
                  vtssOspf6ConfigAreaRangeTableRowEditorIsSpecificCost,
                  vtssOspf6ConfigAreaRangeTableRowEditorCost,
                  vtssOspf6ConfigAreaRangeTableRowEditorAction }
    STATUS      current
    DESCRIPTION
        "A collection of objects."
    ::= { vtssOspf6MibGroups 7 }

vtssOspf6ConfigStubAreaTableInfoGroup OBJECT-GROUP
    OBJECTS     { vtssOspf6ConfigStubAreaInstanceId,
                  vtssOspf6ConfigStubAreaAreaId,
                  vtssOspf6ConfigStubAreaNoSummary,
                  vtssOspf6ConfigStubAreaAction }
    STATUS      current
    DESCRIPTION
        "A collection of objects."
    ::= { vtssOspf6MibGroups 8 }

vtssOspf6ConfigStubAreaTableRowEditorInfoGroup OBJECT-GROUP
    OBJECTS     { vtssOspf6ConfigStubAreaTableRowEditorInstanceId,
                  vtssOspf6ConfigStubAreaTableRowEditorAreaId,
                  vtssOspf6ConfigStubAreaTableRowEditorNoSummary,
                  vtssOspf6ConfigStubAreaTableRowEditorAction }
    STATUS      current
    DESCRIPTION
        "A collection of objects."
    ::= { vtssOspf6MibGroups 9 }

vtssOspf6ConfigInterfaceTableInfoGroup OBJECT-GROUP
    OBJECTS     { vtssOspf6ConfigInterfaceIfIndex,
                  vtssOspf6ConfigInterfacePriority,
                  vtssOspf6ConfigInterfaceIsSpecificCost,
                  vtssOspf6ConfigInterfaceCost,
                  vtssOspf6ConfigInterfaceDeadInterval,
                  vtssOspf6ConfigInterfaceHelloInterval,
                  vtssOspf6ConfigInterfaceRetransmitInterval,
                  vtssOspf6ConfigInterfaceIsPassiveInterface,
                  vtssOspf6ConfigInterfaceTransmitDelay,
                  vtssOspf6ConfigInterfaceMtuIgnore }
    STATUS      current
    DESCRIPTION
        "A collection of objects."
    ::= { vtssOspf6MibGroups 10 }

vtssOspf6StatusRouterTableInfoGroup OBJECT-GROUP
    OBJECTS     { vtssOspf6StatusRouterInstanceId,
                  vtssOspf6StatusRouterRouterId,
                  vtssOspf6StatusRouterSpfDelay,
                  vtssOspf6StatusRouterSpfHoldTime,
                  vtssOspf6StatusRouterSpfMaxWaitTime,
                  vtssOspf6StatusRouterLastExcutedSpfTs,
                  vtssOspf6StatusRouterAttachedAreaCount }
    STATUS      current
    DESCRIPTION
        "A collection of objects."
    ::= { vtssOspf6MibGroups 11 }

vtssOspf6StatusRouteAreaTableInfoGroup OBJECT-GROUP
    OBJECTS     { vtssOspf6StatusRouteAreaInstanceId,
                  vtssOspf6StatusRouteAreaAreaId,
                  vtssOspf6StatusRouteAreaIsBackbone,
                  vtssOspf6StatusRouteAreaAreaType,
                  vtssOspf6StatusRouteAreaAttachedIntfCount,
                  vtssOspf6StatusRouteAreaSpfExecutedCount,
                  vtssOspf6StatusRouteAreaLsaCount }
    STATUS      current
    DESCRIPTION
        "A collection of objects."
    ::= { vtssOspf6MibGroups 12 }

vtssOspf6StatusInterfaceTableInfoGroup OBJECT-GROUP
    OBJECTS     { vtssOspf6StatusInterfaceIfIndex,
                  vtssOspf6StatusInterfaceStatus,
                  vtssOspf6StatusInterfacePassive,
                  vtssOspf6StatusInterfaceNetwork,
                  vtssOspf6StatusInterfaceIpSubnetMaskLength,
                  vtssOspf6StatusInterfaceAreaId,
                  vtssOspf6StatusInterfaceRouterId,
                  vtssOspf6StatusInterfaceCost,
                  vtssOspf6StatusInterfaceState,
                  vtssOspf6StatusInterfacePriority,
                  vtssOspf6StatusInterfaceDrId,
                  vtssOspf6StatusInterfaceBdrId,
                  vtssOspf6StatusInterfaceHelloTime,
                  vtssOspf6StatusInterfaceDeadTime,
                  vtssOspf6StatusInterfaceRetransmitTime,
                  vtssOspf6StatusInterfaceTransmitDelay }
    STATUS      current
    DESCRIPTION
        "A collection of objects."
    ::= { vtssOspf6MibGroups 13 }

vtssOspf6StatusNeighborIpv6TableInfoGroup OBJECT-GROUP
    OBJECTS     { vtssOspf6StatusNeighborIpv6InstanceId,
                  vtssOspf6StatusNeighborIpv6RouterId,
                  vtssOspf6StatusNeighborIpv6Ipv6Addr,
                  vtssOspf6StatusNeighborIpv6IfIndex,
                  vtssOspf6StatusNeighborIpv6IpAddr,
                  vtssOspf6StatusNeighborIpv6AreaId,
                  vtssOspf6StatusNeighborIpv6NeighborId,
                  vtssOspf6StatusNeighborIpv6Priority,
                  vtssOspf6StatusNeighborIpv6State,
                  vtssOspf6StatusNeighborIpv6DrId,
                  vtssOspf6StatusNeighborIpv6BdrId,
                  vtssOspf6StatusNeighborIpv6DeadTime,
                  vtssOspf6StatusNeighborIpv6TransitAreaId }
    STATUS      current
    DESCRIPTION
        "A collection of objects."
    ::= { vtssOspf6MibGroups 14 }

vtssOspf6StatusRouteIpv6TableInfoGroup OBJECT-GROUP
    OBJECTS     { vtssOspf6StatusRouteIpv6InstanceId,
                  vtssOspf6StatusRouteIpv6RouteType,
                  vtssOspf6StatusRouteIpv6Network,
                  vtssOspf6StatusRouteIpv6IpSubnetMaskLength,
                  vtssOspf6StatusRouteIpv6AreaId,
                  vtssOspf6StatusRouteIpv6NextHop,
                  vtssOspf6StatusRouteIpv6Cost,
                  vtssOspf6StatusRouteIpv6AsCost,
                  vtssOspf6StatusRouteIpv6BorderRouterType,
                  vtssOspf6StatusRouteIpv6Ifindex,
                  vtssOspf6StatusRouteIpv6IsConnected }
    STATUS      current
    DESCRIPTION
        "A collection of objects."
    ::= { vtssOspf6MibGroups 15 }

vtssOspf6StatusDbTableInfoGroup OBJECT-GROUP
    OBJECTS     { vtssOspf6StatusDbInstanceId,
                  vtssOspf6StatusDbAreaId, vtssOspf6StatusDbLsdbType,
                  vtssOspf6StatusDbLinkStateId,
                  vtssOspf6StatusDbAdvRouterId, vtssOspf6StatusDbAge,
                  vtssOspf6StatusDbSequence,
                  vtssOspf6StatusDbRouterLinkCount }
    STATUS      current
    DESCRIPTION
        "A collection of objects."
    ::= { vtssOspf6MibGroups 16 }

vtssOspf6StatusDbRouterTableInfoGroup OBJECT-GROUP
    OBJECTS     { vtssOspf6StatusDbRouterInstanceId,
                  vtssOspf6StatusDbRouterAreaId,
                  vtssOspf6StatusDbRouterLsdbType,
                  vtssOspf6StatusDbRouterLinkStateId,
                  vtssOspf6StatusDbRouterAdvRouterId,
                  vtssOspf6StatusDbRouterAge,
                  vtssOspf6StatusDbRouterOptions,
                  vtssOspf6StatusDbRouterSequence,
                  vtssOspf6StatusDbRouterChecksum,
                  vtssOspf6StatusDbRouterLength,
                  vtssOspf6StatusDbRouterRouterLinkCount }
    STATUS      current
    DESCRIPTION
        "A collection of objects."
    ::= { vtssOspf6MibGroups 17 }

vtssOspf6StatusDbNetworkTableInfoGroup OBJECT-GROUP
    OBJECTS     { vtssOspf6StatusDbNetworkInstanceId,
                  vtssOspf6StatusDbNetworkAreaId,
                  vtssOspf6StatusDbNetworkLsdbType,
                  vtssOspf6StatusDbNetworkLinkStateId,
                  vtssOspf6StatusDbNetworkAdvRouterId,
                  vtssOspf6StatusDbNetworkAge,
                  vtssOspf6StatusDbNetworkOptions,
                  vtssOspf6StatusDbNetworkSequence,
                  vtssOspf6StatusDbNetworkChecksum,
                  vtssOspf6StatusDbNetworkLength,
                  vtssOspf6StatusDbNetworkAttachedRouterCount }
    STATUS      current
    DESCRIPTION
        "A collection of objects."
    ::= { vtssOspf6MibGroups 18 }

vtssOspf6StatusDbInterAreaPrefixTableInfoGroup OBJECT-GROUP
    OBJECTS     { vtssOspf6StatusDbInterAreaPrefixInstanceId,
                  vtssOspf6StatusDbInterAreaPrefixAreaId,
                  vtssOspf6StatusDbInterAreaPrefixLsdbType,
                  vtssOspf6StatusDbInterAreaPrefixLinkStateId,
                  vtssOspf6StatusDbInterAreaPrefixAdvRouterId,
                  vtssOspf6StatusDbInterAreaPrefixAge,
                  vtssOspf6StatusDbInterAreaPrefixOptions,
                  vtssOspf6StatusDbInterAreaPrefixSequence,
                  vtssOspf6StatusDbInterAreaPrefixChecksum,
                  vtssOspf6StatusDbInterAreaPrefixLength,
                  vtssOspf6StatusDbInterAreaPrefixPrefixAddress,
                  vtssOspf6StatusDbInterAreaPrefixIpSubnetMaskLength,
                  vtssOspf6StatusDbInterAreaPrefixMetric }
    STATUS      current
    DESCRIPTION
        "A collection of objects."
    ::= { vtssOspf6MibGroups 19 }

vtssOspf6StatusDbInterAreaRouterTableInfoGroup OBJECT-GROUP
    OBJECTS     { vtssOspf6StatusDbInterAreaRouterInstanceId,
                  vtssOspf6StatusDbInterAreaRouterAreaId,
                  vtssOspf6StatusDbInterAreaRouterLsdbType,
                  vtssOspf6StatusDbInterAreaRouterLinkStateId,
                  vtssOspf6StatusDbInterAreaRouterAdvRouterId,
                  vtssOspf6StatusDbInterAreaRouterAge,
                  vtssOspf6StatusDbInterAreaRouterOptions,
                  vtssOspf6StatusDbInterAreaRouterSequence,
                  vtssOspf6StatusDbInterAreaRouterChecksum,
                  vtssOspf6StatusDbInterAreaRouterLength,
                  vtssOspf6StatusDbInterAreaRouterMetric }
    STATUS      current
    DESCRIPTION
        "A collection of objects."
    ::= { vtssOspf6MibGroups 20 }

vtssOspf6StatusDbExternalTableInfoGroup OBJECT-GROUP
    OBJECTS     { vtssOspf6StatusDbExternalInstanceId,
                  vtssOspf6StatusDbExternalAreaId,
                  vtssOspf6StatusDbExternalLsdbType,
                  vtssOspf6StatusDbExternalLinkStateId,
                  vtssOspf6StatusDbExternalAdvRouterId,
                  vtssOspf6StatusDbExternalAge,
                  vtssOspf6StatusDbExternalOptions,
                  vtssOspf6StatusDbExternalSequence,
                  vtssOspf6StatusDbExternalChecksum,
                  vtssOspf6StatusDbExternalLength,
                  vtssOspf6StatusDbExternalPrefixAddress,
                  vtssOspf6StatusDbExternalIpSubnetMaskLength,
                  vtssOspf6StatusDbExternalMetric,
                  vtssOspf6StatusDbExternalMetricType,
                  vtssOspf6StatusDbExternalForwardAddress }
    STATUS      current
    DESCRIPTION
        "A collection of objects."
    ::= { vtssOspf6MibGroups 21 }

vtssOspf6StatusDbLinkTableInfoGroup OBJECT-GROUP
    OBJECTS     { vtssOspf6StatusDbLinkInstanceId,
                  vtssOspf6StatusDbLinkAreaId,
                  vtssOspf6StatusDbLinkLsdbType,
                  vtssOspf6StatusDbLinkLinkStateId,
                  vtssOspf6StatusDbLinkAdvRouterId,
                  vtssOspf6StatusDbLinkAge,
                  vtssOspf6StatusDbLinkOptions,
                  vtssOspf6StatusDbLinkSequence,
                  vtssOspf6StatusDbLinkChecksum,
                  vtssOspf6StatusDbLinkLength,
                  vtssOspf6StatusDbLinkLinkLocalAddress,
                  vtssOspf6StatusDbLinkPrefixCnt }
    STATUS      current
    DESCRIPTION
        "A collection of objects."
    ::= { vtssOspf6MibGroups 22 }

vtssOspf6StatusDbintraAreaPrefixTableInfoGroup OBJECT-GROUP
    OBJECTS     { vtssOspf6StatusDbintraAreaPrefixInstanceId,
                  vtssOspf6StatusDbintraAreaPrefixAreaId,
                  vtssOspf6StatusDbintraAreaPrefixLsdbType,
                  vtssOspf6StatusDbintraAreaPrefixLinkStateId,
                  vtssOspf6StatusDbintraAreaPrefixAdvRouterId,
                  vtssOspf6StatusDbintraAreaPrefixAge,
                  vtssOspf6StatusDbintraAreaPrefixOptions,
                  vtssOspf6StatusDbintraAreaPrefixSequence,
                  vtssOspf6StatusDbintraAreaPrefixChecksum,
                  vtssOspf6StatusDbintraAreaPrefixLength,
                  vtssOspf6StatusDbintraAreaPrefixLinkLocalAddress,
                  vtssOspf6StatusDbintraAreaPrefixPrefixCnt }
    STATUS      current
    DESCRIPTION
        "A collection of objects."
    ::= { vtssOspf6MibGroups 23 }

vtssOspf6ControlGlobalsInfoGroup OBJECT-GROUP
    OBJECTS     { vtssOspf6ControlGlobalsReloadProcess }
    STATUS      current
    DESCRIPTION
        "A collection of objects."
    ::= { vtssOspf6MibGroups 24 }

vtssOspf6MibCompliance MODULE-COMPLIANCE
    STATUS      current
    DESCRIPTION
        "The compliance statement for the implementation."

    MODULE      -- this module

    MANDATORY-GROUPS { vtssOspf6CapabilitiesInfoGroup,
                       vtssOspf6ConfigProcessTableInfoGroup,
                       vtssOspf6ConfigProcessTableRowEditorInfoGroup,
                       vtssOspf6ConfigRouterTableInfoGroup,
                       vtssOspf6ConfigRouterInterfaceTableInfoGroup,
                       vtssOspf6ConfigAreaRangeTableInfoGroup,
                       vtssOspf6ConfigAreaRangeTableRowEditorInfoGroup,
                       vtssOspf6ConfigStubAreaTableInfoGroup,
                       vtssOspf6ConfigStubAreaTableRowEditorInfoGroup,
                       vtssOspf6ConfigInterfaceTableInfoGroup,
                       vtssOspf6StatusRouterTableInfoGroup,
                       vtssOspf6StatusRouteAreaTableInfoGroup,
                       vtssOspf6StatusInterfaceTableInfoGroup,
                       vtssOspf6StatusNeighborIpv6TableInfoGroup,
                       vtssOspf6StatusRouteIpv6TableInfoGroup,
                       vtssOspf6StatusDbTableInfoGroup,
                       vtssOspf6StatusDbRouterTableInfoGroup,
                       vtssOspf6StatusDbNetworkTableInfoGroup,
                       vtssOspf6StatusDbInterAreaPrefixTableInfoGroup,
                       vtssOspf6StatusDbInterAreaRouterTableInfoGroup,
                       vtssOspf6StatusDbExternalTableInfoGroup,
                       vtssOspf6StatusDbLinkTableInfoGroup,
                       vtssOspf6StatusDbintraAreaPrefixTableInfoGroup,
                       vtssOspf6ControlGlobalsInfoGroup }

    ::= { vtssOspf6MibCompliances 1 }

END
