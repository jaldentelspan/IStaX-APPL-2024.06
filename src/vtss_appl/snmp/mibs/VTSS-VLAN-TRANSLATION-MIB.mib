-- *****************************************************************
-- VLAN-TRANSLATION-MIB:  Microsemi ENT private MIB
-- ****************************************************************

VTSS-VLAN-TRANSLATION-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    Unsigned32 FROM SNMPv2-SMI
    VTSSInterfaceIndex FROM VTSS-TC
    VTSSRowEditorState FROM VTSS-TC
    ;

vtssVlanTranslationMib MODULE-IDENTITY
    LAST-UPDATED "201710250000Z"
    ORGANIZATION
        "Microsemi Corporation"
    CONTACT-INFO
        "Application support: http://www.microchip.com/support"
    DESCRIPTION
        "Private VLAN TRANSLATION MIB."
    REVISION    "201710250000Z"
    DESCRIPTION
        "Added unidirectional translation"
    REVISION    "201406300000Z"
    DESCRIPTION
        "Initial version"
    ::= { vtssSwitchMgmt 85 }


VTSSVlanTranslationDir ::= TEXTUAL-CONVENTION
    STATUS      current
    DESCRIPTION
        "The VLAN Translation Direction."
    SYNTAX      INTEGER { both(0), ingress(1), egress(2) }

vtssVlanTranslationMibObjects OBJECT IDENTIFIER
    ::= { vtssVlanTranslationMib 1 }

vtssVlanTranslationCapabilities OBJECT IDENTIFIER
    ::= { vtssVlanTranslationMibObjects 1 }

vtssVlanTranslationCapabilitiesMaxNumberOfTranslations OBJECT-TYPE
    SYNTAX      Unsigned32
    MAX-ACCESS  read-only
    STATUS      current
    DESCRIPTION
        "Maximum number of VLAN translation mappings the user can store in the
         VLAN Translation mapping table."
    ::= { vtssVlanTranslationCapabilities 1 }

vtssVlanTranslationConfig OBJECT IDENTIFIER
    ::= { vtssVlanTranslationMibObjects 2 }

vtssVlanTranslationConfigTranslation OBJECT IDENTIFIER
    ::= { vtssVlanTranslationConfig 1 }

vtssVlanTranslationConfigTranslationTable OBJECT-TYPE
    SYNTAX      SEQUENCE OF VTSSVlanTranslationConfigTranslationEntry
    MAX-ACCESS  not-accessible
    STATUS      current
    DESCRIPTION
        "This is the VLAN translation mapping table.
         
         Here the user stores VLAN translation mappings (VID->TVID) inside
         groups that can later be activated on specific switch interfaces"
    ::= { vtssVlanTranslationConfigTranslation 1 }

vtssVlanTranslationConfigTranslationEntry OBJECT-TYPE
    SYNTAX      VTSSVlanTranslationConfigTranslationEntry
    MAX-ACCESS  not-accessible
    STATUS      current
    DESCRIPTION
        "Each entry in this table represents a VLAN translation mapping stored
         inside a specific VLAN translation Group.
         
         The entry key is the Group ID and the source VLAN ID, while the value
         is the translated VID.
         
         "
    INDEX       { vtssVlanTranslationConfigTranslationGroupId,
                  vtssVlanTranslationConfigTranslationDirection,
                  vtssVlanTranslationConfigTranslationVlanId }
    ::= { vtssVlanTranslationConfigTranslationTable 1 }

VTSSVlanTranslationConfigTranslationEntry ::= SEQUENCE {
    vtssVlanTranslationConfigTranslationGroupId    Integer32,
    vtssVlanTranslationConfigTranslationDirection  VTSSVlanTranslationDir,
    vtssVlanTranslationConfigTranslationVlanId     Integer32,
    vtssVlanTranslationConfigTranslationTVlanId    Integer32,
    vtssVlanTranslationConfigTranslationAction     VTSSRowEditorState
}

vtssVlanTranslationConfigTranslationGroupId OBJECT-TYPE
    SYNTAX      Integer32 (1..65535)
    MAX-ACCESS  accessible-for-notify
    STATUS      current
    DESCRIPTION
        "Group ID of the VLAN translation mapping key."
    ::= { vtssVlanTranslationConfigTranslationEntry 1 }

vtssVlanTranslationConfigTranslationDirection OBJECT-TYPE
    SYNTAX      VTSSVlanTranslationDir
    MAX-ACCESS  accessible-for-notify
    STATUS      current
    DESCRIPTION
        "The VLAN Translation Direction."
    ::= { vtssVlanTranslationConfigTranslationEntry 2 }

vtssVlanTranslationConfigTranslationVlanId OBJECT-TYPE
    SYNTAX      Integer32 (1..4095)
    MAX-ACCESS  accessible-for-notify
    STATUS      current
    DESCRIPTION
        "Vlan ID of the VLAN translation mapping key."
    ::= { vtssVlanTranslationConfigTranslationEntry 3 }

vtssVlanTranslationConfigTranslationTVlanId OBJECT-TYPE
    SYNTAX      Integer32 (1..4095)
    MAX-ACCESS  read-write
    STATUS      current
    DESCRIPTION
        "Translated VLAN ID of the VLAN translation mapping."
    ::= { vtssVlanTranslationConfigTranslationEntry 4 }

vtssVlanTranslationConfigTranslationAction OBJECT-TYPE
    SYNTAX      VTSSRowEditorState
    MAX-ACCESS  read-write
    STATUS      current
    DESCRIPTION
        "Action"
    ::= { vtssVlanTranslationConfigTranslationEntry 100 }

vtssVlanTranslationConfigTranslationRowEditor OBJECT IDENTIFIER
    ::= { vtssVlanTranslationConfigTranslation 2 }

vtssVlanTranslationConfigTranslationRowEditorGroupId OBJECT-TYPE
    SYNTAX      Integer32 (1..65535)
    MAX-ACCESS  read-write
    STATUS      current
    DESCRIPTION
        "Group ID of the VLAN translation mapping key."
    ::= { vtssVlanTranslationConfigTranslationRowEditor 1 }

vtssVlanTranslationConfigTranslationRowEditorDirection OBJECT-TYPE
    SYNTAX      VTSSVlanTranslationDir
    MAX-ACCESS  read-write
    STATUS      current
    DESCRIPTION
        "The VLAN Translation Direction."
    ::= { vtssVlanTranslationConfigTranslationRowEditor 2 }

vtssVlanTranslationConfigTranslationRowEditorVlanId OBJECT-TYPE
    SYNTAX      Integer32 (1..4095)
    MAX-ACCESS  read-write
    STATUS      current
    DESCRIPTION
        "Vlan ID of the VLAN translation mapping key."
    ::= { vtssVlanTranslationConfigTranslationRowEditor 3 }

vtssVlanTranslationConfigTranslationRowEditorTVlanId OBJECT-TYPE
    SYNTAX      Integer32 (1..4095)
    MAX-ACCESS  read-write
    STATUS      current
    DESCRIPTION
        "Translated VLAN ID of the VLAN translation mapping."
    ::= { vtssVlanTranslationConfigTranslationRowEditor 4 }

vtssVlanTranslationConfigTranslationRowEditorAction OBJECT-TYPE
    SYNTAX      VTSSRowEditorState
    MAX-ACCESS  read-write
    STATUS      current
    DESCRIPTION
        "Action"
    ::= { vtssVlanTranslationConfigTranslationRowEditor 100 }

vtssVlanTranslationConfigInterfaces OBJECT IDENTIFIER
    ::= { vtssVlanTranslationConfig 2 }

vtssVlanTranslationConfigInterfacesIfTable OBJECT-TYPE
    SYNTAX      SEQUENCE OF VTSSVlanTranslationConfigInterfacesIfEntry
    MAX-ACCESS  not-accessible
    STATUS      current
    DESCRIPTION
        "This is the VLAN translation interface table. The number of interfaces
         is the total number of ports available on the switch. Each one of these
         interfaces can be set to use a specific Group of VLAN translation
         mappings, identified by the respective Group ID."
    ::= { vtssVlanTranslationConfigInterfaces 1 }

vtssVlanTranslationConfigInterfacesIfEntry OBJECT-TYPE
    SYNTAX      VTSSVlanTranslationConfigInterfacesIfEntry
    MAX-ACCESS  not-accessible
    STATUS      current
    DESCRIPTION
        "Entries in this table represent switch interfaces and their matching
         VLAN translation Groups (identified through their Group IDs)"
    INDEX       { vtssVlanTranslationConfigInterfacesIfIfIndex }
    ::= { vtssVlanTranslationConfigInterfacesIfTable 1 }

VTSSVlanTranslationConfigInterfacesIfEntry ::= SEQUENCE {
    vtssVlanTranslationConfigInterfacesIfIfIndex  VTSSInterfaceIndex,
    vtssVlanTranslationConfigInterfacesIfGroupId  Integer32
}

vtssVlanTranslationConfigInterfacesIfIfIndex OBJECT-TYPE
    SYNTAX      VTSSInterfaceIndex
    MAX-ACCESS  accessible-for-notify
    STATUS      current
    DESCRIPTION
        "Interface index number."
    ::= { vtssVlanTranslationConfigInterfacesIfEntry 1 }

vtssVlanTranslationConfigInterfacesIfGroupId OBJECT-TYPE
    SYNTAX      Integer32 (1..65535)
    MAX-ACCESS  read-write
    STATUS      current
    DESCRIPTION
        "Group ID of the interface configuration."
    ::= { vtssVlanTranslationConfigInterfacesIfEntry 2 }

vtssVlanTranslationMibConformance OBJECT IDENTIFIER
    ::= { vtssVlanTranslationMib 2 }

vtssVlanTranslationMibCompliances OBJECT IDENTIFIER
    ::= { vtssVlanTranslationMibConformance 1 }

vtssVlanTranslationMibGroups OBJECT IDENTIFIER
    ::= { vtssVlanTranslationMibConformance 2 }

vtssVlanTranslationCapabilitiesInfoGroup OBJECT-GROUP
    OBJECTS     {                   vtssVlanTranslationCapabilitiesMaxNumberOfTranslations }
    STATUS      current
    DESCRIPTION
        "A collection of objects."
    ::= { vtssVlanTranslationMibGroups 1 }

vtssVlanTranslationConfigTranslationTableInfoGroup OBJECT-GROUP
    OBJECTS     { vtssVlanTranslationConfigTranslationGroupId,
                  vtssVlanTranslationConfigTranslationDirection,
                  vtssVlanTranslationConfigTranslationVlanId,
                  vtssVlanTranslationConfigTranslationTVlanId,
                  vtssVlanTranslationConfigTranslationAction }
    STATUS      current
    DESCRIPTION
        "A collection of objects."
    ::= { vtssVlanTranslationMibGroups 2 }

vtssVlanTranslationConfigTranslationRowEditorInfoGroup OBJECT-GROUP
    OBJECTS     {                   vtssVlanTranslationConfigTranslationRowEditorGroupId,
                  vtssVlanTranslationConfigTranslationRowEditorDirection,
                  vtssVlanTranslationConfigTranslationRowEditorVlanId,
                  vtssVlanTranslationConfigTranslationRowEditorTVlanId,
                  vtssVlanTranslationConfigTranslationRowEditorAction }
    STATUS      current
    DESCRIPTION
        "A collection of objects."
    ::= { vtssVlanTranslationMibGroups 3 }

vtssVlanTranslationConfigInterfacesIfTableInfoGroup OBJECT-GROUP
    OBJECTS     { vtssVlanTranslationConfigInterfacesIfIfIndex,
                  vtssVlanTranslationConfigInterfacesIfGroupId }
    STATUS      current
    DESCRIPTION
        "A collection of objects."
    ::= { vtssVlanTranslationMibGroups 4 }

vtssVlanTranslationMibCompliance MODULE-COMPLIANCE
    STATUS      current
    DESCRIPTION
        "The compliance statement for the implementation."

    MODULE      -- this module

    MANDATORY-GROUPS { vtssVlanTranslationCapabilitiesInfoGroup,
                       vtssVlanTranslationConfigTranslationTableInfoGroup,
                       vtssVlanTranslationConfigTranslationRowEditorInfoGroup,
                       vtssVlanTranslationConfigInterfacesIfTableInfoGroup }

    ::= { vtssVlanTranslationMibCompliances 1 }

END
