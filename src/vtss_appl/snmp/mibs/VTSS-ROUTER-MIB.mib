-- *****************************************************************
-- ROUTER-MIB:  Microsemi ENT private MIB
-- ****************************************************************

VTSS-ROUTER-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    IpAddress FROM SNMPv2-SMI
    Unsigned32 FROM SNMPv2-SMI
    TruthValue FROM SNMPv2-TC
    VTSSDisplayString FROM VTSS-TC
    VTSSRowEditorState FROM VTSS-TC
    ;

vtssRouterMib MODULE-IDENTITY
    LAST-UPDATED "201807270000Z"
    ORGANIZATION
        "Microsemi Corporation"
    CONTACT-INFO
        "Application support: http://www.microchip.com/support"
    DESCRIPTION
        "This is a private version of the ROUTER MIB."
    REVISION    "201807270000Z"
    DESCRIPTION
        "Initial version."
    ::= { vtssSwitchMgmt 153 }


VTSSRouterAccessListMode ::= TEXTUAL-CONVENTION
    STATUS      current
    DESCRIPTION
        "The access right mode of the router access-list entry."
    SYNTAX      INTEGER { deny(0), permit(1) }

vtssRouterMibObjects OBJECT IDENTIFIER
    ::= { vtssRouterMib 1 }

vtssRouterCapabilities OBJECT IDENTIFIER
    ::= { vtssRouterMibObjects 1 }

vtssRouterCapabilitiesMaxKeyChainNameMaxCount OBJECT-TYPE
    SYNTAX      Unsigned32
    MAX-ACCESS  read-only
    STATUS      current
    DESCRIPTION
        "The maximum count of the router key-chain name list"
    ::= { vtssRouterCapabilities 1 }

vtssRouterCapabilitiesMinKeyChainNameLen OBJECT-TYPE
    SYNTAX      Unsigned32
    MAX-ACCESS  read-only
    STATUS      current
    DESCRIPTION
        "The minimum name length of router key chain"
    ::= { vtssRouterCapabilities 2 }

vtssRouterCapabilitiesMaxKeyChainNameLen OBJECT-TYPE
    SYNTAX      Unsigned32
    MAX-ACCESS  read-only
    STATUS      current
    DESCRIPTION
        "The maximum name length of router key chain"
    ::= { vtssRouterCapabilities 3 }

vtssRouterCapabilitiesMinKeyChainKeyId OBJECT-TYPE
    SYNTAX      Unsigned32
    MAX-ACCESS  read-only
    STATUS      current
    DESCRIPTION
        "The minimum value of router key chain key ID"
    ::= { vtssRouterCapabilities 4 }

vtssRouterCapabilitiesMaxKeyChainKeyId OBJECT-TYPE
    SYNTAX      Unsigned32
    MAX-ACCESS  read-only
    STATUS      current
    DESCRIPTION
        "The maximum value of router key chain key ID"
    ::= { vtssRouterCapabilities 5 }

vtssRouterCapabilitiesMinKeyChainPlainTextKeyStringLen OBJECT-TYPE
    SYNTAX      Unsigned32
    MAX-ACCESS  read-only
    STATUS      current
    DESCRIPTION
        "The minimum length of router key chain plain text key string"
    ::= { vtssRouterCapabilities 6 }

vtssRouterCapabilitiesMaxKeyChainPlainTextKeyStringLen OBJECT-TYPE
    SYNTAX      Unsigned32
    MAX-ACCESS  read-only
    STATUS      current
    DESCRIPTION
        "The maximum length of router key chain plain text key string"
    ::= { vtssRouterCapabilities 7 }

vtssRouterCapabilitiesMinKeyChainKeyEncryptedStringLen OBJECT-TYPE
    SYNTAX      Unsigned32
    MAX-ACCESS  read-only
    STATUS      current
    DESCRIPTION
        "The minimum length of router key chain encrypted key string"
    ::= { vtssRouterCapabilities 8 }

vtssRouterCapabilitiesMaxKeyChainKeyEncryptedStringLen OBJECT-TYPE
    SYNTAX      Unsigned32
    MAX-ACCESS  read-only
    STATUS      current
    DESCRIPTION
        "The maximum length of router key chain encrypted key string"
    ::= { vtssRouterCapabilities 9 }

vtssRouterCapabilitiesAccessListMaxCount OBJECT-TYPE
    SYNTAX      Unsigned32
    MAX-ACCESS  read-only
    STATUS      current
    DESCRIPTION
        "The maximum count of the router access-list"
    ::= { vtssRouterCapabilities 10 }

vtssRouterCapabilitiesMinAccessListNameLen OBJECT-TYPE
    SYNTAX      Unsigned32
    MAX-ACCESS  read-only
    STATUS      current
    DESCRIPTION
        "The minimum name length of router access-list"
    ::= { vtssRouterCapabilities 11 }

vtssRouterCapabilitiesMaxAccessListNameLen OBJECT-TYPE
    SYNTAX      Unsigned32
    MAX-ACCESS  read-only
    STATUS      current
    DESCRIPTION
        "The maximum name length of router access-list"
    ::= { vtssRouterCapabilities 12 }

vtssRouterCapabilitiesMinAcePrecedence OBJECT-TYPE
    SYNTAX      Unsigned32
    MAX-ACCESS  read-only
    STATUS      current
    DESCRIPTION
        "The minimum value of RIP access-list entry precedence"
    ::= { vtssRouterCapabilities 13 }

vtssRouterCapabilitiesMaxAcePrecedence OBJECT-TYPE
    SYNTAX      Unsigned32
    MAX-ACCESS  read-only
    STATUS      current
    DESCRIPTION
        "The maximum value of RIP access-list entry precedence"
    ::= { vtssRouterCapabilities 14 }

vtssRouterConfig OBJECT IDENTIFIER
    ::= { vtssRouterMibObjects 2 }

vtssRouterConfigKeyChainTable OBJECT-TYPE
    SYNTAX      SEQUENCE OF VTSSRouterConfigKeyChainEntry
    MAX-ACCESS  not-accessible
    STATUS      current
    DESCRIPTION
        "This is router key chain name table."
    ::= { vtssRouterConfig 1 }

vtssRouterConfigKeyChainEntry OBJECT-TYPE
    SYNTAX      VTSSRouterConfigKeyChainEntry
    MAX-ACCESS  not-accessible
    STATUS      current
    DESCRIPTION
        "Each row contains the name for the key chain."
    INDEX       { vtssRouterConfigKeyChainKeyChainName }
    ::= { vtssRouterConfigKeyChainTable 1 }

VTSSRouterConfigKeyChainEntry ::= SEQUENCE {
    vtssRouterConfigKeyChainKeyChainName  VTSSDisplayString,
    vtssRouterConfigKeyChainAction        VTSSRowEditorState
}

vtssRouterConfigKeyChainKeyChainName OBJECT-TYPE
    SYNTAX      VTSSDisplayString (SIZE(0..31))
    MAX-ACCESS  accessible-for-notify
    STATUS      current
    DESCRIPTION
        "The key chain name."
    ::= { vtssRouterConfigKeyChainEntry 1 }

vtssRouterConfigKeyChainAction OBJECT-TYPE
    SYNTAX      VTSSRowEditorState
    MAX-ACCESS  read-write
    STATUS      current
    DESCRIPTION
        "Action"
    ::= { vtssRouterConfigKeyChainEntry 100 }

vtssRouterConfigKeyChainTableRowEditor OBJECT IDENTIFIER
    ::= { vtssRouterConfig 2 }

vtssRouterConfigKeyChainTableRowEditorKeyChainName OBJECT-TYPE
    SYNTAX      VTSSDisplayString (SIZE(0..31))
    MAX-ACCESS  read-write
    STATUS      current
    DESCRIPTION
        "The key chain name."
    ::= { vtssRouterConfigKeyChainTableRowEditor 1 }

vtssRouterConfigKeyChainTableRowEditorAction OBJECT-TYPE
    SYNTAX      VTSSRowEditorState
    MAX-ACCESS  read-write
    STATUS      current
    DESCRIPTION
        "Action"
    ::= { vtssRouterConfigKeyChainTableRowEditor 100 }

vtssRouterConfigKeyChainKeyIdTable OBJECT-TYPE
    SYNTAX      SEQUENCE OF VTSSRouterConfigKeyChainKeyIdEntry
    MAX-ACCESS  not-accessible
    STATUS      current
    DESCRIPTION
        "This is router key chain key ID configuration table."
    ::= { vtssRouterConfig 3 }

vtssRouterConfigKeyChainKeyIdEntry OBJECT-TYPE
    SYNTAX      VTSSRouterConfigKeyChainKeyIdEntry
    MAX-ACCESS  not-accessible
    STATUS      current
    DESCRIPTION
        "Each row contains the key configuration of the corresponding key chain
         and key ID."
    INDEX       { vtssRouterConfigKeyChainKeyIdKeyChainName,
                  vtssRouterConfigKeyChainKeyIdKeyId }
    ::= { vtssRouterConfigKeyChainKeyIdTable 1 }

VTSSRouterConfigKeyChainKeyIdEntry ::= SEQUENCE {
    vtssRouterConfigKeyChainKeyIdKeyChainName  VTSSDisplayString,
    vtssRouterConfigKeyChainKeyIdKeyId         Integer32,
    vtssRouterConfigKeyChainKeyIdIsEncrypted   TruthValue,
    vtssRouterConfigKeyChainKeyIdKeyString     VTSSDisplayString,
    vtssRouterConfigKeyChainKeyIdAction        VTSSRowEditorState
}

vtssRouterConfigKeyChainKeyIdKeyChainName OBJECT-TYPE
    SYNTAX      VTSSDisplayString (SIZE(0..31))
    MAX-ACCESS  accessible-for-notify
    STATUS      current
    DESCRIPTION
        "The key chain name."
    ::= { vtssRouterConfigKeyChainKeyIdEntry 1 }

vtssRouterConfigKeyChainKeyIdKeyId OBJECT-TYPE
    SYNTAX      Integer32 (1..255)
    MAX-ACCESS  accessible-for-notify
    STATUS      current
    DESCRIPTION
        "The key ID of key chain."
    ::= { vtssRouterConfigKeyChainKeyIdEntry 2 }

vtssRouterConfigKeyChainKeyIdIsEncrypted OBJECT-TYPE
    SYNTAX      TruthValue
    MAX-ACCESS  read-write
    STATUS      current
    DESCRIPTION
        "The flag indicates the key string is encrypted or not. TRUE means the
         key string is encrypted. FALSE means the key string is plain text."
    ::= { vtssRouterConfigKeyChainKeyIdEntry 3 }

vtssRouterConfigKeyChainKeyIdKeyString OBJECT-TYPE
    SYNTAX      VTSSDisplayString (SIZE(0..224))
    MAX-ACCESS  read-write
    STATUS      current
    DESCRIPTION
        "The key string."
    ::= { vtssRouterConfigKeyChainKeyIdEntry 4 }

vtssRouterConfigKeyChainKeyIdAction OBJECT-TYPE
    SYNTAX      VTSSRowEditorState
    MAX-ACCESS  read-write
    STATUS      current
    DESCRIPTION
        "Action"
    ::= { vtssRouterConfigKeyChainKeyIdEntry 100 }

vtssRouterConfigKeyChainKeyIdTableRowEditor OBJECT IDENTIFIER
    ::= { vtssRouterConfig 4 }

vtssRouterConfigKeyChainKeyIdTableRowEditorKeyChainName OBJECT-TYPE
    SYNTAX      VTSSDisplayString (SIZE(0..31))
    MAX-ACCESS  read-write
    STATUS      current
    DESCRIPTION
        "The key chain name."
    ::= { vtssRouterConfigKeyChainKeyIdTableRowEditor 1 }

vtssRouterConfigKeyChainKeyIdTableRowEditorKeyId OBJECT-TYPE
    SYNTAX      Integer32 (1..255)
    MAX-ACCESS  read-write
    STATUS      current
    DESCRIPTION
        "The key ID of key chain."
    ::= { vtssRouterConfigKeyChainKeyIdTableRowEditor 2 }

vtssRouterConfigKeyChainKeyIdTableRowEditorIsEncrypted OBJECT-TYPE
    SYNTAX      TruthValue
    MAX-ACCESS  read-write
    STATUS      current
    DESCRIPTION
        "The flag indicates the key string is encrypted or not. TRUE means the
         key string is encrypted. FALSE means the key string is plain text."
    ::= { vtssRouterConfigKeyChainKeyIdTableRowEditor 3 }

vtssRouterConfigKeyChainKeyIdTableRowEditorKeyString OBJECT-TYPE
    SYNTAX      VTSSDisplayString (SIZE(0..224))
    MAX-ACCESS  read-write
    STATUS      current
    DESCRIPTION
        "The key string."
    ::= { vtssRouterConfigKeyChainKeyIdTableRowEditor 4 }

vtssRouterConfigKeyChainKeyIdTableRowEditorAction OBJECT-TYPE
    SYNTAX      VTSSRowEditorState
    MAX-ACCESS  read-write
    STATUS      current
    DESCRIPTION
        "Action"
    ::= { vtssRouterConfigKeyChainKeyIdTableRowEditor 100 }

vtssRouterConfigAccessListTable OBJECT-TYPE
    SYNTAX      SEQUENCE OF VTSSRouterConfigAccessListEntry
    MAX-ACCESS  not-accessible
    STATUS      current
    DESCRIPTION
        "This is router access-list configuration table."
    ::= { vtssRouterConfig 5 }

vtssRouterConfigAccessListEntry OBJECT-TYPE
    SYNTAX      VTSSRouterConfigAccessListEntry
    MAX-ACCESS  not-accessible
    STATUS      current
    DESCRIPTION
        "Each access-list entry has a set of parameters."
    INDEX       { vtssRouterConfigAccessListName,
                  vtssRouterConfigAccessListMode,
                  vtssRouterConfigAccessListNetwork,
                  vtssRouterConfigAccessListIpSubnetMaskLength }
    ::= { vtssRouterConfigAccessListTable 1 }

VTSSRouterConfigAccessListEntry ::= SEQUENCE {
    vtssRouterConfigAccessListName                VTSSDisplayString,
    vtssRouterConfigAccessListMode                VTSSRouterAccessListMode,
    vtssRouterConfigAccessListNetwork             IpAddress,
    vtssRouterConfigAccessListIpSubnetMaskLength  Integer32,
    vtssRouterConfigAccessListAction              VTSSRowEditorState
}

vtssRouterConfigAccessListName OBJECT-TYPE
    SYNTAX      VTSSDisplayString (SIZE(0..31))
    MAX-ACCESS  accessible-for-notify
    STATUS      current
    DESCRIPTION
        "Access-list name."
    ::= { vtssRouterConfigAccessListEntry 1 }

vtssRouterConfigAccessListMode OBJECT-TYPE
    SYNTAX      VTSSRouterAccessListMode
    MAX-ACCESS  accessible-for-notify
    STATUS      current
    DESCRIPTION
        "The access right mode of the access-list entry."
    ::= { vtssRouterConfigAccessListEntry 2 }

vtssRouterConfigAccessListNetwork OBJECT-TYPE
    SYNTAX      IpAddress
    MAX-ACCESS  accessible-for-notify
    STATUS      current
    DESCRIPTION
        "IPv4 network address."
    ::= { vtssRouterConfigAccessListEntry 3 }

vtssRouterConfigAccessListIpSubnetMaskLength OBJECT-TYPE
    SYNTAX      Integer32 (0..32)
    MAX-ACCESS  accessible-for-notify
    STATUS      current
    DESCRIPTION
        "IPv4 network mask length."
    ::= { vtssRouterConfigAccessListEntry 4 }

vtssRouterConfigAccessListAction OBJECT-TYPE
    SYNTAX      VTSSRowEditorState
    MAX-ACCESS  read-write
    STATUS      current
    DESCRIPTION
        "Action"
    ::= { vtssRouterConfigAccessListEntry 100 }

vtssRouterConfigAccessListTableRowEditor OBJECT IDENTIFIER
    ::= { vtssRouterConfig 6 }

vtssRouterConfigAccessListTableRowEditorName OBJECT-TYPE
    SYNTAX      VTSSDisplayString (SIZE(0..31))
    MAX-ACCESS  read-write
    STATUS      current
    DESCRIPTION
        "Access-list name."
    ::= { vtssRouterConfigAccessListTableRowEditor 1 }

vtssRouterConfigAccessListTableRowEditorMode OBJECT-TYPE
    SYNTAX      VTSSRouterAccessListMode
    MAX-ACCESS  read-write
    STATUS      current
    DESCRIPTION
        "The access right mode of the access-list entry."
    ::= { vtssRouterConfigAccessListTableRowEditor 2 }

vtssRouterConfigAccessListTableRowEditorNetwork OBJECT-TYPE
    SYNTAX      IpAddress
    MAX-ACCESS  read-write
    STATUS      current
    DESCRIPTION
        "IPv4 network address."
    ::= { vtssRouterConfigAccessListTableRowEditor 3 }

vtssRouterConfigAccessListTableRowEditorIpSubnetMaskLength OBJECT-TYPE
    SYNTAX      Integer32 (0..32)
    MAX-ACCESS  read-write
    STATUS      current
    DESCRIPTION
        "IPv4 network mask length."
    ::= { vtssRouterConfigAccessListTableRowEditor 4 }

vtssRouterConfigAccessListTableRowEditorAction OBJECT-TYPE
    SYNTAX      VTSSRowEditorState
    MAX-ACCESS  read-write
    STATUS      current
    DESCRIPTION
        "Action"
    ::= { vtssRouterConfigAccessListTableRowEditor 100 }

vtssRouterStatus OBJECT IDENTIFIER
    ::= { vtssRouterMibObjects 3 }

vtssRouterStatusAccessListTable OBJECT-TYPE
    SYNTAX      SEQUENCE OF VTSSRouterStatusAccessListEntry
    MAX-ACCESS  not-accessible
    STATUS      current
    DESCRIPTION
        "This is router access-list configuration table."
    ::= { vtssRouterStatus 2 }

vtssRouterStatusAccessListEntry OBJECT-TYPE
    SYNTAX      VTSSRouterStatusAccessListEntry
    MAX-ACCESS  not-accessible
    STATUS      current
    DESCRIPTION
        "Each access-list entry has a set of parameters."
    INDEX       { vtssRouterStatusAccessListName,
                  vtssRouterStatusAccessListRouterAccessListPrecedence }
    ::= { vtssRouterStatusAccessListTable 1 }

VTSSRouterStatusAccessListEntry ::= SEQUENCE {
    vtssRouterStatusAccessListName                        VTSSDisplayString,
    vtssRouterStatusAccessListRouterAccessListPrecedence  Unsigned32,
    vtssRouterStatusAccessListMode                        VTSSRouterAccessListMode,
    vtssRouterStatusAccessListNetworkAddress              IpAddress,
    vtssRouterStatusAccessListNetworkPrefixSize           Integer32
}

vtssRouterStatusAccessListName OBJECT-TYPE
    SYNTAX      VTSSDisplayString (SIZE(0..31))
    MAX-ACCESS  accessible-for-notify
    STATUS      current
    DESCRIPTION
        "Access-list name."
    ::= { vtssRouterStatusAccessListEntry 1 }

vtssRouterStatusAccessListRouterAccessListPrecedence OBJECT-TYPE
    SYNTAX      Unsigned32
    MAX-ACCESS  accessible-for-notify
    STATUS      current
    DESCRIPTION
        "The precedence of router access-list entry."
    ::= { vtssRouterStatusAccessListEntry 2 }

vtssRouterStatusAccessListMode OBJECT-TYPE
    SYNTAX      VTSSRouterAccessListMode
    MAX-ACCESS  read-only
    STATUS      current
    DESCRIPTION
        "The access right mode of the access-list entry."
    ::= { vtssRouterStatusAccessListEntry 3 }

vtssRouterStatusAccessListNetworkAddress OBJECT-TYPE
    SYNTAX      IpAddress
    MAX-ACCESS  read-only
    STATUS      current
    DESCRIPTION
        "The IPv4 address of the access-list entry."
    ::= { vtssRouterStatusAccessListEntry 4 }

vtssRouterStatusAccessListNetworkPrefixSize OBJECT-TYPE
    SYNTAX      Integer32 (0..32)
    MAX-ACCESS  read-only
    STATUS      current
    DESCRIPTION
        "The network prefix size of the access-list entry."
    ::= { vtssRouterStatusAccessListEntry 5 }

vtssRouterMibConformance OBJECT IDENTIFIER
    ::= { vtssRouterMib 2 }

vtssRouterMibCompliances OBJECT IDENTIFIER
    ::= { vtssRouterMibConformance 1 }

vtssRouterMibGroups OBJECT IDENTIFIER
    ::= { vtssRouterMibConformance 2 }

vtssRouterCapabilitiesInfoGroup OBJECT-GROUP
    OBJECTS     { vtssRouterCapabilitiesMaxKeyChainNameMaxCount,
                  vtssRouterCapabilitiesMinKeyChainNameLen,
                  vtssRouterCapabilitiesMaxKeyChainNameLen,
                  vtssRouterCapabilitiesMinKeyChainKeyId,
                  vtssRouterCapabilitiesMaxKeyChainKeyId,
                  vtssRouterCapabilitiesMinKeyChainPlainTextKeyStringLen,
                  vtssRouterCapabilitiesMaxKeyChainPlainTextKeyStringLen,
                  vtssRouterCapabilitiesMinKeyChainKeyEncryptedStringLen,
                  vtssRouterCapabilitiesMaxKeyChainKeyEncryptedStringLen,
                  vtssRouterCapabilitiesAccessListMaxCount,
                  vtssRouterCapabilitiesMinAccessListNameLen,
                  vtssRouterCapabilitiesMaxAccessListNameLen,
                  vtssRouterCapabilitiesMinAcePrecedence,
                  vtssRouterCapabilitiesMaxAcePrecedence }
    STATUS      current
    DESCRIPTION
        "A collection of objects."
    ::= { vtssRouterMibGroups 1 }

vtssRouterConfigKeyChainTableInfoGroup OBJECT-GROUP
    OBJECTS     { vtssRouterConfigKeyChainKeyChainName,
                  vtssRouterConfigKeyChainAction }
    STATUS      current
    DESCRIPTION
        "A collection of objects."
    ::= { vtssRouterMibGroups 2 }

vtssRouterConfigKeyChainTableRowEditorInfoGroup OBJECT-GROUP
    OBJECTS     {                   vtssRouterConfigKeyChainTableRowEditorKeyChainName,
                  vtssRouterConfigKeyChainTableRowEditorAction }
    STATUS      current
    DESCRIPTION
        "A collection of objects."
    ::= { vtssRouterMibGroups 3 }

vtssRouterConfigKeyChainKeyIdTableInfoGroup OBJECT-GROUP
    OBJECTS     { vtssRouterConfigKeyChainKeyIdKeyChainName,
                  vtssRouterConfigKeyChainKeyIdKeyId,
                  vtssRouterConfigKeyChainKeyIdIsEncrypted,
                  vtssRouterConfigKeyChainKeyIdKeyString,
                  vtssRouterConfigKeyChainKeyIdAction }
    STATUS      current
    DESCRIPTION
        "A collection of objects."
    ::= { vtssRouterMibGroups 4 }

vtssRouterConfigKeyChainKeyIdTableRowEditorInfoGroup OBJECT-GROUP
    OBJECTS     {                   vtssRouterConfigKeyChainKeyIdTableRowEditorKeyChainName,
                  vtssRouterConfigKeyChainKeyIdTableRowEditorKeyId,
                  vtssRouterConfigKeyChainKeyIdTableRowEditorIsEncrypted,
                  vtssRouterConfigKeyChainKeyIdTableRowEditorKeyString,
                  vtssRouterConfigKeyChainKeyIdTableRowEditorAction }
    STATUS      current
    DESCRIPTION
        "A collection of objects."
    ::= { vtssRouterMibGroups 5 }

vtssRouterConfigAccessListTableInfoGroup OBJECT-GROUP
    OBJECTS     { vtssRouterConfigAccessListName,
                  vtssRouterConfigAccessListMode,
                  vtssRouterConfigAccessListNetwork,
                  vtssRouterConfigAccessListIpSubnetMaskLength,
                  vtssRouterConfigAccessListAction }
    STATUS      current
    DESCRIPTION
        "A collection of objects."
    ::= { vtssRouterMibGroups 6 }

vtssRouterConfigAccessListTableRowEditorInfoGroup OBJECT-GROUP
    OBJECTS     { vtssRouterConfigAccessListTableRowEditorName,
                  vtssRouterConfigAccessListTableRowEditorMode,
                  vtssRouterConfigAccessListTableRowEditorNetwork,
                  vtssRouterConfigAccessListTableRowEditorIpSubnetMaskLength,
                  vtssRouterConfigAccessListTableRowEditorAction }
    STATUS      current
    DESCRIPTION
        "A collection of objects."
    ::= { vtssRouterMibGroups 7 }

vtssRouterStatusAccessListTableInfoGroup OBJECT-GROUP
    OBJECTS     { vtssRouterStatusAccessListName,
                  vtssRouterStatusAccessListRouterAccessListPrecedence,
                  vtssRouterStatusAccessListMode,
                  vtssRouterStatusAccessListNetworkAddress,
                  vtssRouterStatusAccessListNetworkPrefixSize }
    STATUS      current
    DESCRIPTION
        "A collection of objects."
    ::= { vtssRouterMibGroups 8 }

vtssRouterMibCompliance MODULE-COMPLIANCE
    STATUS      current
    DESCRIPTION
        "The compliance statement for the implementation."

    MODULE      -- this module

    MANDATORY-GROUPS { vtssRouterCapabilitiesInfoGroup,
                       vtssRouterConfigKeyChainTableInfoGroup,
                       vtssRouterConfigKeyChainTableRowEditorInfoGroup,
                       vtssRouterConfigKeyChainKeyIdTableInfoGroup,
                       vtssRouterConfigKeyChainKeyIdTableRowEditorInfoGroup,
                       vtssRouterConfigAccessListTableInfoGroup,
                       vtssRouterConfigAccessListTableRowEditorInfoGroup,
                       vtssRouterStatusAccessListTableInfoGroup }

    ::= { vtssRouterMibCompliances 1 }

END
