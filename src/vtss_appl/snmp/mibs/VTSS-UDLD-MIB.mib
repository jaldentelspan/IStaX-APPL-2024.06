-- *****************************************************************
-- UDLD-MIB:  Microsemi ENT private MIB
-- ****************************************************************

VTSS-UDLD-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Unsigned32 FROM SNMPv2-SMI
    VTSSDisplayString FROM VTSS-TC
    VTSSInterfaceIndex FROM VTSS-TC
    ;

vtssUdldMib MODULE-IDENTITY
    LAST-UPDATED "201407010000Z"
    ORGANIZATION
        "Microsemi Corporation"
    CONTACT-INFO
        "Application support: http://www.microchip.com/support"
    DESCRIPTION
        "This is a private MIB for udld"
    REVISION    "201407010000Z"
    DESCRIPTION
        "Initial version"
    ::= { vtssSwitchMgmt 123 }


VTSSUdldDetectionState ::= TEXTUAL-CONVENTION
    STATUS      current
    DESCRIPTION
        "This enumeration defines the link detection state."
    SYNTAX      INTEGER { inDeterminant(0), uniDirectional(1),
                          biDirectional(2), neighborMismatch(3),
                          loopback(4), multipleNeighbor(5) }

VTSSUdldMode ::= TEXTUAL-CONVENTION
    STATUS      current
    DESCRIPTION
        "This enumeration defines the available udld mode."
    SYNTAX      INTEGER { disable(0), normal(1), aggressive(2) }

vtssUdldMibObjects OBJECT IDENTIFIER
    ::= { vtssUdldMib 1 }

vtssUdldConfig OBJECT IDENTIFIER
    ::= { vtssUdldMibObjects 2 }

vtssUdldConfigInterface OBJECT IDENTIFIER
    ::= { vtssUdldConfig 1 }

vtssUdldConfigInterfaceParamTable OBJECT-TYPE
    SYNTAX      SEQUENCE OF VTSSUdldConfigInterfaceParamEntry
    MAX-ACCESS  not-accessible
    STATUS      current
    DESCRIPTION
        "This is a table of udld interface conf parameters"
    ::= { vtssUdldConfigInterface 1 }

vtssUdldConfigInterfaceParamEntry OBJECT-TYPE
    SYNTAX      VTSSUdldConfigInterfaceParamEntry
    MAX-ACCESS  not-accessible
    STATUS      current
    DESCRIPTION
        "Each physical interface has a set of configurable parameters"
    INDEX       { vtssUdldConfigInterfaceParamIfIndex }
    ::= { vtssUdldConfigInterfaceParamTable 1 }

VTSSUdldConfigInterfaceParamEntry ::= SEQUENCE {
    vtssUdldConfigInterfaceParamIfIndex           VTSSInterfaceIndex,
    vtssUdldConfigInterfaceParamUdldMode          VTSSUdldMode,
    vtssUdldConfigInterfaceParamProbeMsgInterval  Unsigned32
}

vtssUdldConfigInterfaceParamIfIndex OBJECT-TYPE
    SYNTAX      VTSSInterfaceIndex
    MAX-ACCESS  accessible-for-notify
    STATUS      current
    DESCRIPTION
        "Logical interface number."
    ::= { vtssUdldConfigInterfaceParamEntry 1 }

vtssUdldConfigInterfaceParamUdldMode OBJECT-TYPE
    SYNTAX      VTSSUdldMode
    MAX-ACCESS  read-write
    STATUS      current
    DESCRIPTION
        "Port udld mode disable/normal/aggresive."
    ::= { vtssUdldConfigInterfaceParamEntry 2 }

vtssUdldConfigInterfaceParamProbeMsgInterval OBJECT-TYPE
    SYNTAX      Unsigned32 (7..90)
    MAX-ACCESS  read-write
    STATUS      current
    DESCRIPTION
        "Port probe message interval(seconds). Valid range: 7 to 90 seconds."
    ::= { vtssUdldConfigInterfaceParamEntry 3 }

vtssUdldStatus OBJECT IDENTIFIER
    ::= { vtssUdldMibObjects 3 }

vtssUdldStatusInterface OBJECT IDENTIFIER
    ::= { vtssUdldStatus 1 }

vtssUdldStatusInterfaceTable OBJECT-TYPE
    SYNTAX      SEQUENCE OF VTSSUdldStatusInterfaceEntry
    MAX-ACCESS  not-accessible
    STATUS      current
    DESCRIPTION
        "This is a table of udld interface local device information"
    ::= { vtssUdldStatusInterface 1 }

vtssUdldStatusInterfaceEntry OBJECT-TYPE
    SYNTAX      VTSSUdldStatusInterfaceEntry
    MAX-ACCESS  not-accessible
    STATUS      current
    DESCRIPTION
        "Each udld enabled interface has a local device information"
    INDEX       { vtssUdldStatusInterfaceIfIndex }
    ::= { vtssUdldStatusInterfaceTable 1 }

VTSSUdldStatusInterfaceEntry ::= SEQUENCE {
    vtssUdldStatusInterfaceIfIndex     VTSSInterfaceIndex,
    vtssUdldStatusInterfaceDeviceID    VTSSDisplayString,
    vtssUdldStatusInterfaceDeviceName  VTSSDisplayString,
    vtssUdldStatusInterfaceLinkState   VTSSUdldDetectionState
}

vtssUdldStatusInterfaceIfIndex OBJECT-TYPE
    SYNTAX      VTSSInterfaceIndex
    MAX-ACCESS  accessible-for-notify
    STATUS      current
    DESCRIPTION
        "Logical interface number."
    ::= { vtssUdldStatusInterfaceEntry 1 }

vtssUdldStatusInterfaceDeviceID OBJECT-TYPE
    SYNTAX      VTSSDisplayString (SIZE(0..254))
    MAX-ACCESS  read-only
    STATUS      current
    DESCRIPTION
        "Local device id."
    ::= { vtssUdldStatusInterfaceEntry 2 }

vtssUdldStatusInterfaceDeviceName OBJECT-TYPE
    SYNTAX      VTSSDisplayString (SIZE(0..254))
    MAX-ACCESS  read-only
    STATUS      current
    DESCRIPTION
        "Local device name."
    ::= { vtssUdldStatusInterfaceEntry 3 }

vtssUdldStatusInterfaceLinkState OBJECT-TYPE
    SYNTAX      VTSSUdldDetectionState
    MAX-ACCESS  read-only
    STATUS      current
    DESCRIPTION
        "Local device link detected state."
    ::= { vtssUdldStatusInterfaceEntry 4 }

vtssUdldStatusInterfaceNeighborTable OBJECT-TYPE
    SYNTAX      SEQUENCE OF VTSSUdldStatusInterfaceNeighborEntry
    MAX-ACCESS  not-accessible
    STATUS      current
    DESCRIPTION
        "This is a table of udld interface neighbor cache information"
    ::= { vtssUdldStatusInterface 2 }

vtssUdldStatusInterfaceNeighborEntry OBJECT-TYPE
    SYNTAX      VTSSUdldStatusInterfaceNeighborEntry
    MAX-ACCESS  not-accessible
    STATUS      current
    DESCRIPTION
        "Each udld enabled interface has a neighbor cache information"
    INDEX       { vtssUdldStatusInterfaceNeighborIfIndex }
    ::= { vtssUdldStatusInterfaceNeighborTable 1 }

VTSSUdldStatusInterfaceNeighborEntry ::= SEQUENCE {
    vtssUdldStatusInterfaceNeighborIfIndex             VTSSInterfaceIndex,
    vtssUdldStatusInterfaceNeighborNeighborDeviceID    VTSSDisplayString,
    vtssUdldStatusInterfaceNeighborNeighborPortID      VTSSDisplayString,
    vtssUdldStatusInterfaceNeighborNeighborDeviceName  VTSSDisplayString,
    vtssUdldStatusInterfaceNeighborLinkDetectionState  VTSSUdldDetectionState
}

vtssUdldStatusInterfaceNeighborIfIndex OBJECT-TYPE
    SYNTAX      VTSSInterfaceIndex
    MAX-ACCESS  accessible-for-notify
    STATUS      current
    DESCRIPTION
        "Logical interface number."
    ::= { vtssUdldStatusInterfaceNeighborEntry 1 }

vtssUdldStatusInterfaceNeighborNeighborDeviceID OBJECT-TYPE
    SYNTAX      VTSSDisplayString (SIZE(0..254))
    MAX-ACCESS  read-only
    STATUS      current
    DESCRIPTION
        "Neighbor device id."
    ::= { vtssUdldStatusInterfaceNeighborEntry 2 }

vtssUdldStatusInterfaceNeighborNeighborPortID OBJECT-TYPE
    SYNTAX      VTSSDisplayString (SIZE(0..254))
    MAX-ACCESS  read-only
    STATUS      current
    DESCRIPTION
        "Neighbor port id."
    ::= { vtssUdldStatusInterfaceNeighborEntry 3 }

vtssUdldStatusInterfaceNeighborNeighborDeviceName OBJECT-TYPE
    SYNTAX      VTSSDisplayString (SIZE(0..254))
    MAX-ACCESS  read-only
    STATUS      current
    DESCRIPTION
        "Neighbor device name."
    ::= { vtssUdldStatusInterfaceNeighborEntry 4 }

vtssUdldStatusInterfaceNeighborLinkDetectionState OBJECT-TYPE
    SYNTAX      VTSSUdldDetectionState
    MAX-ACCESS  read-only
    STATUS      current
    DESCRIPTION
        "Neighbor device link detected state."
    ::= { vtssUdldStatusInterfaceNeighborEntry 5 }

vtssUdldMibConformance OBJECT IDENTIFIER
    ::= { vtssUdldMib 2 }

vtssUdldMibCompliances OBJECT IDENTIFIER
    ::= { vtssUdldMibConformance 1 }

vtssUdldMibGroups OBJECT IDENTIFIER
    ::= { vtssUdldMibConformance 2 }

vtssUdldConfigInterfaceParamTableInfoGroup OBJECT-GROUP
    OBJECTS     { vtssUdldConfigInterfaceParamIfIndex,
                  vtssUdldConfigInterfaceParamUdldMode,
                  vtssUdldConfigInterfaceParamProbeMsgInterval }
    STATUS      current
    DESCRIPTION
        "A collection of objects."
    ::= { vtssUdldMibGroups 1 }

vtssUdldStatusInterfaceTableInfoGroup OBJECT-GROUP
    OBJECTS     { vtssUdldStatusInterfaceIfIndex,
                  vtssUdldStatusInterfaceDeviceID,
                  vtssUdldStatusInterfaceDeviceName,
                  vtssUdldStatusInterfaceLinkState }
    STATUS      current
    DESCRIPTION
        "A collection of objects."
    ::= { vtssUdldMibGroups 2 }

vtssUdldStatusInterfaceNeighborTableInfoGroup OBJECT-GROUP
    OBJECTS     { vtssUdldStatusInterfaceNeighborIfIndex,
                  vtssUdldStatusInterfaceNeighborNeighborDeviceID,
                  vtssUdldStatusInterfaceNeighborNeighborPortID,
                  vtssUdldStatusInterfaceNeighborNeighborDeviceName,
                  vtssUdldStatusInterfaceNeighborLinkDetectionState }
    STATUS      current
    DESCRIPTION
        "A collection of objects."
    ::= { vtssUdldMibGroups 3 }

vtssUdldMibCompliance MODULE-COMPLIANCE
    STATUS      current
    DESCRIPTION
        "The compliance statement for the implementation."

    MODULE      -- this module

    MANDATORY-GROUPS { vtssUdldConfigInterfaceParamTableInfoGroup,
                       vtssUdldStatusInterfaceTableInfoGroup,
                       vtssUdldStatusInterfaceNeighborTableInfoGroup }

    ::= { vtssUdldMibCompliances 1 }

END
