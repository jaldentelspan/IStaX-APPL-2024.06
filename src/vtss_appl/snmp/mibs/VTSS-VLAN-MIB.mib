-- *****************************************************************
-- VLAN-MIB:  Microsemi ENT private MIB
-- ****************************************************************

VTSS-VLAN-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    TruthValue FROM SNMPv2-TC
    VTSSDisplayString FROM VTSS-TC
    VTSSEtherType FROM VTSS-TC
    VTSSInterfaceIndex FROM VTSS-TC
    VTSSPortList FROM VTSS-TC
    VTSSRowEditorState FROM VTSS-TC
    VTSSUnsigned16 FROM VTSS-TC
    VTSSVlan FROM VTSS-TC
    VTSSVlanListQuarter FROM VTSS-TC
    ;

vtssVlanMib MODULE-IDENTITY
    LAST-UPDATED "202104290000Z"
    ORGANIZATION
        "Microsemi Corporation"
    CONTACT-INFO
        "Application support: http://www.microchip.com/support"
    DESCRIPTION
        "Private MIB for VLAN."
    REVISION    "202104290000Z"
    DESCRIPTION
        "Added support for MRP VLAN user"
    REVISION    "202008240000Z"
    DESCRIPTION
        "Add support for managing flooding"
    REVISION    "201904050000Z"
    DESCRIPTION
        "Obsoleted a couple of VLAN users"
    REVISION    "201501160000Z"
    DESCRIPTION
        "Added Shared VLAN Learning table"
    REVISION    "201407010000Z"
    DESCRIPTION
        "Initial version"
    ::= { vtssSwitchMgmt 13 }


VTSSVlanEgressTagging ::= TEXTUAL-CONVENTION
    STATUS      current
    DESCRIPTION
        "An integer that indicates how egress tagging occurs."
    SYNTAX      INTEGER { untagThis(0), tagThis(1), tagAll(2),
                          untagAll(3) }

VTSSVlanIngressAcceptance ::= TEXTUAL-CONVENTION
    STATUS      current
    DESCRIPTION
        "An integer that indicates the type of frames that are not discarded on
         ingress w.r.t. VLAN tagging."
    SYNTAX      INTEGER { all(0), tagged(1), untagged(2) }

VTSSVlanPortMode ::= TEXTUAL-CONVENTION
    STATUS      current
    DESCRIPTION
        "Determines the underlying port mode.
         
         Access ports are only members of one VLAN, the AccessVlan.
         
         Trunk ports are by default members of all VLANs, which can be limited
         with TrunkVlans.
         
         Hybrid ports allow for changing all port VLAN parameters. As trunk
         ports, hybrid ports are by default members of all VLANs, which can be
         limited with HybridVlans."
    SYNTAX      INTEGER { access(0), trunk(1), hybrid(2) }

VTSSVlanPortType ::= TEXTUAL-CONVENTION
    STATUS      current
    DESCRIPTION
        "An integer that indicates if a port is VLAN aware, and if so, to which
         EtherType it is sensitive."
    SYNTAX      INTEGER { unaware(0), c(1), s(2), sCustom(3) }

VTSSVlanUserType ::= TEXTUAL-CONVENTION
    STATUS      current
    DESCRIPTION
        "An integer that indicates the VLAN user type. A value of 'combined'
         indicates the VLAN settings as programmed to hardware. A value of
         'admin' indicates the VLAN settings as programmed by the administrative
         user, and any other value indicates a software module that changes VLAN
         settings 'behind the scenes'."
    SYNTAX      INTEGER { combined(0), admin(1), dot1x(3), mvrp(4),
                          gvrp(5), mvr(6), voiceVlan(7), mstp(8),
                          erps(9), mrp(10), mepObsolete(11),
                          evcObsolete(12), vcl(13), rmirror(14) }

vtssVlanMibObjects OBJECT IDENTIFIER
    ::= { vtssVlanMib 1 }

vtssVlanCapabilities OBJECT IDENTIFIER
    ::= { vtssVlanMibObjects 1 }

vtssVlanCapabilitiesVlanIdMin OBJECT-TYPE
    SYNTAX      VTSSVlan
    MAX-ACCESS  read-only
    STATUS      current
    DESCRIPTION
        "The minimum VLAN ID that can be configured on the device."
    ::= { vtssVlanCapabilities 1 }

vtssVlanCapabilitiesVlanIdMax OBJECT-TYPE
    SYNTAX      VTSSVlan
    MAX-ACCESS  read-only
    STATUS      current
    DESCRIPTION
        "The maximum VLAN ID that can be configured on the device."
    ::= { vtssVlanCapabilities 2 }

vtssVlanCapabilitiesFidCnt OBJECT-TYPE
    SYNTAX      VTSSUnsigned16
    MAX-ACCESS  read-only
    STATUS      current
    DESCRIPTION
        "The number of Shared VLAN Learning (SVL) Filter IDs (FIDs) supported by
         this device. 0 if SVL is not supported."
    ::= { vtssVlanCapabilities 3 }

vtssVlanCapabilitiesHasFlooding OBJECT-TYPE
    SYNTAX      TruthValue
    MAX-ACCESS  read-only
    STATUS      current
    DESCRIPTION
        "If true, flooding can be managed."
    ::= { vtssVlanCapabilities 4 }

vtssVlanConfig OBJECT IDENTIFIER
    ::= { vtssVlanMibObjects 2 }

vtssVlanConfigGlobals OBJECT IDENTIFIER
    ::= { vtssVlanConfig 1 }

vtssVlanConfigGlobalsMain OBJECT IDENTIFIER
    ::= { vtssVlanConfigGlobals 1 }

vtssVlanConfigGlobalsMainCustomSPortEtherType OBJECT-TYPE
    SYNTAX      VTSSEtherType (1536..65535)
    MAX-ACCESS  read-write
    STATUS      current
    DESCRIPTION
        "TPID (EtherType) for ports marked as Custom-S tag aware."
    ::= { vtssVlanConfigGlobalsMain 1 }

vtssVlanConfigGlobalsMainAccessVlans0To1K OBJECT-TYPE
    SYNTAX      VTSSVlanListQuarter
    MAX-ACCESS  read-write
    STATUS      current
    DESCRIPTION
        "First quarter of bit-array indicating the enabled access VLANs."
    ::= { vtssVlanConfigGlobalsMain 2 }

vtssVlanConfigGlobalsMainAccessVlans1KTo2K OBJECT-TYPE
    SYNTAX      VTSSVlanListQuarter
    MAX-ACCESS  read-write
    STATUS      current
    DESCRIPTION
        "Second quarter of bit-array indicating the enabled access VLANs."
    ::= { vtssVlanConfigGlobalsMain 3 }

vtssVlanConfigGlobalsMainAccessVlans2KTo3K OBJECT-TYPE
    SYNTAX      VTSSVlanListQuarter
    MAX-ACCESS  read-write
    STATUS      current
    DESCRIPTION
        "Third quarter of bit-array indicating the enabled access VLANs."
    ::= { vtssVlanConfigGlobalsMain 4 }

vtssVlanConfigGlobalsMainAccessVlans3KTo4K OBJECT-TYPE
    SYNTAX      VTSSVlanListQuarter
    MAX-ACCESS  read-write
    STATUS      current
    DESCRIPTION
        "Last quarter of bit-array indicating the enabled access VLANs."
    ::= { vtssVlanConfigGlobalsMain 5 }

vtssVlanConfigGlobalsNameTable OBJECT-TYPE
    SYNTAX      SEQUENCE OF VTSSVlanConfigGlobalsNameEntry
    MAX-ACCESS  not-accessible
    STATUS      current
    DESCRIPTION
        "Table of VLAN names."
    ::= { vtssVlanConfigGlobals 2 }

vtssVlanConfigGlobalsNameEntry OBJECT-TYPE
    SYNTAX      VTSSVlanConfigGlobalsNameEntry
    MAX-ACCESS  not-accessible
    STATUS      current
    DESCRIPTION
        "Each row contains the name of a given VLAN."
    INDEX       { vtssVlanConfigGlobalsNameVlanId }
    ::= { vtssVlanConfigGlobalsNameTable 1 }

VTSSVlanConfigGlobalsNameEntry ::= SEQUENCE {
    vtssVlanConfigGlobalsNameVlanId  VTSSVlan,
    vtssVlanConfigGlobalsNameName    VTSSDisplayString
}

vtssVlanConfigGlobalsNameVlanId OBJECT-TYPE
    SYNTAX      VTSSVlan
    MAX-ACCESS  accessible-for-notify
    STATUS      current
    DESCRIPTION
        "VLAN ID. Valid range is 1 - 4095."
    ::= { vtssVlanConfigGlobalsNameEntry 1 }

vtssVlanConfigGlobalsNameName OBJECT-TYPE
    SYNTAX      VTSSDisplayString (SIZE(0..32))
    MAX-ACCESS  read-write
    STATUS      current
    DESCRIPTION
        "VLAN Name. Default for VLAN 1 is 'default'. Default for any other VLAN
         is 'VLANxxxx', where 'xxxx' is a decimal representation of the VLAN ID
         with leading zeroes."
    ::= { vtssVlanConfigGlobalsNameEntry 2 }

vtssVlanConfigGlobalsFloodingTable OBJECT-TYPE
    SYNTAX      SEQUENCE OF VTSSVlanConfigGlobalsFloodingEntry
    MAX-ACCESS  not-accessible
    STATUS      current
    DESCRIPTION
        "(Table of VLAN flooding configuration.)This is an optional table and is
         only present if vlanCapabilities.hasFlooding is true."
    ::= { vtssVlanConfigGlobals 3 }

vtssVlanConfigGlobalsFloodingEntry OBJECT-TYPE
    SYNTAX      VTSSVlanConfigGlobalsFloodingEntry
    MAX-ACCESS  not-accessible
    STATUS      current
    DESCRIPTION
        "Each row contains the flooding configuration of a given VLAN."
    INDEX       { vtssVlanConfigGlobalsFloodingVlanId }
    ::= { vtssVlanConfigGlobalsFloodingTable 1 }

VTSSVlanConfigGlobalsFloodingEntry ::= SEQUENCE {
    vtssVlanConfigGlobalsFloodingVlanId    VTSSVlan,
    vtssVlanConfigGlobalsFloodingFlooding  TruthValue
}

vtssVlanConfigGlobalsFloodingVlanId OBJECT-TYPE
    SYNTAX      VTSSVlan
    MAX-ACCESS  accessible-for-notify
    STATUS      current
    DESCRIPTION
        "VLAN ID. Valid range is 1 - 4095."
    ::= { vtssVlanConfigGlobalsFloodingEntry 1 }

vtssVlanConfigGlobalsFloodingFlooding OBJECT-TYPE
    SYNTAX      TruthValue
    MAX-ACCESS  read-write
    STATUS      current
    DESCRIPTION
        "Flooding."
    ::= { vtssVlanConfigGlobalsFloodingEntry 2 }

vtssVlanConfigInterfaces OBJECT IDENTIFIER
    ::= { vtssVlanConfig 2 }

vtssVlanConfigInterfacesTable OBJECT-TYPE
    SYNTAX      SEQUENCE OF VTSSVlanConfigInterfacesEntry
    MAX-ACCESS  not-accessible
    STATUS      current
    DESCRIPTION
        "Table of per-port configuration."
    ::= { vtssVlanConfigInterfaces 1 }

vtssVlanConfigInterfacesEntry OBJECT-TYPE
    SYNTAX      VTSSVlanConfigInterfacesEntry
    MAX-ACCESS  not-accessible
    STATUS      current
    DESCRIPTION
        "Each row contains the VLAN configuration for a port interface."
    INDEX       { vtssVlanConfigInterfacesIfIndex }
    ::= { vtssVlanConfigInterfacesTable 1 }

VTSSVlanConfigInterfacesEntry ::= SEQUENCE {
    vtssVlanConfigInterfacesIfIndex                  VTSSInterfaceIndex,
    vtssVlanConfigInterfacesMode                     VTSSVlanPortMode,
    vtssVlanConfigInterfacesAccessVlan               VTSSVlan,
    vtssVlanConfigInterfacesTrunkNativeVlan          VTSSVlan,
    vtssVlanConfigInterfacesTrunkTagNativeVlan       TruthValue,
    vtssVlanConfigInterfacesTrunkVlans0KTo1K         VTSSVlanListQuarter,
    vtssVlanConfigInterfacesTrunkVlans1KTo2K         VTSSVlanListQuarter,
    vtssVlanConfigInterfacesTrunkVlans2KTo3K         VTSSVlanListQuarter,
    vtssVlanConfigInterfacesTrunkVlans3KTo4K         VTSSVlanListQuarter,
    vtssVlanConfigInterfacesHybridNativeVlan         VTSSVlan,
    vtssVlanConfigInterfacesHybridPortType           VTSSVlanPortType,
    vtssVlanConfigInterfacesHybridIngressFiltering   TruthValue,
    vtssVlanConfigInterfacesHybridIngressAcceptance  VTSSVlanIngressAcceptance,
    vtssVlanConfigInterfacesHybridEgressTagging      VTSSVlanEgressTagging,
    vtssVlanConfigInterfacesHybridVlans0KTo1K        VTSSVlanListQuarter,
    vtssVlanConfigInterfacesHybridVlans1KTo2K        VTSSVlanListQuarter,
    vtssVlanConfigInterfacesHybridVlans2KTo3K        VTSSVlanListQuarter,
    vtssVlanConfigInterfacesHybridVlans3KTo4K        VTSSVlanListQuarter,
    vtssVlanConfigInterfacesForbiddenVlans0KTo1K     VTSSVlanListQuarter,
    vtssVlanConfigInterfacesForbiddenVlans1KTo2K     VTSSVlanListQuarter,
    vtssVlanConfigInterfacesForbiddenVlans2KTo3K     VTSSVlanListQuarter,
    vtssVlanConfigInterfacesForbiddenVlans3KTo4K     VTSSVlanListQuarter
}

vtssVlanConfigInterfacesIfIndex OBJECT-TYPE
    SYNTAX      VTSSInterfaceIndex
    MAX-ACCESS  accessible-for-notify
    STATUS      current
    DESCRIPTION
        "Logical interface index."
    ::= { vtssVlanConfigInterfacesEntry 1 }

vtssVlanConfigInterfacesMode OBJECT-TYPE
    SYNTAX      VTSSVlanPortMode
    MAX-ACCESS  read-write
    STATUS      current
    DESCRIPTION
        "VLAN mode of the port."
    ::= { vtssVlanConfigInterfacesEntry 2 }

vtssVlanConfigInterfacesAccessVlan OBJECT-TYPE
    SYNTAX      VTSSVlan
    MAX-ACCESS  read-write
    STATUS      current
    DESCRIPTION
        "The port VLAN ID the port will be assigned when Mode is Access."
    ::= { vtssVlanConfigInterfacesEntry 3 }

vtssVlanConfigInterfacesTrunkNativeVlan OBJECT-TYPE
    SYNTAX      VTSSVlan
    MAX-ACCESS  read-write
    STATUS      current
    DESCRIPTION
        "The port VLAN ID the port will be assigned when Mode is trunk."
    ::= { vtssVlanConfigInterfacesEntry 4 }

vtssVlanConfigInterfacesTrunkTagNativeVlan OBJECT-TYPE
    SYNTAX      TruthValue
    MAX-ACCESS  read-write
    STATUS      current
    DESCRIPTION
        "Controls whether frames classified to TrunkNativeVlan get tagged on
         egress. Used when Mode is trunk."
    ::= { vtssVlanConfigInterfacesEntry 5 }

vtssVlanConfigInterfacesTrunkVlans0KTo1K OBJECT-TYPE
    SYNTAX      VTSSVlanListQuarter
    MAX-ACCESS  read-write
    STATUS      current
    DESCRIPTION
        "First quarter of bit-array indicating whether the port is member of a
         VLAN ('1') or not ('0'). Used when Mode is trunk."
    ::= { vtssVlanConfigInterfacesEntry 6 }

vtssVlanConfigInterfacesTrunkVlans1KTo2K OBJECT-TYPE
    SYNTAX      VTSSVlanListQuarter
    MAX-ACCESS  read-write
    STATUS      current
    DESCRIPTION
        "Second quarter of bit-array indicating whether the port is member of a
         VLAN ('1') or not ('0'). Used when Mode is trunk."
    ::= { vtssVlanConfigInterfacesEntry 7 }

vtssVlanConfigInterfacesTrunkVlans2KTo3K OBJECT-TYPE
    SYNTAX      VTSSVlanListQuarter
    MAX-ACCESS  read-write
    STATUS      current
    DESCRIPTION
        "Third quarter of bit-array indicating whether the port is member of a
         VLAN ('1') or not ('0'). Used when Mode is trunk."
    ::= { vtssVlanConfigInterfacesEntry 8 }

vtssVlanConfigInterfacesTrunkVlans3KTo4K OBJECT-TYPE
    SYNTAX      VTSSVlanListQuarter
    MAX-ACCESS  read-write
    STATUS      current
    DESCRIPTION
        "Last quarter of bit-array indicating whether the port is member of a
         VLAN ('1') or not ('0'). Used when Mode is trunk."
    ::= { vtssVlanConfigInterfacesEntry 9 }

vtssVlanConfigInterfacesHybridNativeVlan OBJECT-TYPE
    SYNTAX      VTSSVlan
    MAX-ACCESS  read-write
    STATUS      current
    DESCRIPTION
        "The port VLAN ID the port will be assigned when Mode is hybrid."
    ::= { vtssVlanConfigInterfacesEntry 10 }

vtssVlanConfigInterfacesHybridPortType OBJECT-TYPE
    SYNTAX      VTSSVlanPortType
    MAX-ACCESS  read-write
    STATUS      current
    DESCRIPTION
        "Controls awareness and whether it reacts to C-tags, S-tags,
         Custom-S-tags. Used when Mode is hybrid."
    ::= { vtssVlanConfigInterfacesEntry 11 }

vtssVlanConfigInterfacesHybridIngressFiltering OBJECT-TYPE
    SYNTAX      TruthValue
    MAX-ACCESS  read-write
    STATUS      current
    DESCRIPTION
        "Controls whether frames classified to a certain VLAN ID get discarded
         (true) or not (false) if the port is not member of the VLAN ID. Used
         when Mode is hybrid."
    ::= { vtssVlanConfigInterfacesEntry 12 }

vtssVlanConfigInterfacesHybridIngressAcceptance OBJECT-TYPE
    SYNTAX      VTSSVlanIngressAcceptance
    MAX-ACCESS  read-write
    STATUS      current
    DESCRIPTION
        "Controls whether frames are accepted on ingress depending on VLAN tag
         in frame. Used when Mode is hybrid."
    ::= { vtssVlanConfigInterfacesEntry 13 }

vtssVlanConfigInterfacesHybridEgressTagging OBJECT-TYPE
    SYNTAX      VTSSVlanEgressTagging
    MAX-ACCESS  read-write
    STATUS      current
    DESCRIPTION
        "Controls tagging of frames on egress. tagThis(1) is not allowed. Used
         when Mode is hybrid."
    ::= { vtssVlanConfigInterfacesEntry 14 }

vtssVlanConfigInterfacesHybridVlans0KTo1K OBJECT-TYPE
    SYNTAX      VTSSVlanListQuarter
    MAX-ACCESS  read-write
    STATUS      current
    DESCRIPTION
        "First quarter of bit-array indicating whether the port is member of a
         VLAN ('1') or not ('0'). Used when Mode is hybrid."
    ::= { vtssVlanConfigInterfacesEntry 15 }

vtssVlanConfigInterfacesHybridVlans1KTo2K OBJECT-TYPE
    SYNTAX      VTSSVlanListQuarter
    MAX-ACCESS  read-write
    STATUS      current
    DESCRIPTION
        "Second quarter of bit-array indicating whether the port is member of a
         VLAN ('1') or not ('0'). Used when Mode is hybrid."
    ::= { vtssVlanConfigInterfacesEntry 16 }

vtssVlanConfigInterfacesHybridVlans2KTo3K OBJECT-TYPE
    SYNTAX      VTSSVlanListQuarter
    MAX-ACCESS  read-write
    STATUS      current
    DESCRIPTION
        "Third quarter of bit-array indicating whether the port is member of a
         VLAN ('1') or not ('0'). Used when Mode is hybrid."
    ::= { vtssVlanConfigInterfacesEntry 17 }

vtssVlanConfigInterfacesHybridVlans3KTo4K OBJECT-TYPE
    SYNTAX      VTSSVlanListQuarter
    MAX-ACCESS  read-write
    STATUS      current
    DESCRIPTION
        "Last quarter of bit-array indicating whether the port is member of a
         VLAN ('1') or not ('0'). Used when Mode is hybrid."
    ::= { vtssVlanConfigInterfacesEntry 18 }

vtssVlanConfigInterfacesForbiddenVlans0KTo1K OBJECT-TYPE
    SYNTAX      VTSSVlanListQuarter
    MAX-ACCESS  read-write
    STATUS      current
    DESCRIPTION
        "First quarter of bit-array indicating whether the port can ever become
         a member of a VLAN ('0') or not ('1'). Used in all modes."
    ::= { vtssVlanConfigInterfacesEntry 19 }

vtssVlanConfigInterfacesForbiddenVlans1KTo2K OBJECT-TYPE
    SYNTAX      VTSSVlanListQuarter
    MAX-ACCESS  read-write
    STATUS      current
    DESCRIPTION
        "Second quarter of bit-array indicating whether the port can ever become
         a member of a VLAN ('0') or not ('1'). Used in all modes."
    ::= { vtssVlanConfigInterfacesEntry 20 }

vtssVlanConfigInterfacesForbiddenVlans2KTo3K OBJECT-TYPE
    SYNTAX      VTSSVlanListQuarter
    MAX-ACCESS  read-write
    STATUS      current
    DESCRIPTION
        "Third quarter of bit-array indicating whether the port can ever become
         a member of a VLAN ('0') or not ('1'). Used in all modes."
    ::= { vtssVlanConfigInterfacesEntry 21 }

vtssVlanConfigInterfacesForbiddenVlans3KTo4K OBJECT-TYPE
    SYNTAX      VTSSVlanListQuarter
    MAX-ACCESS  read-write
    STATUS      current
    DESCRIPTION
        "Last quarter of bit-array indicating whether the port can ever become a
         member of a VLAN ('0') or not ('1'). Used in all modes."
    ::= { vtssVlanConfigInterfacesEntry 22 }

vtssVlanConfigInterfacesSvlTable OBJECT-TYPE
    SYNTAX      SEQUENCE OF VTSSVlanConfigInterfacesSvlEntry
    MAX-ACCESS  not-accessible
    STATUS      current
    DESCRIPTION
        "Shared VLAN Learning (SVL) allows for having one or more VLAN IDs map
         to the same Filter ID (FID). For a given set of VLANs, if an individual
         MAC address is learned in one VLAN, that learned information is used in
         forwarding decisions taken for that address relative to all other VLANs
         in the given set.
         
         fidCnt, which can be found in the capabilities section, indicates the
         number of FIDs available on this platform. The feature is not available
         if this number is 0."
    ::= { vtssVlanConfigInterfaces 2 }

vtssVlanConfigInterfacesSvlEntry OBJECT-TYPE
    SYNTAX      VTSSVlanConfigInterfacesSvlEntry
    MAX-ACCESS  not-accessible
    STATUS      current
    DESCRIPTION
        "The table is indexed by VLAN ID"
    INDEX       { vtssVlanConfigInterfacesSvlVlanId }
    ::= { vtssVlanConfigInterfacesSvlTable 1 }

VTSSVlanConfigInterfacesSvlEntry ::= SEQUENCE {
    vtssVlanConfigInterfacesSvlVlanId    VTSSVlan,
    vtssVlanConfigInterfacesSvlFilterId  VTSSUnsigned16,
    vtssVlanConfigInterfacesSvlAction    VTSSRowEditorState
}

vtssVlanConfigInterfacesSvlVlanId OBJECT-TYPE
    SYNTAX      VTSSVlan
    MAX-ACCESS  accessible-for-notify
    STATUS      current
    DESCRIPTION
        "VLAN ID. Valid range is 1 - 4095."
    ::= { vtssVlanConfigInterfacesSvlEntry 1 }

vtssVlanConfigInterfacesSvlFilterId OBJECT-TYPE
    SYNTAX      VTSSUnsigned16
    MAX-ACCESS  read-write
    STATUS      current
    DESCRIPTION
        "Filter ID (FID) used in Shared VLAN Learning. Zero or more VLANs may
         map into the same FID."
    ::= { vtssVlanConfigInterfacesSvlEntry 2 }

vtssVlanConfigInterfacesSvlAction OBJECT-TYPE
    SYNTAX      VTSSRowEditorState
    MAX-ACCESS  read-write
    STATUS      current
    DESCRIPTION
        "Action"
    ::= { vtssVlanConfigInterfacesSvlEntry 100 }

vtssVlanConfigInterfacesSvlTableRowEditor OBJECT IDENTIFIER
    ::= { vtssVlanConfigInterfaces 3 }

vtssVlanConfigInterfacesSvlTableRowEditorVlanId OBJECT-TYPE
    SYNTAX      VTSSVlan
    MAX-ACCESS  read-write
    STATUS      current
    DESCRIPTION
        "VLAN ID. Valid range is 1 - 4095."
    ::= { vtssVlanConfigInterfacesSvlTableRowEditor 1 }

vtssVlanConfigInterfacesSvlTableRowEditorFilterId OBJECT-TYPE
    SYNTAX      VTSSUnsigned16
    MAX-ACCESS  read-write
    STATUS      current
    DESCRIPTION
        "Filter ID (FID) used in Shared VLAN Learning. Zero or more VLANs may
         map into the same FID."
    ::= { vtssVlanConfigInterfacesSvlTableRowEditor 2 }

vtssVlanConfigInterfacesSvlTableRowEditorAction OBJECT-TYPE
    SYNTAX      VTSSRowEditorState
    MAX-ACCESS  read-write
    STATUS      current
    DESCRIPTION
        "Action"
    ::= { vtssVlanConfigInterfacesSvlTableRowEditor 100 }

vtssVlanStatus OBJECT IDENTIFIER
    ::= { vtssVlanMibObjects 3 }

vtssVlanStatusInterfaces OBJECT IDENTIFIER
    ::= { vtssVlanStatus 1 }

vtssVlanStatusInterfacesTable OBJECT-TYPE
    SYNTAX      SEQUENCE OF VTSSVlanStatusInterfacesEntry
    MAX-ACCESS  not-accessible
    STATUS      current
    DESCRIPTION
        "Table of per-interface (port) status."
    ::= { vtssVlanStatusInterfaces 1 }

vtssVlanStatusInterfacesEntry OBJECT-TYPE
    SYNTAX      VTSSVlanStatusInterfacesEntry
    MAX-ACCESS  not-accessible
    STATUS      current
    DESCRIPTION
        "Each row contains the VLAN configuration for a port interface for a
         given VLAN user."
    INDEX       { vtssVlanStatusInterfacesIfIndex,
                  vtssVlanStatusInterfacesVlanUser }
    ::= { vtssVlanStatusInterfacesTable 1 }

VTSSVlanStatusInterfacesEntry ::= SEQUENCE {
    vtssVlanStatusInterfacesIfIndex            VTSSInterfaceIndex,
    vtssVlanStatusInterfacesVlanUser           VTSSVlanUserType,
    vtssVlanStatusInterfacesPvid               VTSSVlan,
    vtssVlanStatusInterfacesUvid               VTSSVlan,
    vtssVlanStatusInterfacesPortType           VTSSVlanPortType,
    vtssVlanStatusInterfacesIngressFiltering   TruthValue,
    vtssVlanStatusInterfacesIngressAcceptance  VTSSVlanIngressAcceptance,
    vtssVlanStatusInterfacesEgressTagging      VTSSVlanEgressTagging
}

vtssVlanStatusInterfacesIfIndex OBJECT-TYPE
    SYNTAX      VTSSInterfaceIndex
    MAX-ACCESS  accessible-for-notify
    STATUS      current
    DESCRIPTION
        "Logical interface index."
    ::= { vtssVlanStatusInterfacesEntry 1 }

vtssVlanStatusInterfacesVlanUser OBJECT-TYPE
    SYNTAX      VTSSVlanUserType
    MAX-ACCESS  accessible-for-notify
    STATUS      current
    DESCRIPTION
        "VLAN user."
    ::= { vtssVlanStatusInterfacesEntry 2 }

vtssVlanStatusInterfacesPvid OBJECT-TYPE
    SYNTAX      VTSSVlan
    MAX-ACCESS  read-only
    STATUS      current
    DESCRIPTION
        "Port VLAN ID set by this user."
    ::= { vtssVlanStatusInterfacesEntry 3 }

vtssVlanStatusInterfacesUvid OBJECT-TYPE
    SYNTAX      VTSSVlan
    MAX-ACCESS  read-only
    STATUS      current
    DESCRIPTION
        "Untagged VLAN ID set by a user. This may only be populated by non-admin
         users."
    ::= { vtssVlanStatusInterfacesEntry 4 }

vtssVlanStatusInterfacesPortType OBJECT-TYPE
    SYNTAX      VTSSVlanPortType
    MAX-ACCESS  read-only
    STATUS      current
    DESCRIPTION
        "VLAN Awareness and tag reaction set by this user."
    ::= { vtssVlanStatusInterfacesEntry 5 }

vtssVlanStatusInterfacesIngressFiltering OBJECT-TYPE
    SYNTAX      TruthValue
    MAX-ACCESS  read-only
    STATUS      current
    DESCRIPTION
        "Ingress filtering enabled or disabled by this user."
    ::= { vtssVlanStatusInterfacesEntry 6 }

vtssVlanStatusInterfacesIngressAcceptance OBJECT-TYPE
    SYNTAX      VTSSVlanIngressAcceptance
    MAX-ACCESS  read-only
    STATUS      current
    DESCRIPTION
        "VLAN tagging accepted upon ingress configured by this user."
    ::= { vtssVlanStatusInterfacesEntry 7 }

vtssVlanStatusInterfacesEgressTagging OBJECT-TYPE
    SYNTAX      VTSSVlanEgressTagging
    MAX-ACCESS  read-only
    STATUS      current
    DESCRIPTION
        "Egress tagging configured by this user."
    ::= { vtssVlanStatusInterfacesEntry 8 }

vtssVlanStatusMemberships OBJECT IDENTIFIER
    ::= { vtssVlanStatus 2 }

vtssVlanStatusMembershipsVlanTable OBJECT-TYPE
    SYNTAX      SEQUENCE OF VTSSVlanStatusMembershipsVlanEntry
    MAX-ACCESS  not-accessible
    STATUS      current
    DESCRIPTION
        "Table of per-VLAN, per-VLAN user port memberships."
    ::= { vtssVlanStatusMemberships 1 }

vtssVlanStatusMembershipsVlanEntry OBJECT-TYPE
    SYNTAX      VTSSVlanStatusMembershipsVlanEntry
    MAX-ACCESS  not-accessible
    STATUS      current
    DESCRIPTION
        "Each row contains a port list of VLAN memberships for a given VLAN and
         VLAN user.The table is sparsely populated, so if a VLAN user doesn't
         contribute, the row is non-existent."
    INDEX       { vtssVlanStatusMembershipsVlanVlanId,
                  vtssVlanStatusMembershipsVlanVlanUser }
    ::= { vtssVlanStatusMembershipsVlanTable 1 }

VTSSVlanStatusMembershipsVlanEntry ::= SEQUENCE {
    vtssVlanStatusMembershipsVlanVlanId    VTSSVlan,
    vtssVlanStatusMembershipsVlanVlanUser  VTSSVlanUserType,
    vtssVlanStatusMembershipsVlanPortList  VTSSPortList
}

vtssVlanStatusMembershipsVlanVlanId OBJECT-TYPE
    SYNTAX      VTSSVlan
    MAX-ACCESS  accessible-for-notify
    STATUS      current
    DESCRIPTION
        "VLAN ID. Valid range is 1 - 4095."
    ::= { vtssVlanStatusMembershipsVlanEntry 1 }

vtssVlanStatusMembershipsVlanVlanUser OBJECT-TYPE
    SYNTAX      VTSSVlanUserType
    MAX-ACCESS  accessible-for-notify
    STATUS      current
    DESCRIPTION
        "VLAN user."
    ::= { vtssVlanStatusMembershipsVlanEntry 2 }

vtssVlanStatusMembershipsVlanPortList OBJECT-TYPE
    SYNTAX      VTSSPortList
    MAX-ACCESS  read-only
    STATUS      current
    DESCRIPTION
        "Port list."
    ::= { vtssVlanStatusMembershipsVlanEntry 3 }

vtssVlanMibConformance OBJECT IDENTIFIER
    ::= { vtssVlanMib 2 }

vtssVlanMibCompliances OBJECT IDENTIFIER
    ::= { vtssVlanMibConformance 1 }

vtssVlanMibGroups OBJECT IDENTIFIER
    ::= { vtssVlanMibConformance 2 }

vtssVlanCapabilitiesInfoGroup OBJECT-GROUP
    OBJECTS     { vtssVlanCapabilitiesVlanIdMin,
                  vtssVlanCapabilitiesVlanIdMax,
                  vtssVlanCapabilitiesFidCnt,
                  vtssVlanCapabilitiesHasFlooding }
    STATUS      current
    DESCRIPTION
        "A collection of objects."
    ::= { vtssVlanMibGroups 1 }

vtssVlanConfigGlobalsMainInfoGroup OBJECT-GROUP
    OBJECTS     { vtssVlanConfigGlobalsMainCustomSPortEtherType,
                  vtssVlanConfigGlobalsMainAccessVlans0To1K,
                  vtssVlanConfigGlobalsMainAccessVlans1KTo2K,
                  vtssVlanConfigGlobalsMainAccessVlans2KTo3K,
                  vtssVlanConfigGlobalsMainAccessVlans3KTo4K }
    STATUS      current
    DESCRIPTION
        "A collection of objects."
    ::= { vtssVlanMibGroups 2 }

vtssVlanConfigGlobalsNameTableInfoGroup OBJECT-GROUP
    OBJECTS     { vtssVlanConfigGlobalsNameVlanId,
                  vtssVlanConfigGlobalsNameName }
    STATUS      current
    DESCRIPTION
        "A collection of objects."
    ::= { vtssVlanMibGroups 3 }

vtssVlanConfigGlobalsFloodingTableInfoGroup OBJECT-GROUP
    OBJECTS     { vtssVlanConfigGlobalsFloodingVlanId,
                  vtssVlanConfigGlobalsFloodingFlooding }
    STATUS      current
    DESCRIPTION
        "A collection of objects."
    ::= { vtssVlanMibGroups 4 }

vtssVlanConfigInterfacesTableInfoGroup OBJECT-GROUP
    OBJECTS     { vtssVlanConfigInterfacesIfIndex,
                  vtssVlanConfigInterfacesMode,
                  vtssVlanConfigInterfacesAccessVlan,
                  vtssVlanConfigInterfacesTrunkNativeVlan,
                  vtssVlanConfigInterfacesTrunkTagNativeVlan,
                  vtssVlanConfigInterfacesTrunkVlans0KTo1K,
                  vtssVlanConfigInterfacesTrunkVlans1KTo2K,
                  vtssVlanConfigInterfacesTrunkVlans2KTo3K,
                  vtssVlanConfigInterfacesTrunkVlans3KTo4K,
                  vtssVlanConfigInterfacesHybridNativeVlan,
                  vtssVlanConfigInterfacesHybridPortType,
                  vtssVlanConfigInterfacesHybridIngressFiltering,
                  vtssVlanConfigInterfacesHybridIngressAcceptance,
                  vtssVlanConfigInterfacesHybridEgressTagging,
                  vtssVlanConfigInterfacesHybridVlans0KTo1K,
                  vtssVlanConfigInterfacesHybridVlans1KTo2K,
                  vtssVlanConfigInterfacesHybridVlans2KTo3K,
                  vtssVlanConfigInterfacesHybridVlans3KTo4K,
                  vtssVlanConfigInterfacesForbiddenVlans0KTo1K,
                  vtssVlanConfigInterfacesForbiddenVlans1KTo2K,
                  vtssVlanConfigInterfacesForbiddenVlans2KTo3K,
                  vtssVlanConfigInterfacesForbiddenVlans3KTo4K }
    STATUS      current
    DESCRIPTION
        "A collection of objects."
    ::= { vtssVlanMibGroups 5 }

vtssVlanConfigInterfacesSvlTableInfoGroup OBJECT-GROUP
    OBJECTS     { vtssVlanConfigInterfacesSvlVlanId,
                  vtssVlanConfigInterfacesSvlFilterId,
                  vtssVlanConfigInterfacesSvlAction }
    STATUS      current
    DESCRIPTION
        "A collection of objects."
    ::= { vtssVlanMibGroups 6 }

vtssVlanConfigInterfacesSvlTableRowEditorInfoGroup OBJECT-GROUP
    OBJECTS     { vtssVlanConfigInterfacesSvlTableRowEditorVlanId,
                  vtssVlanConfigInterfacesSvlTableRowEditorFilterId,
                  vtssVlanConfigInterfacesSvlTableRowEditorAction }
    STATUS      current
    DESCRIPTION
        "A collection of objects."
    ::= { vtssVlanMibGroups 7 }

vtssVlanStatusInterfacesTableInfoGroup OBJECT-GROUP
    OBJECTS     { vtssVlanStatusInterfacesIfIndex,
                  vtssVlanStatusInterfacesVlanUser,
                  vtssVlanStatusInterfacesPvid,
                  vtssVlanStatusInterfacesUvid,
                  vtssVlanStatusInterfacesPortType,
                  vtssVlanStatusInterfacesIngressFiltering,
                  vtssVlanStatusInterfacesIngressAcceptance,
                  vtssVlanStatusInterfacesEgressTagging }
    STATUS      current
    DESCRIPTION
        "A collection of objects."
    ::= { vtssVlanMibGroups 8 }

vtssVlanStatusMembershipsVlanTableInfoGroup OBJECT-GROUP
    OBJECTS     { vtssVlanStatusMembershipsVlanVlanId,
                  vtssVlanStatusMembershipsVlanVlanUser,
                  vtssVlanStatusMembershipsVlanPortList }
    STATUS      current
    DESCRIPTION
        "A collection of objects."
    ::= { vtssVlanMibGroups 9 }

vtssVlanMibCompliance MODULE-COMPLIANCE
    STATUS      current
    DESCRIPTION
        "The compliance statement for the implementation."

    MODULE      -- this module

    MANDATORY-GROUPS { vtssVlanCapabilitiesInfoGroup,
                       vtssVlanConfigGlobalsMainInfoGroup,
                       vtssVlanConfigGlobalsNameTableInfoGroup,
                       vtssVlanConfigGlobalsFloodingTableInfoGroup,
                       vtssVlanConfigInterfacesTableInfoGroup,
                       vtssVlanConfigInterfacesSvlTableInfoGroup,
                       vtssVlanConfigInterfacesSvlTableRowEditorInfoGroup,
                       vtssVlanStatusInterfacesTableInfoGroup,
                       vtssVlanStatusMembershipsVlanTableInfoGroup }

    ::= { vtssVlanMibCompliances 1 }

END
