-- *****************************************************************
-- IPMC-SNOOPING-MIB:  Microsemi ENT private MIB
-- ****************************************************************

VTSS-IPMC-SNOOPING-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    IpAddress FROM SNMPv2-SMI
    Unsigned32 FROM SNMPv2-SMI
    TruthValue FROM SNMPv2-TC
    VTSSDisplayString FROM VTSS-TC
    VTSSInterfaceIndex FROM VTSS-TC
    VTSSIpmcFilterMode FROM VTSS-TC
    VTSSIpmcQuerierStatus FROM VTSS-TC
    VTSSPortList FROM VTSS-TC
    VTSSUnsigned8 FROM VTSS-TC
    ;

vtssIpmcSnoopingMib MODULE-IDENTITY
    LAST-UPDATED "202210210000Z"
    ORGANIZATION
        "Microsemi Corporation"
    CONTACT-INFO
        "Application support: http://www.microchip.com/support"
    DESCRIPTION
        "This is a private version of the IPMC Snooping MIB"
    REVISION    "202210210000Z"
    DESCRIPTION
        "Restructured entire MIB"
    REVISION    "201612130000Z"
    DESCRIPTION
        "Removed the add/delete methods for VLAN interfaces from IGMP/MLD"
    REVISION    "201407010000Z"
    DESCRIPTION
        "Initial version"
    ::= { vtssSwitchMgmt 69 }


VTSSIpmcSnoopingIgmpInterfaceCompatibilityEnum ::= TEXTUAL-CONVENTION
    STATUS      current
    DESCRIPTION
        "This enumeration indicates the version compatibility for IGMP snooping
         VLAN interface."
    SYNTAX      INTEGER { auto(0), igmpv1(1), igmpv2(2), igmpv3(3) }

VTSSIpmcSnoopingMldInterfaceCompatibilityEnum ::= TEXTUAL-CONVENTION
    STATUS      current
    DESCRIPTION
        "This enumeration indicates the version compatibility for MLD snooping
         VLAN interface."
    SYNTAX      INTEGER { auto(0), mldv1(1), mldv2(2) }

VTSSIpmcSnoopingRouterPortStatusEnum ::= TEXTUAL-CONVENTION
    STATUS      current
    DESCRIPTION
        "This enumeration indicates the router port status from IGMP/MLD
         snooping."
    SYNTAX      INTEGER { none(0), static(1), dynamic(2), both(3) }

vtssIpmcSnoopingMibObjects OBJECT IDENTIFIER
    ::= { vtssIpmcSnoopingMib 1 }

vtssIpmcSnoopingConfig OBJECT IDENTIFIER
    ::= { vtssIpmcSnoopingMibObjects 2 }

vtssIpmcSnoopingConfigIgmpGlobals OBJECT IDENTIFIER
    ::= { vtssIpmcSnoopingConfig 1 }

vtssIpmcSnoopingConfigIgmpGlobalsAdminState OBJECT-TYPE
    SYNTAX      TruthValue
    MAX-ACCESS  read-write
    STATUS      current
    DESCRIPTION
        "Enable/Disable the IGMP snooping global functionality."
    ::= { vtssIpmcSnoopingConfigIgmpGlobals 1 }

vtssIpmcSnoopingConfigIgmpGlobalsUnregisteredFlooding OBJECT-TYPE
    SYNTAX      TruthValue
    MAX-ACCESS  read-write
    STATUS      current
    DESCRIPTION
        "Enable/Disable the control for flooding unregistered IPv4 multicast
         traffic."
    ::= { vtssIpmcSnoopingConfigIgmpGlobals 2 }

vtssIpmcSnoopingConfigIgmpGlobalsSsmRangeAddress OBJECT-TYPE
    SYNTAX      IpAddress
    MAX-ACCESS  read-write
    STATUS      current
    DESCRIPTION
        "The address prefix value defined for IGMP SSM service model."
    ::= { vtssIpmcSnoopingConfigIgmpGlobals 3 }

vtssIpmcSnoopingConfigIgmpGlobalsSsmRangeMask OBJECT-TYPE
    SYNTAX      Unsigned32
    MAX-ACCESS  read-write
    STATUS      current
    DESCRIPTION
        "The address prefix length defined for MLD/IGMP SSM service model."
    ::= { vtssIpmcSnoopingConfigIgmpGlobals 4 }

vtssIpmcSnoopingConfigIgmpGlobalsProxy OBJECT-TYPE
    SYNTAX      TruthValue
    MAX-ACCESS  read-write
    STATUS      current
    DESCRIPTION
        "Enable/Disable the MLD/IGMP proxy functionality."
    ::= { vtssIpmcSnoopingConfigIgmpGlobals 5 }

vtssIpmcSnoopingConfigIgmpGlobalsLeaveProxy OBJECT-TYPE
    SYNTAX      TruthValue
    MAX-ACCESS  read-write
    STATUS      current
    DESCRIPTION
        "Enable/Disable the MLD/IGMP leave-proxy functionality."
    ::= { vtssIpmcSnoopingConfigIgmpGlobals 6 }

vtssIpmcSnoopingConfigIgmpPortTable OBJECT-TYPE
    SYNTAX      SEQUENCE OF VTSSIpmcSnoopingConfigIgmpPortEntry
    MAX-ACCESS  not-accessible
    STATUS      current
    DESCRIPTION
        "This is a table for managing extra IGMP snooping helper features per
         port basis"
    ::= { vtssIpmcSnoopingConfig 2 }

vtssIpmcSnoopingConfigIgmpPortEntry OBJECT-TYPE
    SYNTAX      VTSSIpmcSnoopingConfigIgmpPortEntry
    MAX-ACCESS  not-accessible
    STATUS      current
    DESCRIPTION
        "Each port has a set of parameters"
    INDEX       { vtssIpmcSnoopingConfigIgmpPortPortIndex }
    ::= { vtssIpmcSnoopingConfigIgmpPortTable 1 }

VTSSIpmcSnoopingConfigIgmpPortEntry ::= SEQUENCE {
    vtssIpmcSnoopingConfigIgmpPortPortIndex         VTSSInterfaceIndex,
    vtssIpmcSnoopingConfigIgmpPortAsRouterPort      VTSSUnsigned8,
    vtssIpmcSnoopingConfigIgmpPortDoFastLeave       TruthValue,
    vtssIpmcSnoopingConfigIgmpPortThrottlingNumber  Unsigned32,
    vtssIpmcSnoopingConfigIgmpPortFilteringProfile  VTSSDisplayString
}

vtssIpmcSnoopingConfigIgmpPortPortIndex OBJECT-TYPE
    SYNTAX      VTSSInterfaceIndex
    MAX-ACCESS  accessible-for-notify
    STATUS      current
    DESCRIPTION
        "Logical interface number of the physical port."
    ::= { vtssIpmcSnoopingConfigIgmpPortEntry 1 }

vtssIpmcSnoopingConfigIgmpPortAsRouterPort OBJECT-TYPE
    SYNTAX      VTSSUnsigned8
    MAX-ACCESS  read-write
    STATUS      current
    DESCRIPTION
        "Enable/Disable the IGMP/MLD static router port functionality."
    ::= { vtssIpmcSnoopingConfigIgmpPortEntry 2 }

vtssIpmcSnoopingConfigIgmpPortDoFastLeave OBJECT-TYPE
    SYNTAX      TruthValue
    MAX-ACCESS  read-write
    STATUS      current
    DESCRIPTION
        "Enable/Disable the IGMP/MLD fast leave functionality."
    ::= { vtssIpmcSnoopingConfigIgmpPortEntry 3 }

vtssIpmcSnoopingConfigIgmpPortThrottlingNumber OBJECT-TYPE
    SYNTAX      Unsigned32
    MAX-ACCESS  read-write
    STATUS      current
    DESCRIPTION
        "The maximum number of groups to be registered on the specific port."
    ::= { vtssIpmcSnoopingConfigIgmpPortEntry 4 }

vtssIpmcSnoopingConfigIgmpPortFilteringProfile OBJECT-TYPE
    SYNTAX      VTSSDisplayString (SIZE(0..16))
    MAX-ACCESS  read-write
    STATUS      current
    DESCRIPTION
        "The profile used for IGMP filtering per-port basis."
    ::= { vtssIpmcSnoopingConfigIgmpPortEntry 5 }

vtssIpmcSnoopingConfigIgmpInterfaceTable OBJECT-TYPE
    SYNTAX      SEQUENCE OF VTSSIpmcSnoopingConfigIgmpInterfaceEntry
    MAX-ACCESS  not-accessible
    STATUS      current
    DESCRIPTION
        "This is a table for managing IGMP Snooping VLAN interface entries."
    ::= { vtssIpmcSnoopingConfig 3 }

vtssIpmcSnoopingConfigIgmpInterfaceEntry OBJECT-TYPE
    SYNTAX      VTSSIpmcSnoopingConfigIgmpInterfaceEntry
    MAX-ACCESS  not-accessible
    STATUS      current
    DESCRIPTION
        "Each entry has a set of parameters"
    INDEX       { vtssIpmcSnoopingConfigIgmpInterfaceIfIndex }
    ::= { vtssIpmcSnoopingConfigIgmpInterfaceTable 1 }

VTSSIpmcSnoopingConfigIgmpInterfaceEntry ::= SEQUENCE {
    vtssIpmcSnoopingConfigIgmpInterfaceIfIndex          VTSSInterfaceIndex,
    vtssIpmcSnoopingConfigIgmpInterfaceAdminState       TruthValue,
    vtssIpmcSnoopingConfigIgmpInterfaceQuerierElection  TruthValue,
    vtssIpmcSnoopingConfigIgmpInterfaceQuerierAddress   IpAddress,
    vtssIpmcSnoopingConfigIgmpInterfaceCompatibility    VTSSIpmcSnoopingIgmpInterfaceCompatibilityEnum,
    vtssIpmcSnoopingConfigIgmpInterfacePriority         VTSSUnsigned8,
    vtssIpmcSnoopingConfigIgmpInterfaceRv               Unsigned32,
    vtssIpmcSnoopingConfigIgmpInterfaceQi               Unsigned32,
    vtssIpmcSnoopingConfigIgmpInterfaceQri              Unsigned32,
    vtssIpmcSnoopingConfigIgmpInterfaceLmqi             Unsigned32,
    vtssIpmcSnoopingConfigIgmpInterfaceUri              Unsigned32
}

vtssIpmcSnoopingConfigIgmpInterfaceIfIndex OBJECT-TYPE
    SYNTAX      VTSSInterfaceIndex
    MAX-ACCESS  accessible-for-notify
    STATUS      current
    DESCRIPTION
        "Logical interface number of the VLAN interface."
    ::= { vtssIpmcSnoopingConfigIgmpInterfaceEntry 1 }

vtssIpmcSnoopingConfigIgmpInterfaceAdminState OBJECT-TYPE
    SYNTAX      TruthValue
    MAX-ACCESS  read-write
    STATUS      current
    DESCRIPTION
        "Enable/Disable snooping on this VLAN."
    ::= { vtssIpmcSnoopingConfigIgmpInterfaceEntry 2 }

vtssIpmcSnoopingConfigIgmpInterfaceQuerierElection OBJECT-TYPE
    SYNTAX      TruthValue
    MAX-ACCESS  read-write
    STATUS      current
    DESCRIPTION
        "Enable/Disable the capability to run IGMP/MLD Querier election per-VLAN
         basis."
    ::= { vtssIpmcSnoopingConfigIgmpInterfaceEntry 3 }

vtssIpmcSnoopingConfigIgmpInterfaceQuerierAddress OBJECT-TYPE
    SYNTAX      IpAddress
    MAX-ACCESS  read-write
    STATUS      current
    DESCRIPTION
        "The static IPv4 source address of the specific IGMP interface for
         seding IGMP Query message with respect to IGMP Querier election."
    ::= { vtssIpmcSnoopingConfigIgmpInterfaceEntry 4 }

vtssIpmcSnoopingConfigIgmpInterfaceCompatibility OBJECT-TYPE
    SYNTAX      VTSSIpmcSnoopingIgmpInterfaceCompatibilityEnum
    MAX-ACCESS  read-write
    STATUS      current
    DESCRIPTION
        "The compatibility control for IGMP snooping to run the corresponding
         protocol version."
    ::= { vtssIpmcSnoopingConfigIgmpInterfaceEntry 5 }

vtssIpmcSnoopingConfigIgmpInterfacePriority OBJECT-TYPE
    SYNTAX      VTSSUnsigned8
    MAX-ACCESS  read-write
    STATUS      current
    DESCRIPTION
        "This setting is used as PCP value when transmitting tagged IGMP/MLD
         control frames."
    ::= { vtssIpmcSnoopingConfigIgmpInterfaceEntry 6 }

vtssIpmcSnoopingConfigIgmpInterfaceRv OBJECT-TYPE
    SYNTAX      Unsigned32
    MAX-ACCESS  read-write
    STATUS      current
    DESCRIPTION
        "This setting Robustness Variable is used to control IGMP/MLD protocol
         stack as stated in RFC-3376 8.1."
    ::= { vtssIpmcSnoopingConfigIgmpInterfaceEntry 7 }

vtssIpmcSnoopingConfigIgmpInterfaceQi OBJECT-TYPE
    SYNTAX      Unsigned32
    MAX-ACCESS  read-write
    STATUS      current
    DESCRIPTION
        "This setting Query Interval is used to control IGMP/MLD protocol stack
         as stated in RFC-3376 8.2."
    ::= { vtssIpmcSnoopingConfigIgmpInterfaceEntry 8 }

vtssIpmcSnoopingConfigIgmpInterfaceQri OBJECT-TYPE
    SYNTAX      Unsigned32
    MAX-ACCESS  read-write
    STATUS      current
    DESCRIPTION
        "This setting Query Response Interval is used to control IGMP/MLD
         protocol stack as stated in RFC-3376 8.3."
    ::= { vtssIpmcSnoopingConfigIgmpInterfaceEntry 9 }

vtssIpmcSnoopingConfigIgmpInterfaceLmqi OBJECT-TYPE
    SYNTAX      Unsigned32
    MAX-ACCESS  read-write
    STATUS      current
    DESCRIPTION
        "This setting Last Member Query Interval is used to control IGMP/MLD
         protocol stack as stated in RFC-3376 8.8."
    ::= { vtssIpmcSnoopingConfigIgmpInterfaceEntry 10 }

vtssIpmcSnoopingConfigIgmpInterfaceUri OBJECT-TYPE
    SYNTAX      Unsigned32
    MAX-ACCESS  read-write
    STATUS      current
    DESCRIPTION
        "This setting Unsolicited Report Interval is used to control IGMP/MLD
         protocol stack as stated in RFC-3376 8.11."
    ::= { vtssIpmcSnoopingConfigIgmpInterfaceEntry 11 }

vtssIpmcSnoopingConfigMldGlobals OBJECT IDENTIFIER
    ::= { vtssIpmcSnoopingConfig 5 }

vtssIpmcSnoopingConfigMldGlobalsAdminState OBJECT-TYPE
    SYNTAX      TruthValue
    MAX-ACCESS  read-write
    STATUS      current
    DESCRIPTION
        "Enable/Disable the IGMP snooping global functionality."
    ::= { vtssIpmcSnoopingConfigMldGlobals 1 }

vtssIpmcSnoopingConfigMldGlobalsUnregisteredFlooding OBJECT-TYPE
    SYNTAX      TruthValue
    MAX-ACCESS  read-write
    STATUS      current
    DESCRIPTION
        "Enable/Disable the control for flooding unregistered IPv4 multicast
         traffic."
    ::= { vtssIpmcSnoopingConfigMldGlobals 2 }

vtssIpmcSnoopingConfigMldGlobalsSsmRangeAddress OBJECT-TYPE
    SYNTAX      InetAddressIPv6
    MAX-ACCESS  read-write
    STATUS      current
    DESCRIPTION
        "The address prefix value defined for MLD SSM service model."
    ::= { vtssIpmcSnoopingConfigMldGlobals 3 }

vtssIpmcSnoopingConfigMldGlobalsSsmRangeMask OBJECT-TYPE
    SYNTAX      Unsigned32
    MAX-ACCESS  read-write
    STATUS      current
    DESCRIPTION
        "The address prefix length defined for MLD/IGMP SSM service model."
    ::= { vtssIpmcSnoopingConfigMldGlobals 4 }

vtssIpmcSnoopingConfigMldGlobalsProxy OBJECT-TYPE
    SYNTAX      TruthValue
    MAX-ACCESS  read-write
    STATUS      current
    DESCRIPTION
        "Enable/Disable the MLD/IGMP proxy functionality."
    ::= { vtssIpmcSnoopingConfigMldGlobals 5 }

vtssIpmcSnoopingConfigMldGlobalsLeaveProxy OBJECT-TYPE
    SYNTAX      TruthValue
    MAX-ACCESS  read-write
    STATUS      current
    DESCRIPTION
        "Enable/Disable the MLD/IGMP leave-proxy functionality."
    ::= { vtssIpmcSnoopingConfigMldGlobals 6 }

vtssIpmcSnoopingConfigMldPortTable OBJECT-TYPE
    SYNTAX      SEQUENCE OF VTSSIpmcSnoopingConfigMldPortEntry
    MAX-ACCESS  not-accessible
    STATUS      current
    DESCRIPTION
        "This is a table for managing extra MLD snooping helper features per
         port basis"
    ::= { vtssIpmcSnoopingConfig 6 }

vtssIpmcSnoopingConfigMldPortEntry OBJECT-TYPE
    SYNTAX      VTSSIpmcSnoopingConfigMldPortEntry
    MAX-ACCESS  not-accessible
    STATUS      current
    DESCRIPTION
        "Each port has a set of parameters"
    INDEX       { vtssIpmcSnoopingConfigMldPortPortIndex }
    ::= { vtssIpmcSnoopingConfigMldPortTable 1 }

VTSSIpmcSnoopingConfigMldPortEntry ::= SEQUENCE {
    vtssIpmcSnoopingConfigMldPortPortIndex         VTSSInterfaceIndex,
    vtssIpmcSnoopingConfigMldPortAsRouterPort      VTSSUnsigned8,
    vtssIpmcSnoopingConfigMldPortDoFastLeave       TruthValue,
    vtssIpmcSnoopingConfigMldPortThrottlingNumber  Unsigned32,
    vtssIpmcSnoopingConfigMldPortFilteringProfile  VTSSDisplayString
}

vtssIpmcSnoopingConfigMldPortPortIndex OBJECT-TYPE
    SYNTAX      VTSSInterfaceIndex
    MAX-ACCESS  accessible-for-notify
    STATUS      current
    DESCRIPTION
        "Logical interface number of the physical port."
    ::= { vtssIpmcSnoopingConfigMldPortEntry 1 }

vtssIpmcSnoopingConfigMldPortAsRouterPort OBJECT-TYPE
    SYNTAX      VTSSUnsigned8
    MAX-ACCESS  read-write
    STATUS      current
    DESCRIPTION
        "Enable/Disable the IGMP/MLD static router port functionality."
    ::= { vtssIpmcSnoopingConfigMldPortEntry 2 }

vtssIpmcSnoopingConfigMldPortDoFastLeave OBJECT-TYPE
    SYNTAX      TruthValue
    MAX-ACCESS  read-write
    STATUS      current
    DESCRIPTION
        "Enable/Disable the IGMP/MLD fast leave functionality."
    ::= { vtssIpmcSnoopingConfigMldPortEntry 3 }

vtssIpmcSnoopingConfigMldPortThrottlingNumber OBJECT-TYPE
    SYNTAX      Unsigned32
    MAX-ACCESS  read-write
    STATUS      current
    DESCRIPTION
        "The maximum number of groups to be registered on the specific port."
    ::= { vtssIpmcSnoopingConfigMldPortEntry 4 }

vtssIpmcSnoopingConfigMldPortFilteringProfile OBJECT-TYPE
    SYNTAX      VTSSDisplayString (SIZE(0..16))
    MAX-ACCESS  read-write
    STATUS      current
    DESCRIPTION
        "The profile used for IGMP filtering per-port basis."
    ::= { vtssIpmcSnoopingConfigMldPortEntry 5 }

vtssIpmcSnoopingConfigMldInterfaceTable OBJECT-TYPE
    SYNTAX      SEQUENCE OF VTSSIpmcSnoopingConfigMldInterfaceEntry
    MAX-ACCESS  not-accessible
    STATUS      current
    DESCRIPTION
        "This is a table for managing MLD Snooping VLAN interface entries."
    ::= { vtssIpmcSnoopingConfig 7 }

vtssIpmcSnoopingConfigMldInterfaceEntry OBJECT-TYPE
    SYNTAX      VTSSIpmcSnoopingConfigMldInterfaceEntry
    MAX-ACCESS  not-accessible
    STATUS      current
    DESCRIPTION
        "Each entry has a set of parameters"
    INDEX       { vtssIpmcSnoopingConfigMldInterfaceIfIndex }
    ::= { vtssIpmcSnoopingConfigMldInterfaceTable 1 }

VTSSIpmcSnoopingConfigMldInterfaceEntry ::= SEQUENCE {
    vtssIpmcSnoopingConfigMldInterfaceIfIndex          VTSSInterfaceIndex,
    vtssIpmcSnoopingConfigMldInterfaceAdminState       TruthValue,
    vtssIpmcSnoopingConfigMldInterfaceQuerierElection  TruthValue,
    vtssIpmcSnoopingConfigMldInterfaceCompatibility    VTSSIpmcSnoopingMldInterfaceCompatibilityEnum,
    vtssIpmcSnoopingConfigMldInterfacePriority         VTSSUnsigned8,
    vtssIpmcSnoopingConfigMldInterfaceRv               Unsigned32,
    vtssIpmcSnoopingConfigMldInterfaceQi               Unsigned32,
    vtssIpmcSnoopingConfigMldInterfaceQri              Unsigned32,
    vtssIpmcSnoopingConfigMldInterfaceLmqi             Unsigned32,
    vtssIpmcSnoopingConfigMldInterfaceUri              Unsigned32
}

vtssIpmcSnoopingConfigMldInterfaceIfIndex OBJECT-TYPE
    SYNTAX      VTSSInterfaceIndex
    MAX-ACCESS  accessible-for-notify
    STATUS      current
    DESCRIPTION
        "Logical interface number of the VLAN interface."
    ::= { vtssIpmcSnoopingConfigMldInterfaceEntry 1 }

vtssIpmcSnoopingConfigMldInterfaceAdminState OBJECT-TYPE
    SYNTAX      TruthValue
    MAX-ACCESS  read-write
    STATUS      current
    DESCRIPTION
        "Enable/Disable snooping on this VLAN."
    ::= { vtssIpmcSnoopingConfigMldInterfaceEntry 2 }

vtssIpmcSnoopingConfigMldInterfaceQuerierElection OBJECT-TYPE
    SYNTAX      TruthValue
    MAX-ACCESS  read-write
    STATUS      current
    DESCRIPTION
        "Enable/Disable the capability to run IGMP/MLD Querier election per-VLAN
         basis."
    ::= { vtssIpmcSnoopingConfigMldInterfaceEntry 3 }

vtssIpmcSnoopingConfigMldInterfaceCompatibility OBJECT-TYPE
    SYNTAX      VTSSIpmcSnoopingMldInterfaceCompatibilityEnum
    MAX-ACCESS  read-write
    STATUS      current
    DESCRIPTION
        "The compatibility control for MLD snooping to run the corresponding
         protocol version."
    ::= { vtssIpmcSnoopingConfigMldInterfaceEntry 5 }

vtssIpmcSnoopingConfigMldInterfacePriority OBJECT-TYPE
    SYNTAX      VTSSUnsigned8
    MAX-ACCESS  read-write
    STATUS      current
    DESCRIPTION
        "This setting is used as PCP value when transmitting tagged IGMP/MLD
         control frames."
    ::= { vtssIpmcSnoopingConfigMldInterfaceEntry 6 }

vtssIpmcSnoopingConfigMldInterfaceRv OBJECT-TYPE
    SYNTAX      Unsigned32
    MAX-ACCESS  read-write
    STATUS      current
    DESCRIPTION
        "This setting Robustness Variable is used to control IGMP/MLD protocol
         stack as stated in RFC-3376 8.1."
    ::= { vtssIpmcSnoopingConfigMldInterfaceEntry 7 }

vtssIpmcSnoopingConfigMldInterfaceQi OBJECT-TYPE
    SYNTAX      Unsigned32
    MAX-ACCESS  read-write
    STATUS      current
    DESCRIPTION
        "This setting Query Interval is used to control IGMP/MLD protocol stack
         as stated in RFC-3376 8.2."
    ::= { vtssIpmcSnoopingConfigMldInterfaceEntry 8 }

vtssIpmcSnoopingConfigMldInterfaceQri OBJECT-TYPE
    SYNTAX      Unsigned32
    MAX-ACCESS  read-write
    STATUS      current
    DESCRIPTION
        "This setting Query Response Interval is used to control IGMP/MLD
         protocol stack as stated in RFC-3376 8.3."
    ::= { vtssIpmcSnoopingConfigMldInterfaceEntry 9 }

vtssIpmcSnoopingConfigMldInterfaceLmqi OBJECT-TYPE
    SYNTAX      Unsigned32
    MAX-ACCESS  read-write
    STATUS      current
    DESCRIPTION
        "This setting Last Member Query Interval is used to control IGMP/MLD
         protocol stack as stated in RFC-3376 8.8."
    ::= { vtssIpmcSnoopingConfigMldInterfaceEntry 10 }

vtssIpmcSnoopingConfigMldInterfaceUri OBJECT-TYPE
    SYNTAX      Unsigned32
    MAX-ACCESS  read-write
    STATUS      current
    DESCRIPTION
        "This setting Unsolicited Report Interval is used to control IGMP/MLD
         protocol stack as stated in RFC-3376 8.11."
    ::= { vtssIpmcSnoopingConfigMldInterfaceEntry 11 }

vtssIpmcSnoopingStatus OBJECT IDENTIFIER
    ::= { vtssIpmcSnoopingMibObjects 3 }

vtssIpmcSnoopingStatusIgmpRouterPortTable OBJECT-TYPE
    SYNTAX      SEQUENCE OF VTSSIpmcSnoopingStatusIgmpRouterPortEntry
    MAX-ACCESS  not-accessible
    STATUS      current
    DESCRIPTION
        "This is a table for displaying the IGMP port status."
    ::= { vtssIpmcSnoopingStatus 2 }

vtssIpmcSnoopingStatusIgmpRouterPortEntry OBJECT-TYPE
    SYNTAX      VTSSIpmcSnoopingStatusIgmpRouterPortEntry
    MAX-ACCESS  not-accessible
    STATUS      current
    DESCRIPTION
        "Each entry has a set of parameters."
    INDEX       { vtssIpmcSnoopingStatusIgmpRouterPortPortIndex }
    ::= { vtssIpmcSnoopingStatusIgmpRouterPortTable 1 }

VTSSIpmcSnoopingStatusIgmpRouterPortEntry ::= SEQUENCE {
    vtssIpmcSnoopingStatusIgmpRouterPortPortIndex  VTSSInterfaceIndex,
    vtssIpmcSnoopingStatusIgmpRouterPortStatus     VTSSIpmcSnoopingRouterPortStatusEnum
}

vtssIpmcSnoopingStatusIgmpRouterPortPortIndex OBJECT-TYPE
    SYNTAX      VTSSInterfaceIndex
    MAX-ACCESS  accessible-for-notify
    STATUS      current
    DESCRIPTION
        "Logical interface number of the physical port."
    ::= { vtssIpmcSnoopingStatusIgmpRouterPortEntry 1 }

vtssIpmcSnoopingStatusIgmpRouterPortStatus OBJECT-TYPE
    SYNTAX      VTSSIpmcSnoopingRouterPortStatusEnum
    MAX-ACCESS  read-only
    STATUS      current
    DESCRIPTION
        "The IGMP/MLD snooping router port status."
    ::= { vtssIpmcSnoopingStatusIgmpRouterPortEntry 2 }

vtssIpmcSnoopingStatusIgmpVlanTable OBJECT-TYPE
    SYNTAX      SEQUENCE OF VTSSIpmcSnoopingStatusIgmpVlanEntry
    MAX-ACCESS  not-accessible
    STATUS      current
    DESCRIPTION
        "This is a table for displaying the per VLAN interface status in IGMP
         snooping configuration."
    ::= { vtssIpmcSnoopingStatus 3 }

vtssIpmcSnoopingStatusIgmpVlanEntry OBJECT-TYPE
    SYNTAX      VTSSIpmcSnoopingStatusIgmpVlanEntry
    MAX-ACCESS  not-accessible
    STATUS      current
    DESCRIPTION
        "Each entry has a set of parameters."
    INDEX       { vtssIpmcSnoopingStatusIgmpVlanIfIndex }
    ::= { vtssIpmcSnoopingStatusIgmpVlanTable 1 }

VTSSIpmcSnoopingStatusIgmpVlanEntry ::= SEQUENCE {
    vtssIpmcSnoopingStatusIgmpVlanIfIndex                 VTSSInterfaceIndex,
    vtssIpmcSnoopingStatusIgmpVlanQuerierStatus           VTSSIpmcQuerierStatus,
    vtssIpmcSnoopingStatusIgmpVlanActiveQuerierAddress    IpAddress,
    vtssIpmcSnoopingStatusIgmpVlanQuerierUptime           Unsigned32,
    vtssIpmcSnoopingStatusIgmpVlanQueryInterval           Unsigned32,
    vtssIpmcSnoopingStatusIgmpVlanQuerierExpiryTime       Unsigned32,
    vtssIpmcSnoopingStatusIgmpVlanQuerierVersion          VTSSUnsigned8,
    vtssIpmcSnoopingStatusIgmpVlanQuerierPresentTimeout   Unsigned32,
    vtssIpmcSnoopingStatusIgmpVlanHostVersion             VTSSUnsigned8,
    vtssIpmcSnoopingStatusIgmpVlanHostPresentTimeout      Unsigned32,
    vtssIpmcSnoopingStatusIgmpVlanCounterTxQuery          Unsigned32,
    vtssIpmcSnoopingStatusIgmpVlanCounterTxSpecificQuery  Unsigned32,
    vtssIpmcSnoopingStatusIgmpVlanCounterRxQuery          Unsigned32,
    vtssIpmcSnoopingStatusIgmpVlanCounterRxV1Join         Unsigned32,
    vtssIpmcSnoopingStatusIgmpVlanCounterRxV2Join         Unsigned32,
    vtssIpmcSnoopingStatusIgmpVlanCounterRxV2Leave        Unsigned32,
    vtssIpmcSnoopingStatusIgmpVlanCounterRxV3Join         Unsigned32,
    vtssIpmcSnoopingStatusIgmpVlanCounterRxErrors         Unsigned32
}

vtssIpmcSnoopingStatusIgmpVlanIfIndex OBJECT-TYPE
    SYNTAX      VTSSInterfaceIndex
    MAX-ACCESS  accessible-for-notify
    STATUS      current
    DESCRIPTION
        "Logical interface number of the VLAN interface."
    ::= { vtssIpmcSnoopingStatusIgmpVlanEntry 1 }

vtssIpmcSnoopingStatusIgmpVlanQuerierStatus OBJECT-TYPE
    SYNTAX      VTSSIpmcQuerierStatus
    MAX-ACCESS  read-only
    STATUS      current
    DESCRIPTION
        "The IGMP Querier status of this VLAN interface."
    ::= { vtssIpmcSnoopingStatusIgmpVlanEntry 2 }

vtssIpmcSnoopingStatusIgmpVlanActiveQuerierAddress OBJECT-TYPE
    SYNTAX      IpAddress
    MAX-ACCESS  read-only
    STATUS      current
    DESCRIPTION
        "The active IGMP Querier address on this VLAN interface."
    ::= { vtssIpmcSnoopingStatusIgmpVlanEntry 3 }

vtssIpmcSnoopingStatusIgmpVlanQuerierUptime OBJECT-TYPE
    SYNTAX      Unsigned32
    MAX-ACCESS  read-only
    STATUS      current
    DESCRIPTION
        "Number of seconds this node has acted as IGMP Querier on this VLAN
         interface."
    ::= { vtssIpmcSnoopingStatusIgmpVlanEntry 4 }

vtssIpmcSnoopingStatusIgmpVlanQueryInterval OBJECT-TYPE
    SYNTAX      Unsigned32
    MAX-ACCESS  read-only
    STATUS      current
    DESCRIPTION
        "Time left (in seconds) until next query is sent on this VLAN interface
         if we are the active querier."
    ::= { vtssIpmcSnoopingStatusIgmpVlanEntry 5 }

vtssIpmcSnoopingStatusIgmpVlanQuerierExpiryTime OBJECT-TYPE
    SYNTAX      Unsigned32
    MAX-ACCESS  read-only
    STATUS      current
    DESCRIPTION
        "Querier Expire Time as stated in RFC3376 section 8.5 on this VLAN
         interface."
    ::= { vtssIpmcSnoopingStatusIgmpVlanEntry 6 }

vtssIpmcSnoopingStatusIgmpVlanQuerierVersion OBJECT-TYPE
    SYNTAX      VTSSUnsigned8
    MAX-ACCESS  read-only
    STATUS      current
    DESCRIPTION
        "The current IGMP version that this VLAN interface behaves like when
         running IGMP protocol as a router."
    ::= { vtssIpmcSnoopingStatusIgmpVlanEntry 7 }

vtssIpmcSnoopingStatusIgmpVlanQuerierPresentTimeout OBJECT-TYPE
    SYNTAX      Unsigned32
    MAX-ACCESS  read-only
    STATUS      current
    DESCRIPTION
        "Older Version Querier Present Timeout as stated in RFC3376 section 8.12
         on this VLAN interface."
    ::= { vtssIpmcSnoopingStatusIgmpVlanEntry 8 }

vtssIpmcSnoopingStatusIgmpVlanHostVersion OBJECT-TYPE
    SYNTAX      VTSSUnsigned8
    MAX-ACCESS  read-only
    STATUS      current
    DESCRIPTION
        "Current IGMP compatibility protocol setting for listener ports in this
         VLAN."
    ::= { vtssIpmcSnoopingStatusIgmpVlanEntry 9 }

vtssIpmcSnoopingStatusIgmpVlanHostPresentTimeout OBJECT-TYPE
    SYNTAX      Unsigned32
    MAX-ACCESS  read-only
    STATUS      current
    DESCRIPTION
        "Old Version Host Present Interval as stated in RFC3376 section 8.13 on
         this VLAN interface."
    ::= { vtssIpmcSnoopingStatusIgmpVlanEntry 10 }

vtssIpmcSnoopingStatusIgmpVlanCounterTxQuery OBJECT-TYPE
    SYNTAX      Unsigned32
    MAX-ACCESS  read-only
    STATUS      current
    DESCRIPTION
        "Number of IGMP Query control frames transmitted on this VLAN interface."
    ::= { vtssIpmcSnoopingStatusIgmpVlanEntry 11 }

vtssIpmcSnoopingStatusIgmpVlanCounterTxSpecificQuery OBJECT-TYPE
    SYNTAX      Unsigned32
    MAX-ACCESS  read-only
    STATUS      current
    DESCRIPTION
        "Number of IGMP Group Query control frames transmitted on this VLAN
         interface."
    ::= { vtssIpmcSnoopingStatusIgmpVlanEntry 12 }

vtssIpmcSnoopingStatusIgmpVlanCounterRxQuery OBJECT-TYPE
    SYNTAX      Unsigned32
    MAX-ACCESS  read-only
    STATUS      current
    DESCRIPTION
        "Number of IGMP Query control frames received on this VLAN interface."
    ::= { vtssIpmcSnoopingStatusIgmpVlanEntry 13 }

vtssIpmcSnoopingStatusIgmpVlanCounterRxV1Join OBJECT-TYPE
    SYNTAX      Unsigned32
    MAX-ACCESS  read-only
    STATUS      current
    DESCRIPTION
        "Number of IGMPv1 Join frames received and processed on this VLAN
         interface."
    ::= { vtssIpmcSnoopingStatusIgmpVlanEntry 14 }

vtssIpmcSnoopingStatusIgmpVlanCounterRxV2Join OBJECT-TYPE
    SYNTAX      Unsigned32
    MAX-ACCESS  read-only
    STATUS      current
    DESCRIPTION
        "Number of IGMPv2 Join frames receives on this VLAN interface."
    ::= { vtssIpmcSnoopingStatusIgmpVlanEntry 15 }

vtssIpmcSnoopingStatusIgmpVlanCounterRxV2Leave OBJECT-TYPE
    SYNTAX      Unsigned32
    MAX-ACCESS  read-only
    STATUS      current
    DESCRIPTION
        "Number of IGMPv2 Leave frames received on this VLAN interface."
    ::= { vtssIpmcSnoopingStatusIgmpVlanEntry 16 }

vtssIpmcSnoopingStatusIgmpVlanCounterRxV3Join OBJECT-TYPE
    SYNTAX      Unsigned32
    MAX-ACCESS  read-only
    STATUS      current
    DESCRIPTION
        "Number of IGMPv3 Join frames received on this VLAN interface."
    ::= { vtssIpmcSnoopingStatusIgmpVlanEntry 17 }

vtssIpmcSnoopingStatusIgmpVlanCounterRxErrors OBJECT-TYPE
    SYNTAX      Unsigned32
    MAX-ACCESS  read-only
    STATUS      current
    DESCRIPTION
        "Number of invalid IGMP control frames received on this VLAN interface."
    ::= { vtssIpmcSnoopingStatusIgmpVlanEntry 18 }

vtssIpmcSnoopingStatusIgmpGroupAddressTable OBJECT-TYPE
    SYNTAX      SEQUENCE OF VTSSIpmcSnoopingStatusIgmpGroupAddressEntry
    MAX-ACCESS  not-accessible
    STATUS      current
    DESCRIPTION
        "This is a table for displaying the registered IPv4 multicast group
         address status from IGMP snooping."
    ::= { vtssIpmcSnoopingStatus 4 }

vtssIpmcSnoopingStatusIgmpGroupAddressEntry OBJECT-TYPE
    SYNTAX      VTSSIpmcSnoopingStatusIgmpGroupAddressEntry
    MAX-ACCESS  not-accessible
    STATUS      current
    DESCRIPTION
        "Each entry has a set of parameters."
    INDEX       { vtssIpmcSnoopingStatusIgmpGroupAddressIfIndex,
                  vtssIpmcSnoopingStatusIgmpGroupAddressGroupAddress }
    ::= { vtssIpmcSnoopingStatusIgmpGroupAddressTable 1 }

VTSSIpmcSnoopingStatusIgmpGroupAddressEntry ::= SEQUENCE {
    vtssIpmcSnoopingStatusIgmpGroupAddressIfIndex         VTSSInterfaceIndex,
    vtssIpmcSnoopingStatusIgmpGroupAddressGroupAddress    IpAddress,
    vtssIpmcSnoopingStatusIgmpGroupAddressMemberPorts     VTSSPortList,
    vtssIpmcSnoopingStatusIgmpGroupAddressHardwareSwitch  TruthValue
}

vtssIpmcSnoopingStatusIgmpGroupAddressIfIndex OBJECT-TYPE
    SYNTAX      VTSSInterfaceIndex
    MAX-ACCESS  accessible-for-notify
    STATUS      current
    DESCRIPTION
        "Logical interface number of the VLAN interface."
    ::= { vtssIpmcSnoopingStatusIgmpGroupAddressEntry 1 }

vtssIpmcSnoopingStatusIgmpGroupAddressGroupAddress OBJECT-TYPE
    SYNTAX      IpAddress
    MAX-ACCESS  accessible-for-notify
    STATUS      current
    DESCRIPTION
        "Assigned IPv4 multicast address."
    ::= { vtssIpmcSnoopingStatusIgmpGroupAddressEntry 2 }

vtssIpmcSnoopingStatusIgmpGroupAddressMemberPorts OBJECT-TYPE
    SYNTAX      VTSSPortList
    MAX-ACCESS  read-only
    STATUS      current
    DESCRIPTION
        "Contains the listener ports of this multicast address"
    ::= { vtssIpmcSnoopingStatusIgmpGroupAddressEntry 3 }

vtssIpmcSnoopingStatusIgmpGroupAddressHardwareSwitch OBJECT-TYPE
    SYNTAX      TruthValue
    MAX-ACCESS  read-only
    STATUS      current
    DESCRIPTION
        "If true, the chip contains an entry with this group address"
    ::= { vtssIpmcSnoopingStatusIgmpGroupAddressEntry 4 }

vtssIpmcSnoopingStatusIgmpGroupSrcListTable OBJECT-TYPE
    SYNTAX      SEQUENCE OF VTSSIpmcSnoopingStatusIgmpGroupSrcListEntry
    MAX-ACCESS  not-accessible
    STATUS      current
    DESCRIPTION
        "This is a table for displaying the address SFM (a.k.a Source List
         Multicast) status in source list of the registered IPv4 multicast group
         from IGMP snooping."
    ::= { vtssIpmcSnoopingStatus 5 }

vtssIpmcSnoopingStatusIgmpGroupSrcListEntry OBJECT-TYPE
    SYNTAX      VTSSIpmcSnoopingStatusIgmpGroupSrcListEntry
    MAX-ACCESS  not-accessible
    STATUS      current
    DESCRIPTION
        "Each entry has a set of parameters."
    INDEX       { vtssIpmcSnoopingStatusIgmpGroupSrcListIfIndex,
                  vtssIpmcSnoopingStatusIgmpGroupSrcListGroupAddress,
                  vtssIpmcSnoopingStatusIgmpGroupSrcListPortIndex,
                  vtssIpmcSnoopingStatusIgmpGroupSrcListHostAddress }
    ::= { vtssIpmcSnoopingStatusIgmpGroupSrcListTable 1 }

VTSSIpmcSnoopingStatusIgmpGroupSrcListEntry ::= SEQUENCE {
    vtssIpmcSnoopingStatusIgmpGroupSrcListIfIndex          VTSSInterfaceIndex,
    vtssIpmcSnoopingStatusIgmpGroupSrcListGroupAddress     IpAddress,
    vtssIpmcSnoopingStatusIgmpGroupSrcListPortIndex        VTSSInterfaceIndex,
    vtssIpmcSnoopingStatusIgmpGroupSrcListHostAddress      IpAddress,
    vtssIpmcSnoopingStatusIgmpGroupSrcListGroupFilterMode  VTSSIpmcFilterMode,
    vtssIpmcSnoopingStatusIgmpGroupSrcListFilterTimer      Unsigned32,
    vtssIpmcSnoopingStatusIgmpGroupSrcListSourceType       TruthValue,
    vtssIpmcSnoopingStatusIgmpGroupSrcListSourceTimer      Unsigned32,
    vtssIpmcSnoopingStatusIgmpGroupSrcListHardwareFilter   TruthValue
}

vtssIpmcSnoopingStatusIgmpGroupSrcListIfIndex OBJECT-TYPE
    SYNTAX      VTSSInterfaceIndex
    MAX-ACCESS  accessible-for-notify
    STATUS      current
    DESCRIPTION
        "Logical interface number of the VLAN interface."
    ::= { vtssIpmcSnoopingStatusIgmpGroupSrcListEntry 1 }

vtssIpmcSnoopingStatusIgmpGroupSrcListGroupAddress OBJECT-TYPE
    SYNTAX      IpAddress
    MAX-ACCESS  accessible-for-notify
    STATUS      current
    DESCRIPTION
        "Assigned IPv4 multicast address."
    ::= { vtssIpmcSnoopingStatusIgmpGroupSrcListEntry 2 }

vtssIpmcSnoopingStatusIgmpGroupSrcListPortIndex OBJECT-TYPE
    SYNTAX      VTSSInterfaceIndex
    MAX-ACCESS  accessible-for-notify
    STATUS      current
    DESCRIPTION
        "Logical interface number of the physical port."
    ::= { vtssIpmcSnoopingStatusIgmpGroupSrcListEntry 3 }

vtssIpmcSnoopingStatusIgmpGroupSrcListHostAddress OBJECT-TYPE
    SYNTAX      IpAddress
    MAX-ACCESS  accessible-for-notify
    STATUS      current
    DESCRIPTION
        "Assigned IPv4 source address."
    ::= { vtssIpmcSnoopingStatusIgmpGroupSrcListEntry 4 }

vtssIpmcSnoopingStatusIgmpGroupSrcListGroupFilterMode OBJECT-TYPE
    SYNTAX      VTSSIpmcFilterMode
    MAX-ACCESS  read-only
    STATUS      current
    DESCRIPTION
        "The filter mode of this multicast group on this port."
    ::= { vtssIpmcSnoopingStatusIgmpGroupSrcListEntry 5 }

vtssIpmcSnoopingStatusIgmpGroupSrcListFilterTimer OBJECT-TYPE
    SYNTAX      Unsigned32
    MAX-ACCESS  read-only
    STATUS      current
    DESCRIPTION
        "The number of seconds until this group on this port times out (only
         used if filter mode is EXCLUDE)."
    ::= { vtssIpmcSnoopingStatusIgmpGroupSrcListEntry 6 }

vtssIpmcSnoopingStatusIgmpGroupSrcListSourceType OBJECT-TYPE
    SYNTAX      TruthValue
    MAX-ACCESS  read-only
    STATUS      current
    DESCRIPTION
        "Indicates whether this source address is forwarding or not."
    ::= { vtssIpmcSnoopingStatusIgmpGroupSrcListEntry 7 }

vtssIpmcSnoopingStatusIgmpGroupSrcListSourceTimer OBJECT-TYPE
    SYNTAX      Unsigned32
    MAX-ACCESS  read-only
    STATUS      current
    DESCRIPTION
        "The number of seconds until this source times out."
    ::= { vtssIpmcSnoopingStatusIgmpGroupSrcListEntry 8 }

vtssIpmcSnoopingStatusIgmpGroupSrcListHardwareFilter OBJECT-TYPE
    SYNTAX      TruthValue
    MAX-ACCESS  read-only
    STATUS      current
    DESCRIPTION
        "If true, the chip contains an entry with this source address."
    ::= { vtssIpmcSnoopingStatusIgmpGroupSrcListEntry 9 }

vtssIpmcSnoopingStatusMldRouterPortTable OBJECT-TYPE
    SYNTAX      SEQUENCE OF VTSSIpmcSnoopingStatusMldRouterPortEntry
    MAX-ACCESS  not-accessible
    STATUS      current
    DESCRIPTION
        "This is a table for displaying the MLD router port status."
    ::= { vtssIpmcSnoopingStatus 6 }

vtssIpmcSnoopingStatusMldRouterPortEntry OBJECT-TYPE
    SYNTAX      VTSSIpmcSnoopingStatusMldRouterPortEntry
    MAX-ACCESS  not-accessible
    STATUS      current
    DESCRIPTION
        "Each entry has a set of parameters."
    INDEX       { vtssIpmcSnoopingStatusMldRouterPortPortIndex }
    ::= { vtssIpmcSnoopingStatusMldRouterPortTable 1 }

VTSSIpmcSnoopingStatusMldRouterPortEntry ::= SEQUENCE {
    vtssIpmcSnoopingStatusMldRouterPortPortIndex  VTSSInterfaceIndex,
    vtssIpmcSnoopingStatusMldRouterPortStatus     VTSSIpmcSnoopingRouterPortStatusEnum
}

vtssIpmcSnoopingStatusMldRouterPortPortIndex OBJECT-TYPE
    SYNTAX      VTSSInterfaceIndex
    MAX-ACCESS  accessible-for-notify
    STATUS      current
    DESCRIPTION
        "Logical interface number of the physical port."
    ::= { vtssIpmcSnoopingStatusMldRouterPortEntry 1 }

vtssIpmcSnoopingStatusMldRouterPortStatus OBJECT-TYPE
    SYNTAX      VTSSIpmcSnoopingRouterPortStatusEnum
    MAX-ACCESS  read-only
    STATUS      current
    DESCRIPTION
        "The IGMP/MLD snooping router port status."
    ::= { vtssIpmcSnoopingStatusMldRouterPortEntry 2 }

vtssIpmcSnoopingStatusMldVlanTable OBJECT-TYPE
    SYNTAX      SEQUENCE OF VTSSIpmcSnoopingStatusMldVlanEntry
    MAX-ACCESS  not-accessible
    STATUS      current
    DESCRIPTION
        "This is a table for displaying the per VLAN interface status in MLD
         snooping configuration."
    ::= { vtssIpmcSnoopingStatus 7 }

vtssIpmcSnoopingStatusMldVlanEntry OBJECT-TYPE
    SYNTAX      VTSSIpmcSnoopingStatusMldVlanEntry
    MAX-ACCESS  not-accessible
    STATUS      current
    DESCRIPTION
        "Each entry has a set of parameters."
    INDEX       { vtssIpmcSnoopingStatusMldVlanIfIndex }
    ::= { vtssIpmcSnoopingStatusMldVlanTable 1 }

VTSSIpmcSnoopingStatusMldVlanEntry ::= SEQUENCE {
    vtssIpmcSnoopingStatusMldVlanIfIndex                 VTSSInterfaceIndex,
    vtssIpmcSnoopingStatusMldVlanQuerierStatus           VTSSIpmcQuerierStatus,
    vtssIpmcSnoopingStatusMldVlanActiveQuerierAddress    InetAddressIPv6,
    vtssIpmcSnoopingStatusMldVlanQuerierUptime           Unsigned32,
    vtssIpmcSnoopingStatusMldVlanQueryInterval           Unsigned32,
    vtssIpmcSnoopingStatusMldVlanQuerierExpiryTime       Unsigned32,
    vtssIpmcSnoopingStatusMldVlanQuerierVersion          VTSSUnsigned8,
    vtssIpmcSnoopingStatusMldVlanQuerierPresentTimeout   Unsigned32,
    vtssIpmcSnoopingStatusMldVlanHostVersion             VTSSUnsigned8,
    vtssIpmcSnoopingStatusMldVlanHostPresentTimeout      Unsigned32,
    vtssIpmcSnoopingStatusMldVlanCounterTxQuery          Unsigned32,
    vtssIpmcSnoopingStatusMldVlanCounterTxSpecificQuery  Unsigned32,
    vtssIpmcSnoopingStatusMldVlanCounterRxQuery          Unsigned32,
    vtssIpmcSnoopingStatusMldVlanCounterRxV1Report       Unsigned32,
    vtssIpmcSnoopingStatusMldVlanCounterRxV1Done         Unsigned32,
    vtssIpmcSnoopingStatusMldVlanCounterRxV2Report       Unsigned32,
    vtssIpmcSnoopingStatusMldVlanCounterRxErrors         Unsigned32
}

vtssIpmcSnoopingStatusMldVlanIfIndex OBJECT-TYPE
    SYNTAX      VTSSInterfaceIndex
    MAX-ACCESS  accessible-for-notify
    STATUS      current
    DESCRIPTION
        "Logical interface number of the VLAN interface."
    ::= { vtssIpmcSnoopingStatusMldVlanEntry 1 }

vtssIpmcSnoopingStatusMldVlanQuerierStatus OBJECT-TYPE
    SYNTAX      VTSSIpmcQuerierStatus
    MAX-ACCESS  read-only
    STATUS      current
    DESCRIPTION
        "The MLD Querier status of this VLAN interface."
    ::= { vtssIpmcSnoopingStatusMldVlanEntry 2 }

vtssIpmcSnoopingStatusMldVlanActiveQuerierAddress OBJECT-TYPE
    SYNTAX      InetAddressIPv6
    MAX-ACCESS  read-only
    STATUS      current
    DESCRIPTION
        "The active MLD Querier address on this VLAN interface."
    ::= { vtssIpmcSnoopingStatusMldVlanEntry 3 }

vtssIpmcSnoopingStatusMldVlanQuerierUptime OBJECT-TYPE
    SYNTAX      Unsigned32
    MAX-ACCESS  read-only
    STATUS      current
    DESCRIPTION
        "Number of seconds this node has acted as MLD Querier on this VLAN
         interface."
    ::= { vtssIpmcSnoopingStatusMldVlanEntry 4 }

vtssIpmcSnoopingStatusMldVlanQueryInterval OBJECT-TYPE
    SYNTAX      Unsigned32
    MAX-ACCESS  read-only
    STATUS      current
    DESCRIPTION
        "Time left (in seconds) until next query is sent on this VLAN interface
         if we are the active querier."
    ::= { vtssIpmcSnoopingStatusMldVlanEntry 5 }

vtssIpmcSnoopingStatusMldVlanQuerierExpiryTime OBJECT-TYPE
    SYNTAX      Unsigned32
    MAX-ACCESS  read-only
    STATUS      current
    DESCRIPTION
        "Querier Expire Time as stated in RFC3810 section 9.5 on this VLAN
         interface."
    ::= { vtssIpmcSnoopingStatusMldVlanEntry 6 }

vtssIpmcSnoopingStatusMldVlanQuerierVersion OBJECT-TYPE
    SYNTAX      VTSSUnsigned8
    MAX-ACCESS  read-only
    STATUS      current
    DESCRIPTION
        "The current MLD version that this VLAN interface behaves like when
         running MLD protocol as a router."
    ::= { vtssIpmcSnoopingStatusMldVlanEntry 7 }

vtssIpmcSnoopingStatusMldVlanQuerierPresentTimeout OBJECT-TYPE
    SYNTAX      Unsigned32
    MAX-ACCESS  read-only
    STATUS      current
    DESCRIPTION
        "Older Version Querier Present Timeout as stated in RFC3810 section 9.12
         on this VLAN interface."
    ::= { vtssIpmcSnoopingStatusMldVlanEntry 8 }

vtssIpmcSnoopingStatusMldVlanHostVersion OBJECT-TYPE
    SYNTAX      VTSSUnsigned8
    MAX-ACCESS  read-only
    STATUS      current
    DESCRIPTION
        "Current MLD compatibility protocol setting for listener ports in this
         VLAN."
    ::= { vtssIpmcSnoopingStatusMldVlanEntry 9 }

vtssIpmcSnoopingStatusMldVlanHostPresentTimeout OBJECT-TYPE
    SYNTAX      Unsigned32
    MAX-ACCESS  read-only
    STATUS      current
    DESCRIPTION
        "Old Version Host Present Interval as stated in RFC3810 section 9.13 on
         this VLAN interface."
    ::= { vtssIpmcSnoopingStatusMldVlanEntry 10 }

vtssIpmcSnoopingStatusMldVlanCounterTxQuery OBJECT-TYPE
    SYNTAX      Unsigned32
    MAX-ACCESS  read-only
    STATUS      current
    DESCRIPTION
        "Number of MLD Query control frames transmitted on this VLAN interface."
    ::= { vtssIpmcSnoopingStatusMldVlanEntry 11 }

vtssIpmcSnoopingStatusMldVlanCounterTxSpecificQuery OBJECT-TYPE
    SYNTAX      Unsigned32
    MAX-ACCESS  read-only
    STATUS      current
    DESCRIPTION
        "Number of MLD Group Query control frames transmitted on this VLAN
         interface."
    ::= { vtssIpmcSnoopingStatusMldVlanEntry 12 }

vtssIpmcSnoopingStatusMldVlanCounterRxQuery OBJECT-TYPE
    SYNTAX      Unsigned32
    MAX-ACCESS  read-only
    STATUS      current
    DESCRIPTION
        "Number of MLD Query control frames received on this VLAN interface."
    ::= { vtssIpmcSnoopingStatusMldVlanEntry 13 }

vtssIpmcSnoopingStatusMldVlanCounterRxV1Report OBJECT-TYPE
    SYNTAX      Unsigned32
    MAX-ACCESS  read-only
    STATUS      current
    DESCRIPTION
        "Number of MLDv1 Report frames received on this VLAN interface."
    ::= { vtssIpmcSnoopingStatusMldVlanEntry 14 }

vtssIpmcSnoopingStatusMldVlanCounterRxV1Done OBJECT-TYPE
    SYNTAX      Unsigned32
    MAX-ACCESS  read-only
    STATUS      current
    DESCRIPTION
        "Number of MLDv1 Done frames received on this VLAN interface."
    ::= { vtssIpmcSnoopingStatusMldVlanEntry 15 }

vtssIpmcSnoopingStatusMldVlanCounterRxV2Report OBJECT-TYPE
    SYNTAX      Unsigned32
    MAX-ACCESS  read-only
    STATUS      current
    DESCRIPTION
        "Number of MLDv2 Report frames received on this VLAN interface."
    ::= { vtssIpmcSnoopingStatusMldVlanEntry 16 }

vtssIpmcSnoopingStatusMldVlanCounterRxErrors OBJECT-TYPE
    SYNTAX      Unsigned32
    MAX-ACCESS  read-only
    STATUS      current
    DESCRIPTION
        "Number of invalid MLD control frames received on this VLAN interface."
    ::= { vtssIpmcSnoopingStatusMldVlanEntry 17 }

vtssIpmcSnoopingStatusMldGroupAddressTable OBJECT-TYPE
    SYNTAX      SEQUENCE OF VTSSIpmcSnoopingStatusMldGroupAddressEntry
    MAX-ACCESS  not-accessible
    STATUS      current
    DESCRIPTION
        "This is a table for displaying the registered IPv6 multicast group
         address status from MLD snooping."
    ::= { vtssIpmcSnoopingStatus 8 }

vtssIpmcSnoopingStatusMldGroupAddressEntry OBJECT-TYPE
    SYNTAX      VTSSIpmcSnoopingStatusMldGroupAddressEntry
    MAX-ACCESS  not-accessible
    STATUS      current
    DESCRIPTION
        "Each entry has a set of parameters."
    INDEX       { vtssIpmcSnoopingStatusMldGroupAddressIfIndex,
                  vtssIpmcSnoopingStatusMldGroupAddressGroupAddress }
    ::= { vtssIpmcSnoopingStatusMldGroupAddressTable 1 }

VTSSIpmcSnoopingStatusMldGroupAddressEntry ::= SEQUENCE {
    vtssIpmcSnoopingStatusMldGroupAddressIfIndex         VTSSInterfaceIndex,
    vtssIpmcSnoopingStatusMldGroupAddressGroupAddress    InetAddressIPv6,
    vtssIpmcSnoopingStatusMldGroupAddressMemberPorts     VTSSPortList,
    vtssIpmcSnoopingStatusMldGroupAddressHardwareSwitch  TruthValue
}

vtssIpmcSnoopingStatusMldGroupAddressIfIndex OBJECT-TYPE
    SYNTAX      VTSSInterfaceIndex
    MAX-ACCESS  accessible-for-notify
    STATUS      current
    DESCRIPTION
        "Logical interface number of the VLAN interface."
    ::= { vtssIpmcSnoopingStatusMldGroupAddressEntry 1 }

vtssIpmcSnoopingStatusMldGroupAddressGroupAddress OBJECT-TYPE
    SYNTAX      InetAddressIPv6
    MAX-ACCESS  accessible-for-notify
    STATUS      current
    DESCRIPTION
        "Assigned IPv6 multicast address."
    ::= { vtssIpmcSnoopingStatusMldGroupAddressEntry 2 }

vtssIpmcSnoopingStatusMldGroupAddressMemberPorts OBJECT-TYPE
    SYNTAX      VTSSPortList
    MAX-ACCESS  read-only
    STATUS      current
    DESCRIPTION
        "Contains the listener ports of this multicast address"
    ::= { vtssIpmcSnoopingStatusMldGroupAddressEntry 3 }

vtssIpmcSnoopingStatusMldGroupAddressHardwareSwitch OBJECT-TYPE
    SYNTAX      TruthValue
    MAX-ACCESS  read-only
    STATUS      current
    DESCRIPTION
        "If true, the chip contains an entry with this group address"
    ::= { vtssIpmcSnoopingStatusMldGroupAddressEntry 4 }

vtssIpmcSnoopingStatusMldGroupSrcListTable OBJECT-TYPE
    SYNTAX      SEQUENCE OF VTSSIpmcSnoopingStatusMldGroupSrcListEntry
    MAX-ACCESS  not-accessible
    STATUS      current
    DESCRIPTION
        "This is a table for displaying the address SFM (a.k.a Source List
         Multicast) status in source list of the registered IPv6 multicast group
         from MLD snooping."
    ::= { vtssIpmcSnoopingStatus 9 }

vtssIpmcSnoopingStatusMldGroupSrcListEntry OBJECT-TYPE
    SYNTAX      VTSSIpmcSnoopingStatusMldGroupSrcListEntry
    MAX-ACCESS  not-accessible
    STATUS      current
    DESCRIPTION
        "Each entry has a set of parameters."
    INDEX       { vtssIpmcSnoopingStatusMldGroupSrcListIfIndex,
                  vtssIpmcSnoopingStatusMldGroupSrcListGroupAddress,
                  vtssIpmcSnoopingStatusMldGroupSrcListPortIndex,
                  vtssIpmcSnoopingStatusMldGroupSrcListHostAddress }
    ::= { vtssIpmcSnoopingStatusMldGroupSrcListTable 1 }

VTSSIpmcSnoopingStatusMldGroupSrcListEntry ::= SEQUENCE {
    vtssIpmcSnoopingStatusMldGroupSrcListIfIndex          VTSSInterfaceIndex,
    vtssIpmcSnoopingStatusMldGroupSrcListGroupAddress     InetAddressIPv6,
    vtssIpmcSnoopingStatusMldGroupSrcListPortIndex        VTSSInterfaceIndex,
    vtssIpmcSnoopingStatusMldGroupSrcListHostAddress      InetAddressIPv6,
    vtssIpmcSnoopingStatusMldGroupSrcListGroupFilterMode  VTSSIpmcFilterMode,
    vtssIpmcSnoopingStatusMldGroupSrcListFilterTimer      Unsigned32,
    vtssIpmcSnoopingStatusMldGroupSrcListSourceType       TruthValue,
    vtssIpmcSnoopingStatusMldGroupSrcListSourceTimer      Unsigned32,
    vtssIpmcSnoopingStatusMldGroupSrcListHardwareFilter   TruthValue
}

vtssIpmcSnoopingStatusMldGroupSrcListIfIndex OBJECT-TYPE
    SYNTAX      VTSSInterfaceIndex
    MAX-ACCESS  accessible-for-notify
    STATUS      current
    DESCRIPTION
        "Logical interface number of the VLAN interface."
    ::= { vtssIpmcSnoopingStatusMldGroupSrcListEntry 1 }

vtssIpmcSnoopingStatusMldGroupSrcListGroupAddress OBJECT-TYPE
    SYNTAX      InetAddressIPv6
    MAX-ACCESS  accessible-for-notify
    STATUS      current
    DESCRIPTION
        "Assigned IPv6 multicast address."
    ::= { vtssIpmcSnoopingStatusMldGroupSrcListEntry 2 }

vtssIpmcSnoopingStatusMldGroupSrcListPortIndex OBJECT-TYPE
    SYNTAX      VTSSInterfaceIndex
    MAX-ACCESS  accessible-for-notify
    STATUS      current
    DESCRIPTION
        "Logical interface number of the physical port."
    ::= { vtssIpmcSnoopingStatusMldGroupSrcListEntry 3 }

vtssIpmcSnoopingStatusMldGroupSrcListHostAddress OBJECT-TYPE
    SYNTAX      InetAddressIPv6
    MAX-ACCESS  accessible-for-notify
    STATUS      current
    DESCRIPTION
        "Assigned IPv6 source address."
    ::= { vtssIpmcSnoopingStatusMldGroupSrcListEntry 4 }

vtssIpmcSnoopingStatusMldGroupSrcListGroupFilterMode OBJECT-TYPE
    SYNTAX      VTSSIpmcFilterMode
    MAX-ACCESS  read-only
    STATUS      current
    DESCRIPTION
        "The filter mode of this multicast group on this port."
    ::= { vtssIpmcSnoopingStatusMldGroupSrcListEntry 5 }

vtssIpmcSnoopingStatusMldGroupSrcListFilterTimer OBJECT-TYPE
    SYNTAX      Unsigned32
    MAX-ACCESS  read-only
    STATUS      current
    DESCRIPTION
        "The number of seconds until this group on this port times out (only
         used if filter mode is EXCLUDE)."
    ::= { vtssIpmcSnoopingStatusMldGroupSrcListEntry 6 }

vtssIpmcSnoopingStatusMldGroupSrcListSourceType OBJECT-TYPE
    SYNTAX      TruthValue
    MAX-ACCESS  read-only
    STATUS      current
    DESCRIPTION
        "Indicates whether this source address is forwarding or not."
    ::= { vtssIpmcSnoopingStatusMldGroupSrcListEntry 7 }

vtssIpmcSnoopingStatusMldGroupSrcListSourceTimer OBJECT-TYPE
    SYNTAX      Unsigned32
    MAX-ACCESS  read-only
    STATUS      current
    DESCRIPTION
        "The number of seconds until this source times out."
    ::= { vtssIpmcSnoopingStatusMldGroupSrcListEntry 8 }

vtssIpmcSnoopingStatusMldGroupSrcListHardwareFilter OBJECT-TYPE
    SYNTAX      TruthValue
    MAX-ACCESS  read-only
    STATUS      current
    DESCRIPTION
        "If true, the chip contains an entry with this source address."
    ::= { vtssIpmcSnoopingStatusMldGroupSrcListEntry 9 }

vtssIpmcSnoopingControl OBJECT IDENTIFIER
    ::= { vtssIpmcSnoopingMibObjects 4 }

vtssIpmcSnoopingControlStatistics OBJECT IDENTIFIER
    ::= { vtssIpmcSnoopingControl 1 }

vtssIpmcSnoopingControlStatisticsIgmpClearByIfIndex OBJECT IDENTIFIER
    ::= { vtssIpmcSnoopingControlStatistics 1 }

vtssIpmcSnoopingControlStatisticsIgmpClearByIfIndexIfIndex OBJECT-TYPE
    SYNTAX      VTSSInterfaceIndex
    MAX-ACCESS  read-write
    STATUS      current
    DESCRIPTION
        "Logical interface number of the VLAN interface."
    ::= { vtssIpmcSnoopingControlStatisticsIgmpClearByIfIndex 1 }

vtssIpmcSnoopingControlStatisticsIgmpClearByIfIndexClear OBJECT-TYPE
    SYNTAX      TruthValue
    MAX-ACCESS  read-write
    STATUS      current
    DESCRIPTION
        "Set to TRUE to clear the counters of this VLAN."
    ::= { vtssIpmcSnoopingControlStatisticsIgmpClearByIfIndex 4 }

vtssIpmcSnoopingControlStatisticsMldClearByIfIndex OBJECT IDENTIFIER
    ::= { vtssIpmcSnoopingControlStatistics 2 }

vtssIpmcSnoopingControlStatisticsMldClearByIfIndexIfIndex OBJECT-TYPE
    SYNTAX      VTSSInterfaceIndex
    MAX-ACCESS  read-write
    STATUS      current
    DESCRIPTION
        "Logical interface number of the VLAN interface."
    ::= { vtssIpmcSnoopingControlStatisticsMldClearByIfIndex 1 }

vtssIpmcSnoopingControlStatisticsMldClearByIfIndexClear OBJECT-TYPE
    SYNTAX      TruthValue
    MAX-ACCESS  read-write
    STATUS      current
    DESCRIPTION
        "Set to TRUE to clear the counters of this VLAN."
    ::= { vtssIpmcSnoopingControlStatisticsMldClearByIfIndex 4 }

vtssIpmcSnoopingMibConformance OBJECT IDENTIFIER
    ::= { vtssIpmcSnoopingMib 2 }

vtssIpmcSnoopingMibCompliances OBJECT IDENTIFIER
    ::= { vtssIpmcSnoopingMibConformance 1 }

vtssIpmcSnoopingMibGroups OBJECT IDENTIFIER
    ::= { vtssIpmcSnoopingMibConformance 2 }

vtssIpmcSnoopingConfigIgmpGlobalsInfoGroup OBJECT-GROUP
    OBJECTS     { vtssIpmcSnoopingConfigIgmpGlobalsAdminState,
                  vtssIpmcSnoopingConfigIgmpGlobalsUnregisteredFlooding,
                  vtssIpmcSnoopingConfigIgmpGlobalsSsmRangeAddress,
                  vtssIpmcSnoopingConfigIgmpGlobalsSsmRangeMask,
                  vtssIpmcSnoopingConfigIgmpGlobalsProxy,
                  vtssIpmcSnoopingConfigIgmpGlobalsLeaveProxy }
    STATUS      current
    DESCRIPTION
        "A collection of objects."
    ::= { vtssIpmcSnoopingMibGroups 1 }

vtssIpmcSnoopingConfigIgmpPortTableInfoGroup OBJECT-GROUP
    OBJECTS     { vtssIpmcSnoopingConfigIgmpPortPortIndex,
                  vtssIpmcSnoopingConfigIgmpPortAsRouterPort,
                  vtssIpmcSnoopingConfigIgmpPortDoFastLeave,
                  vtssIpmcSnoopingConfigIgmpPortThrottlingNumber,
                  vtssIpmcSnoopingConfigIgmpPortFilteringProfile }
    STATUS      current
    DESCRIPTION
        "A collection of objects."
    ::= { vtssIpmcSnoopingMibGroups 2 }

vtssIpmcSnoopingConfigIgmpInterfaceTableInfoGroup OBJECT-GROUP
    OBJECTS     { vtssIpmcSnoopingConfigIgmpInterfaceIfIndex,
                  vtssIpmcSnoopingConfigIgmpInterfaceAdminState,
                  vtssIpmcSnoopingConfigIgmpInterfaceQuerierElection,
                  vtssIpmcSnoopingConfigIgmpInterfaceQuerierAddress,
                  vtssIpmcSnoopingConfigIgmpInterfaceCompatibility,
                  vtssIpmcSnoopingConfigIgmpInterfacePriority,
                  vtssIpmcSnoopingConfigIgmpInterfaceRv,
                  vtssIpmcSnoopingConfigIgmpInterfaceQi,
                  vtssIpmcSnoopingConfigIgmpInterfaceQri,
                  vtssIpmcSnoopingConfigIgmpInterfaceLmqi,
                  vtssIpmcSnoopingConfigIgmpInterfaceUri }
    STATUS      current
    DESCRIPTION
        "A collection of objects."
    ::= { vtssIpmcSnoopingMibGroups 3 }

vtssIpmcSnoopingConfigMldGlobalsInfoGroup OBJECT-GROUP
    OBJECTS     { vtssIpmcSnoopingConfigMldGlobalsAdminState,
                  vtssIpmcSnoopingConfigMldGlobalsUnregisteredFlooding,
                  vtssIpmcSnoopingConfigMldGlobalsSsmRangeAddress,
                  vtssIpmcSnoopingConfigMldGlobalsSsmRangeMask,
                  vtssIpmcSnoopingConfigMldGlobalsProxy,
                  vtssIpmcSnoopingConfigMldGlobalsLeaveProxy }
    STATUS      current
    DESCRIPTION
        "A collection of objects."
    ::= { vtssIpmcSnoopingMibGroups 4 }

vtssIpmcSnoopingConfigMldPortTableInfoGroup OBJECT-GROUP
    OBJECTS     { vtssIpmcSnoopingConfigMldPortPortIndex,
                  vtssIpmcSnoopingConfigMldPortAsRouterPort,
                  vtssIpmcSnoopingConfigMldPortDoFastLeave,
                  vtssIpmcSnoopingConfigMldPortThrottlingNumber,
                  vtssIpmcSnoopingConfigMldPortFilteringProfile }
    STATUS      current
    DESCRIPTION
        "A collection of objects."
    ::= { vtssIpmcSnoopingMibGroups 5 }

vtssIpmcSnoopingConfigMldInterfaceTableInfoGroup OBJECT-GROUP
    OBJECTS     { vtssIpmcSnoopingConfigMldInterfaceIfIndex,
                  vtssIpmcSnoopingConfigMldInterfaceAdminState,
                  vtssIpmcSnoopingConfigMldInterfaceQuerierElection,
                  vtssIpmcSnoopingConfigMldInterfaceCompatibility,
                  vtssIpmcSnoopingConfigMldInterfacePriority,
                  vtssIpmcSnoopingConfigMldInterfaceRv,
                  vtssIpmcSnoopingConfigMldInterfaceQi,
                  vtssIpmcSnoopingConfigMldInterfaceQri,
                  vtssIpmcSnoopingConfigMldInterfaceLmqi,
                  vtssIpmcSnoopingConfigMldInterfaceUri }
    STATUS      current
    DESCRIPTION
        "A collection of objects."
    ::= { vtssIpmcSnoopingMibGroups 6 }

vtssIpmcSnoopingStatusIgmpRouterPortTableInfoGroup OBJECT-GROUP
    OBJECTS     { vtssIpmcSnoopingStatusIgmpRouterPortPortIndex,
                  vtssIpmcSnoopingStatusIgmpRouterPortStatus }
    STATUS      current
    DESCRIPTION
        "A collection of objects."
    ::= { vtssIpmcSnoopingMibGroups 7 }

vtssIpmcSnoopingStatusIgmpVlanTableInfoGroup OBJECT-GROUP
    OBJECTS     { vtssIpmcSnoopingStatusIgmpVlanIfIndex,
                  vtssIpmcSnoopingStatusIgmpVlanQuerierStatus,
                  vtssIpmcSnoopingStatusIgmpVlanActiveQuerierAddress,
                  vtssIpmcSnoopingStatusIgmpVlanQuerierUptime,
                  vtssIpmcSnoopingStatusIgmpVlanQueryInterval,
                  vtssIpmcSnoopingStatusIgmpVlanQuerierExpiryTime,
                  vtssIpmcSnoopingStatusIgmpVlanQuerierVersion,
                  vtssIpmcSnoopingStatusIgmpVlanQuerierPresentTimeout,
                  vtssIpmcSnoopingStatusIgmpVlanHostVersion,
                  vtssIpmcSnoopingStatusIgmpVlanHostPresentTimeout,
                  vtssIpmcSnoopingStatusIgmpVlanCounterTxQuery,
                  vtssIpmcSnoopingStatusIgmpVlanCounterTxSpecificQuery,
                  vtssIpmcSnoopingStatusIgmpVlanCounterRxQuery,
                  vtssIpmcSnoopingStatusIgmpVlanCounterRxV1Join,
                  vtssIpmcSnoopingStatusIgmpVlanCounterRxV2Join,
                  vtssIpmcSnoopingStatusIgmpVlanCounterRxV2Leave,
                  vtssIpmcSnoopingStatusIgmpVlanCounterRxV3Join,
                  vtssIpmcSnoopingStatusIgmpVlanCounterRxErrors }
    STATUS      current
    DESCRIPTION
        "A collection of objects."
    ::= { vtssIpmcSnoopingMibGroups 8 }

vtssIpmcSnoopingStatusIgmpGroupAddressTableInfoGroup OBJECT-GROUP
    OBJECTS     { vtssIpmcSnoopingStatusIgmpGroupAddressIfIndex,
                  vtssIpmcSnoopingStatusIgmpGroupAddressGroupAddress,
                  vtssIpmcSnoopingStatusIgmpGroupAddressMemberPorts,
                  vtssIpmcSnoopingStatusIgmpGroupAddressHardwareSwitch }
    STATUS      current
    DESCRIPTION
        "A collection of objects."
    ::= { vtssIpmcSnoopingMibGroups 9 }

vtssIpmcSnoopingStatusIgmpGroupSrcListTableInfoGroup OBJECT-GROUP
    OBJECTS     { vtssIpmcSnoopingStatusIgmpGroupSrcListIfIndex,
                  vtssIpmcSnoopingStatusIgmpGroupSrcListGroupAddress,
                  vtssIpmcSnoopingStatusIgmpGroupSrcListPortIndex,
                  vtssIpmcSnoopingStatusIgmpGroupSrcListHostAddress,
                  vtssIpmcSnoopingStatusIgmpGroupSrcListGroupFilterMode,
                  vtssIpmcSnoopingStatusIgmpGroupSrcListFilterTimer,
                  vtssIpmcSnoopingStatusIgmpGroupSrcListSourceType,
                  vtssIpmcSnoopingStatusIgmpGroupSrcListSourceTimer,
                  vtssIpmcSnoopingStatusIgmpGroupSrcListHardwareFilter }
    STATUS      current
    DESCRIPTION
        "A collection of objects."
    ::= { vtssIpmcSnoopingMibGroups 10 }

vtssIpmcSnoopingStatusMldRouterPortTableInfoGroup OBJECT-GROUP
    OBJECTS     { vtssIpmcSnoopingStatusMldRouterPortPortIndex,
                  vtssIpmcSnoopingStatusMldRouterPortStatus }
    STATUS      current
    DESCRIPTION
        "A collection of objects."
    ::= { vtssIpmcSnoopingMibGroups 11 }

vtssIpmcSnoopingStatusMldVlanTableInfoGroup OBJECT-GROUP
    OBJECTS     { vtssIpmcSnoopingStatusMldVlanIfIndex,
                  vtssIpmcSnoopingStatusMldVlanQuerierStatus,
                  vtssIpmcSnoopingStatusMldVlanActiveQuerierAddress,
                  vtssIpmcSnoopingStatusMldVlanQuerierUptime,
                  vtssIpmcSnoopingStatusMldVlanQueryInterval,
                  vtssIpmcSnoopingStatusMldVlanQuerierExpiryTime,
                  vtssIpmcSnoopingStatusMldVlanQuerierVersion,
                  vtssIpmcSnoopingStatusMldVlanQuerierPresentTimeout,
                  vtssIpmcSnoopingStatusMldVlanHostVersion,
                  vtssIpmcSnoopingStatusMldVlanHostPresentTimeout,
                  vtssIpmcSnoopingStatusMldVlanCounterTxQuery,
                  vtssIpmcSnoopingStatusMldVlanCounterTxSpecificQuery,
                  vtssIpmcSnoopingStatusMldVlanCounterRxQuery,
                  vtssIpmcSnoopingStatusMldVlanCounterRxV1Report,
                  vtssIpmcSnoopingStatusMldVlanCounterRxV1Done,
                  vtssIpmcSnoopingStatusMldVlanCounterRxV2Report,
                  vtssIpmcSnoopingStatusMldVlanCounterRxErrors }
    STATUS      current
    DESCRIPTION
        "A collection of objects."
    ::= { vtssIpmcSnoopingMibGroups 12 }

vtssIpmcSnoopingStatusMldGroupAddressTableInfoGroup OBJECT-GROUP
    OBJECTS     { vtssIpmcSnoopingStatusMldGroupAddressIfIndex,
                  vtssIpmcSnoopingStatusMldGroupAddressGroupAddress,
                  vtssIpmcSnoopingStatusMldGroupAddressMemberPorts,
                  vtssIpmcSnoopingStatusMldGroupAddressHardwareSwitch }
    STATUS      current
    DESCRIPTION
        "A collection of objects."
    ::= { vtssIpmcSnoopingMibGroups 13 }

vtssIpmcSnoopingStatusMldGroupSrcListTableInfoGroup OBJECT-GROUP
    OBJECTS     { vtssIpmcSnoopingStatusMldGroupSrcListIfIndex,
                  vtssIpmcSnoopingStatusMldGroupSrcListGroupAddress,
                  vtssIpmcSnoopingStatusMldGroupSrcListPortIndex,
                  vtssIpmcSnoopingStatusMldGroupSrcListHostAddress,
                  vtssIpmcSnoopingStatusMldGroupSrcListGroupFilterMode,
                  vtssIpmcSnoopingStatusMldGroupSrcListFilterTimer,
                  vtssIpmcSnoopingStatusMldGroupSrcListSourceType,
                  vtssIpmcSnoopingStatusMldGroupSrcListSourceTimer,
                  vtssIpmcSnoopingStatusMldGroupSrcListHardwareFilter }
    STATUS      current
    DESCRIPTION
        "A collection of objects."
    ::= { vtssIpmcSnoopingMibGroups 14 }

vtssIpmcSnoopingControlStatisticsIgmpClearByIfIndexInfoGroup OBJECT-GROUP
    OBJECTS     {                   vtssIpmcSnoopingControlStatisticsIgmpClearByIfIndexIfIndex,
                  vtssIpmcSnoopingControlStatisticsIgmpClearByIfIndexClear }
    STATUS      current
    DESCRIPTION
        "A collection of objects."
    ::= { vtssIpmcSnoopingMibGroups 15 }

vtssIpmcSnoopingControlStatisticsMldClearByIfIndexInfoGroup OBJECT-GROUP
    OBJECTS     {                   vtssIpmcSnoopingControlStatisticsMldClearByIfIndexIfIndex,
                  vtssIpmcSnoopingControlStatisticsMldClearByIfIndexClear }
    STATUS      current
    DESCRIPTION
        "A collection of objects."
    ::= { vtssIpmcSnoopingMibGroups 16 }

vtssIpmcSnoopingMibCompliance MODULE-COMPLIANCE
    STATUS      current
    DESCRIPTION
        "The compliance statement for the implementation."

    MODULE      -- this module

    MANDATORY-GROUPS { vtssIpmcSnoopingConfigIgmpGlobalsInfoGroup,
                       vtssIpmcSnoopingConfigIgmpPortTableInfoGroup,
                       vtssIpmcSnoopingConfigIgmpInterfaceTableInfoGroup,
                       vtssIpmcSnoopingConfigMldGlobalsInfoGroup,
                       vtssIpmcSnoopingConfigMldPortTableInfoGroup,
                       vtssIpmcSnoopingConfigMldInterfaceTableInfoGroup,
                       vtssIpmcSnoopingStatusIgmpRouterPortTableInfoGroup,
                       vtssIpmcSnoopingStatusIgmpVlanTableInfoGroup,
                       vtssIpmcSnoopingStatusIgmpGroupAddressTableInfoGroup,
                       vtssIpmcSnoopingStatusIgmpGroupSrcListTableInfoGroup,
                       vtssIpmcSnoopingStatusMldRouterPortTableInfoGroup,
                       vtssIpmcSnoopingStatusMldVlanTableInfoGroup,
                       vtssIpmcSnoopingStatusMldGroupAddressTableInfoGroup,
                       vtssIpmcSnoopingStatusMldGroupSrcListTableInfoGroup,
                       vtssIpmcSnoopingControlStatisticsIgmpClearByIfIndexInfoGroup,
                       vtssIpmcSnoopingControlStatisticsMldClearByIfIndexInfoGroup }

    ::= { vtssIpmcSnoopingMibCompliances 1 }

END
