-- *****************************************************************
-- NAS-MIB:  Microsemi ENT private MIB
-- ****************************************************************

VTSS-NAS-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Unsigned32 FROM SNMPv2-SMI
    MacAddress FROM SNMPv2-TC
    TruthValue FROM SNMPv2-TC
    VTSSDisplayString FROM VTSS-TC
    VTSSInterfaceIndex FROM VTSS-TC
    VTSSUnsigned16 FROM VTSS-TC
    VTSSVlan FROM VTSS-TC
    ;

vtssNasMib MODULE-IDENTITY
    LAST-UPDATED "201712120000Z"
    ORGANIZATION
        "Microsemi Corporation"
    CONTACT-INFO
        "Application support: http://www.microchip.com/support"
    DESCRIPTION
        "This is the Vitesse NAS private MIB."
    REVISION    "201712120000Z"
    DESCRIPTION
        "1) Changed nasPortStatus::cnt to nasPortStatus::multiMode. 2) Added
         authCnt and unauthCnt to NasStatusEntry. 3) Minor editorial changes"
    REVISION    "201407010000Z"
    DESCRIPTION
        "Initial version"
    ::= { vtssSwitchMgmt 21 }


VTSSnasPortControl ::= TEXTUAL-CONVENTION
    STATUS      current
    DESCRIPTION
        "This enumeration the NAS admin state.
         
         "
    SYNTAX      INTEGER { none(0), forceAuthorized(1), auto(2),
                          forceUnAuthorized(3), macBased(4),
                          dot1xSingle(5), dot1xmulti(6) }

VTSSnasPortStatus ::= TEXTUAL-CONVENTION
    STATUS      current
    DESCRIPTION
        "This enumerates the NAS interface status."
    SYNTAX      INTEGER { linkDown(0), authorized(1), unAuthorized(2),
                          disabled(3), multiMode(4) }

VTSSnasVlanType ::= TEXTUAL-CONVENTION
    STATUS      current
    DESCRIPTION
        "This enumeration the NAS VLAN type."
    SYNTAX      INTEGER { none(0), radiusAssigned(1), guestVlan(2) }

vtssNasMibObjects OBJECT IDENTIFIER
    ::= { vtssNasMib 1 }

vtssNasConfig OBJECT IDENTIFIER
    ::= { vtssNasMibObjects 2 }

vtssNasConfigGlobal OBJECT IDENTIFIER
    ::= { vtssNasConfig 1 }

vtssNasConfigGlobalNasMode OBJECT-TYPE
    SYNTAX      TruthValue
    MAX-ACCESS  read-write
    STATUS      current
    DESCRIPTION
        "Set to TRUE to globally enabled or disabled NAS for the switch. If
         globally disabled, all physical interfaces are allowed forwarding of
         frames."
    ::= { vtssNasConfigGlobal 1 }

vtssNasConfigGlobalReauthenticationMode OBJECT-TYPE
    SYNTAX      TruthValue
    MAX-ACCESS  read-write
    STATUS      current
    DESCRIPTION
        "If set to TRUE, successfully authenticated supplicants/clients are
         re-authenticated after the interval specified by the Reauthentication
         Period. Re-authentication for 802.1X-enabled interfaces can be used to
         detect if a new device is plugged into a switch port or if a supplicant
         is no longer attached. For MAC-based ports, re-authentication is only
         useful, if the RADIUS server configuration has changed. It does not
         involve communication between the switch and the client, and therefore
         does not imply that a client is still present on a port (see Aging
         Period)."
    ::= { vtssNasConfigGlobal 2 }

vtssNasConfigGlobalReauthenticationPeriod OBJECT-TYPE
    SYNTAX      VTSSUnsigned16 (1..3600)
    MAX-ACCESS  read-write
    STATUS      current
    DESCRIPTION
        "Sets the period in seconds, after which a connected client must be
         re-authenticated. This is only active if the ReauthenticationMode is
         set to TRUE."
    ::= { vtssNasConfigGlobal 3 }

vtssNasConfigGlobalEapolTimeout OBJECT-TYPE
    SYNTAX      VTSSUnsigned16 (1..65535)
    MAX-ACCESS  read-write
    STATUS      current
    DESCRIPTION
        "Determines the time for re-transmission of Request Identity EAPOL
         frames. This has no effect for MAC-based ports."
    ::= { vtssNasConfigGlobal 4 }

vtssNasConfigGlobalAgingPeriod OBJECT-TYPE
    SYNTAX      Unsigned32 (10..1000000)
    MAX-ACCESS  read-write
    STATUS      current
    DESCRIPTION
        "Specific the PSEC aging period in seconds. In the period the CPU starts
         listening to frames from the given MAC address, and if none arrives
         before period end, the entry will be removed."
    ::= { vtssNasConfigGlobal 5 }

vtssNasConfigGlobalAuthFailureHoldTime OBJECT-TYPE
    SYNTAX      Unsigned32 (10..1000000)
    MAX-ACCESS  read-write
    STATUS      current
    DESCRIPTION
        "Time in seconds to wait before attempting to re-authenticate if
         re-authentication failed for a given client."
    ::= { vtssNasConfigGlobal 6 }

vtssNasConfigGlobalRadiusAssignedQosMode OBJECT-TYPE
    SYNTAX      TruthValue
    MAX-ACCESS  read-write
    STATUS      current
    DESCRIPTION
        "Set to true to enable RADIUS assigned QoS."
    ::= { vtssNasConfigGlobal 7 }

vtssNasConfigGlobalRadiusAssignedVlanMode OBJECT-TYPE
    SYNTAX      TruthValue
    MAX-ACCESS  read-write
    STATUS      current
    DESCRIPTION
        "Set to true to enable RADIUS assigned VLAN."
    ::= { vtssNasConfigGlobal 8 }

vtssNasConfigGlobalGuestVlanMode OBJECT-TYPE
    SYNTAX      TruthValue
    MAX-ACCESS  read-write
    STATUS      current
    DESCRIPTION
        "Set to true to enable Guest VLAN Mode."
    ::= { vtssNasConfigGlobal 9 }

vtssNasConfigGlobalGuestVlanId OBJECT-TYPE
    SYNTAX      VTSSVlan
    MAX-ACCESS  read-write
    STATUS      current
    DESCRIPTION
        "Guest VLAN ID to get assigned to an interface moved to Guest VLAN mode."
    ::= { vtssNasConfigGlobal 10 }

vtssNasConfigGlobalMaxReauthrequestsCount OBJECT-TYPE
    SYNTAX      Unsigned32 (1..255)
    MAX-ACCESS  read-write
    STATUS      current
    DESCRIPTION
        "Maximum re-authentication request count."
    ::= { vtssNasConfigGlobal 11 }

vtssNasConfigGlobalGuestVlanAllowEapols OBJECT-TYPE
    SYNTAX      TruthValue
    MAX-ACCESS  read-write
    STATUS      current
    DESCRIPTION
        "Set to TRUE to allow an interface to move to Guest VLAN even when EAPOL
         packets has been received at an interface."
    ::= { vtssNasConfigGlobal 12 }

vtssNasConfigReAuthTable OBJECT-TYPE
    SYNTAX      SEQUENCE OF VTSSNasConfigReAuthEntry
    MAX-ACCESS  not-accessible
    STATUS      current
    DESCRIPTION
        "This is a table for port configuration"
    ::= { vtssNasConfig 2 }

vtssNasConfigReAuthEntry OBJECT-TYPE
    SYNTAX      VTSSNasConfigReAuthEntry
    MAX-ACCESS  not-accessible
    STATUS      current
    DESCRIPTION
        "Each physical interface has a set of parameters"
    INDEX       { vtssNasConfigReAuthInterfaceNo }
    ::= { vtssNasConfigReAuthTable 1 }

VTSSNasConfigReAuthEntry ::= SEQUENCE {
    vtssNasConfigReAuthInterfaceNo              VTSSInterfaceIndex,
    vtssNasConfigReAuthAdminState               VTSSnasPortControl,
    vtssNasConfigReAuthRadiusAssignedQosState   TruthValue,
    vtssNasConfigReAuthRadiusAssignedVlanState  TruthValue,
    vtssNasConfigReAuthGuestVlanState           TruthValue
}

vtssNasConfigReAuthInterfaceNo OBJECT-TYPE
    SYNTAX      VTSSInterfaceIndex
    MAX-ACCESS  accessible-for-notify
    STATUS      current
    DESCRIPTION
        "Logical interface number."
    ::= { vtssNasConfigReAuthEntry 1 }

vtssNasConfigReAuthAdminState OBJECT-TYPE
    SYNTAX      VTSSnasPortControl
    MAX-ACCESS  read-write
    STATUS      current
    DESCRIPTION
        "Administrative State.
         
         TypeNone : Forces an interface to be disabled.
         
         forceAuthorized : Forces an interface to grant access to all clients,
         802.1X-aware or not.
         
         auto : Requires an 802.1X-aware client to be authorized by the
         authentication server. Clients that are not 802.1X-aware will be denied
         access.
         
         unauthorized : Forces an interface to deny access to all clients,
         802.1X-aware or not.
         
         macBased : The switch authenticates on behalf of the client, using the
         client MAC-address as the username and password and MD5 EAP method.
         
         dot1xSingle : At most one supplicant is allowed to authenticate, and it
         authenticates using normal 802.1X frames.
         
         dot1xmulti : One or more supplicants are allowed to authenticate
         individually using an 802.1X variant, where EAPOL frames sent from the
         switch are directed towards the supplicants MAC address instead of
         using the multi-cast BPDU MAC address. Unauthenticated supplicants will
         not get access.
         
         
         
         Note: The 802.1X Admin State must be set to Authorized for interfaces
         that are enabled forSpanning Tree"
    ::= { vtssNasConfigReAuthEntry 2 }

vtssNasConfigReAuthRadiusAssignedQosState OBJECT-TYPE
    SYNTAX      TruthValue
    MAX-ACCESS  read-write
    STATUS      current
    DESCRIPTION
        "Set to TRUE to enable RADIUS-assigned QoS for this interface."
    ::= { vtssNasConfigReAuthEntry 3 }

vtssNasConfigReAuthRadiusAssignedVlanState OBJECT-TYPE
    SYNTAX      TruthValue
    MAX-ACCESS  read-write
    STATUS      current
    DESCRIPTION
        "Set to TRUE to enable RADIUS-assigned VLAN for this interface."
    ::= { vtssNasConfigReAuthEntry 4 }

vtssNasConfigReAuthGuestVlanState OBJECT-TYPE
    SYNTAX      TruthValue
    MAX-ACCESS  read-write
    STATUS      current
    DESCRIPTION
        "Set to TRUE to enable Guest-VLAN for this interface."
    ::= { vtssNasConfigReAuthEntry 5 }

vtssNasStatus OBJECT IDENTIFIER
    ::= { vtssNasMibObjects 3 }

vtssNasStatusTable OBJECT-TYPE
    SYNTAX      SEQUENCE OF VTSSNasStatusEntry
    MAX-ACCESS  not-accessible
    STATUS      current
    DESCRIPTION
        "This is a table to get NAS per-port status table."
    ::= { vtssNasStatus 1 }

vtssNasStatusEntry OBJECT-TYPE
    SYNTAX      VTSSNasStatusEntry
    MAX-ACCESS  not-accessible
    STATUS      current
    DESCRIPTION
        "Each physical interface has a set of per-port status parameters."
    INDEX       { vtssNasStatusInterfaceNo }
    ::= { vtssNasStatusTable 1 }

VTSSNasStatusEntry ::= SEQUENCE {
    vtssNasStatusInterfaceNo  VTSSInterfaceIndex,
    vtssNasStatusStatus       VTSSnasPortStatus,
    vtssNasStatusQosClass     Unsigned32,
    vtssNasStatusVlanType     VTSSnasVlanType,
    vtssNasStatusVlanId       VTSSVlan,
    vtssNasStatusAuthCnt      Unsigned32,
    vtssNasStatusUnauthCnt    Unsigned32
}

vtssNasStatusInterfaceNo OBJECT-TYPE
    SYNTAX      VTSSInterfaceIndex
    MAX-ACCESS  accessible-for-notify
    STATUS      current
    DESCRIPTION
        "Logical interface number."
    ::= { vtssNasStatusEntry 1 }

vtssNasStatusStatus OBJECT-TYPE
    SYNTAX      VTSSnasPortStatus
    MAX-ACCESS  read-only
    STATUS      current
    DESCRIPTION
        "dot1x port status."
    ::= { vtssNasStatusEntry 2 }

vtssNasStatusQosClass OBJECT-TYPE
    SYNTAX      Unsigned32
    MAX-ACCESS  read-only
    STATUS      current
    DESCRIPTION
        "QoS class for this port. If value is 4294967295 it means that the QoS
         is not overridden."
    ::= { vtssNasStatusEntry 3 }

vtssNasStatusVlanType OBJECT-TYPE
    SYNTAX      VTSSnasVlanType
    MAX-ACCESS  read-only
    STATUS      current
    DESCRIPTION
        "VLAN Type for this port."
    ::= { vtssNasStatusEntry 4 }

vtssNasStatusVlanId OBJECT-TYPE
    SYNTAX      VTSSVlan
    MAX-ACCESS  read-only
    STATUS      current
    DESCRIPTION
        "VLAN Id for this port. 0 if not overridden."
    ::= { vtssNasStatusEntry 5 }

vtssNasStatusAuthCnt OBJECT-TYPE
    SYNTAX      Unsigned32
    MAX-ACCESS  read-only
    STATUS      current
    DESCRIPTION
        "In multi-client modes, number of authenticated clients on this port."
    ::= { vtssNasStatusEntry 6 }

vtssNasStatusUnauthCnt OBJECT-TYPE
    SYNTAX      Unsigned32
    MAX-ACCESS  read-only
    STATUS      current
    DESCRIPTION
        "In multi-client modes, number of unauthenticated clients on this port."
    ::= { vtssNasStatusEntry 7 }

vtssNasStatusLastSupplicantTable OBJECT-TYPE
    SYNTAX      SEQUENCE OF VTSSNasStatusLastSupplicantEntry
    MAX-ACCESS  not-accessible
    STATUS      current
    DESCRIPTION
        "This is a table to get NAS last supplicant"
    ::= { vtssNasStatus 2 }

vtssNasStatusLastSupplicantEntry OBJECT-TYPE
    SYNTAX      VTSSNasStatusLastSupplicantEntry
    MAX-ACCESS  not-accessible
    STATUS      current
    DESCRIPTION
        "Each physical interface has a set of parameters"
    INDEX       { vtssNasStatusLastSupplicantInterfaceNo }
    ::= { vtssNasStatusLastSupplicantTable 1 }

VTSSNasStatusLastSupplicantEntry ::= SEQUENCE {
    vtssNasStatusLastSupplicantInterfaceNo  VTSSInterfaceIndex,
    vtssNasStatusLastSupplicantVlanId       VTSSVlan,
    vtssNasStatusLastSupplicantMac          MacAddress,
    vtssNasStatusLastSupplicantIdentity     VTSSDisplayString
}

vtssNasStatusLastSupplicantInterfaceNo OBJECT-TYPE
    SYNTAX      VTSSInterfaceIndex
    MAX-ACCESS  accessible-for-notify
    STATUS      current
    DESCRIPTION
        "Logical interface number."
    ::= { vtssNasStatusLastSupplicantEntry 1 }

vtssNasStatusLastSupplicantVlanId OBJECT-TYPE
    SYNTAX      VTSSVlan
    MAX-ACCESS  read-only
    STATUS      current
    DESCRIPTION
        "VLAN ID."
    ::= { vtssNasStatusLastSupplicantEntry 2 }

vtssNasStatusLastSupplicantMac OBJECT-TYPE
    SYNTAX      MacAddress
    MAX-ACCESS  read-only
    STATUS      current
    DESCRIPTION
        "Binary version of MacAddrStr."
    ::= { vtssNasStatusLastSupplicantEntry 3 }

vtssNasStatusLastSupplicantIdentity OBJECT-TYPE
    SYNTAX      VTSSDisplayString (SIZE(0..39))
    MAX-ACCESS  read-only
    STATUS      current
    DESCRIPTION
        "Identity string."
    ::= { vtssNasStatusLastSupplicantEntry 4 }

vtssNasControl OBJECT IDENTIFIER
    ::= { vtssNasMibObjects 4 }

vtssNasControlPortTable OBJECT-TYPE
    SYNTAX      SEQUENCE OF VTSSNasControlPortEntry
    MAX-ACCESS  not-accessible
    STATUS      current
    DESCRIPTION
        "This is a table to start NAS re-authorization"
    ::= { vtssNasControl 1 }

vtssNasControlPortEntry OBJECT-TYPE
    SYNTAX      VTSSNasControlPortEntry
    MAX-ACCESS  not-accessible
    STATUS      current
    DESCRIPTION
        "Each physical interface has a set of parameters"
    INDEX       { vtssNasControlPortInterfaceNo }
    ::= { vtssNasControlPortTable 1 }

VTSSNasControlPortEntry ::= SEQUENCE {
    vtssNasControlPortInterfaceNo  VTSSInterfaceIndex,
    vtssNasControlPortNow          TruthValue
}

vtssNasControlPortInterfaceNo OBJECT-TYPE
    SYNTAX      VTSSInterfaceIndex
    MAX-ACCESS  accessible-for-notify
    STATUS      current
    DESCRIPTION
        "Logical interface number."
    ::= { vtssNasControlPortEntry 1 }

vtssNasControlPortNow OBJECT-TYPE
    SYNTAX      TruthValue
    MAX-ACCESS  read-write
    STATUS      current
    DESCRIPTION
        "TRUE to force re-authentication immediately. FALSE to refresh (restart)
         802.1X authentication process."
    ::= { vtssNasControlPortEntry 2 }

vtssNasControlStatisticsClearTable OBJECT-TYPE
    SYNTAX      SEQUENCE OF VTSSNasControlStatisticsClearEntry
    MAX-ACCESS  not-accessible
    STATUS      current
    DESCRIPTION
        "This is a table to clear NAS statistics for a specific interface."
    ::= { vtssNasControl 2 }

vtssNasControlStatisticsClearEntry OBJECT-TYPE
    SYNTAX      VTSSNasControlStatisticsClearEntry
    MAX-ACCESS  not-accessible
    STATUS      current
    DESCRIPTION
        "Each interface has a set of statistics counters"
    INDEX       { vtssNasControlStatisticsClearInterfaceNo }
    ::= { vtssNasControlStatisticsClearTable 1 }

VTSSNasControlStatisticsClearEntry ::= SEQUENCE {
    vtssNasControlStatisticsClearInterfaceNo  VTSSInterfaceIndex,
    vtssNasControlStatisticsClearClear        TruthValue
}

vtssNasControlStatisticsClearInterfaceNo OBJECT-TYPE
    SYNTAX      VTSSInterfaceIndex
    MAX-ACCESS  accessible-for-notify
    STATUS      current
    DESCRIPTION
        "Logical interface number."
    ::= { vtssNasControlStatisticsClearEntry 1 }

vtssNasControlStatisticsClearClear OBJECT-TYPE
    SYNTAX      TruthValue
    MAX-ACCESS  read-write
    STATUS      current
    DESCRIPTION
        "TRUE to clear NAS statistics."
    ::= { vtssNasControlStatisticsClearEntry 5 }

vtssNasStatistics OBJECT IDENTIFIER
    ::= { vtssNasMibObjects 5 }

vtssNasStatisticsEapolTable OBJECT-TYPE
    SYNTAX      SEQUENCE OF VTSSNasStatisticsEapolEntry
    MAX-ACCESS  not-accessible
    STATUS      current
    DESCRIPTION
        "This is a table to get NAS EAPOL statistics."
    ::= { vtssNasStatistics 1 }

vtssNasStatisticsEapolEntry OBJECT-TYPE
    SYNTAX      VTSSNasStatisticsEapolEntry
    MAX-ACCESS  not-accessible
    STATUS      current
    DESCRIPTION
        "Each physical interface has a set of EAPOL counters."
    INDEX       { vtssNasStatisticsEapolInterfaceNo }
    ::= { vtssNasStatisticsEapolTable 1 }

VTSSNasStatisticsEapolEntry ::= SEQUENCE {
    vtssNasStatisticsEapolInterfaceNo                      VTSSInterfaceIndex,
    vtssNasStatisticsEapolDot1xAuthEapolFramesRx           Unsigned32,
    vtssNasStatisticsEapolDot1xAuthEapolFramesTx           Unsigned32,
    vtssNasStatisticsEapolDot1xAuthEapolStartFramesRx      Unsigned32,
    vtssNasStatisticsEapolDot1xAuthEapolLogoffFramesRx     Unsigned32,
    vtssNasStatisticsEapolDot1xAuthEapolRespIdFramesRx     Unsigned32,
    vtssNasStatisticsEapolDot1xAuthEapolRespFramesRx       Unsigned32,
    vtssNasStatisticsEapolDot1xAuthEapolReqIdFramesTx      Unsigned32,
    vtssNasStatisticsEapolDot1xAuthEapolReqFramesTx        Unsigned32,
    vtssNasStatisticsEapolDot1xAuthInvalidEapolFramesRx    Unsigned32,
    vtssNasStatisticsEapolDot1xAuthEapLengthErrorFramesRx  Unsigned32
}

vtssNasStatisticsEapolInterfaceNo OBJECT-TYPE
    SYNTAX      VTSSInterfaceIndex
    MAX-ACCESS  accessible-for-notify
    STATUS      current
    DESCRIPTION
        "Logical interface number."
    ::= { vtssNasStatisticsEapolEntry 1 }

vtssNasStatisticsEapolDot1xAuthEapolFramesRx OBJECT-TYPE
    SYNTAX      Unsigned32
    MAX-ACCESS  read-only
    STATUS      current
    DESCRIPTION
        "Numbers of dot1x Auth Eapol Frames Received."
    ::= { vtssNasStatisticsEapolEntry 5 }

vtssNasStatisticsEapolDot1xAuthEapolFramesTx OBJECT-TYPE
    SYNTAX      Unsigned32
    MAX-ACCESS  read-only
    STATUS      current
    DESCRIPTION
        "Numbers of dot1x Auth Eapol Frames Transmitted."
    ::= { vtssNasStatisticsEapolEntry 6 }

vtssNasStatisticsEapolDot1xAuthEapolStartFramesRx OBJECT-TYPE
    SYNTAX      Unsigned32
    MAX-ACCESS  read-only
    STATUS      current
    DESCRIPTION
        "Numbers of dot1x Auth Eapol Start Frames Received."
    ::= { vtssNasStatisticsEapolEntry 7 }

vtssNasStatisticsEapolDot1xAuthEapolLogoffFramesRx OBJECT-TYPE
    SYNTAX      Unsigned32
    MAX-ACCESS  read-only
    STATUS      current
    DESCRIPTION
        "Numbers of dot1x Auth Eapol Logoff Frames Received."
    ::= { vtssNasStatisticsEapolEntry 8 }

vtssNasStatisticsEapolDot1xAuthEapolRespIdFramesRx OBJECT-TYPE
    SYNTAX      Unsigned32
    MAX-ACCESS  read-only
    STATUS      current
    DESCRIPTION
        "Numbers of dot1x Auth Eapol RespId Frames Received."
    ::= { vtssNasStatisticsEapolEntry 9 }

vtssNasStatisticsEapolDot1xAuthEapolRespFramesRx OBJECT-TYPE
    SYNTAX      Unsigned32
    MAX-ACCESS  read-only
    STATUS      current
    DESCRIPTION
        "Numbers of dot1x Auth Eapol Resp Frames Received."
    ::= { vtssNasStatisticsEapolEntry 10 }

vtssNasStatisticsEapolDot1xAuthEapolReqIdFramesTx OBJECT-TYPE
    SYNTAX      Unsigned32
    MAX-ACCESS  read-only
    STATUS      current
    DESCRIPTION
        "Numbers of dot1x Auth Eapol Req Id Frames Transmitted."
    ::= { vtssNasStatisticsEapolEntry 11 }

vtssNasStatisticsEapolDot1xAuthEapolReqFramesTx OBJECT-TYPE
    SYNTAX      Unsigned32
    MAX-ACCESS  read-only
    STATUS      current
    DESCRIPTION
        "Numbers of dot1x Auth Eapol Req Frames Transmitted."
    ::= { vtssNasStatisticsEapolEntry 12 }

vtssNasStatisticsEapolDot1xAuthInvalidEapolFramesRx OBJECT-TYPE
    SYNTAX      Unsigned32
    MAX-ACCESS  read-only
    STATUS      current
    DESCRIPTION
        "Numbers of dot1x Auth Invalid Eapol Frames Received."
    ::= { vtssNasStatisticsEapolEntry 13 }

vtssNasStatisticsEapolDot1xAuthEapLengthErrorFramesRx OBJECT-TYPE
    SYNTAX      Unsigned32
    MAX-ACCESS  read-only
    STATUS      current
    DESCRIPTION
        "Numbers of dot1x Auth Eap Length Error Frames Received."
    ::= { vtssNasStatisticsEapolEntry 14 }

vtssNasStatisticsRadiusTable OBJECT-TYPE
    SYNTAX      SEQUENCE OF VTSSNasStatisticsRadiusEntry
    MAX-ACCESS  not-accessible
    STATUS      current
    DESCRIPTION
        "This is a table to get NAS EAPOL statistics."
    ::= { vtssNasStatistics 2 }

vtssNasStatisticsRadiusEntry OBJECT-TYPE
    SYNTAX      VTSSNasStatisticsRadiusEntry
    MAX-ACCESS  not-accessible
    STATUS      current
    DESCRIPTION
        "Each physical interface has a set of EAPOL counters."
    INDEX       { vtssNasStatisticsRadiusInterfaceNo }
    ::= { vtssNasStatisticsRadiusTable 1 }

VTSSNasStatisticsRadiusEntry ::= SEQUENCE {
    vtssNasStatisticsRadiusInterfaceNo                       VTSSInterfaceIndex,
    vtssNasStatisticsRadiusBackendResponses                  Unsigned32,
    vtssNasStatisticsRadiusBackendAccessChallenges           Unsigned32,
    vtssNasStatisticsRadiusBackendOtherRequestsToSupplicant  Unsigned32,
    vtssNasStatisticsRadiusBackendAuthSuccesses              Unsigned32,
    vtssNasStatisticsRadiusBackendAuthFails                  Unsigned32
}

vtssNasStatisticsRadiusInterfaceNo OBJECT-TYPE
    SYNTAX      VTSSInterfaceIndex
    MAX-ACCESS  accessible-for-notify
    STATUS      current
    DESCRIPTION
        "Logical interface number."
    ::= { vtssNasStatisticsRadiusEntry 1 }

vtssNasStatisticsRadiusBackendResponses OBJECT-TYPE
    SYNTAX      Unsigned32
    MAX-ACCESS  read-only
    STATUS      current
    DESCRIPTION
        "Numbers of backend Responses."
    ::= { vtssNasStatisticsRadiusEntry 5 }

vtssNasStatisticsRadiusBackendAccessChallenges OBJECT-TYPE
    SYNTAX      Unsigned32
    MAX-ACCESS  read-only
    STATUS      current
    DESCRIPTION
        "Numbers of backend Access Challenges."
    ::= { vtssNasStatisticsRadiusEntry 6 }

vtssNasStatisticsRadiusBackendOtherRequestsToSupplicant OBJECT-TYPE
    SYNTAX      Unsigned32
    MAX-ACCESS  read-only
    STATUS      current
    DESCRIPTION
        "Numbers of backend Other Requests To Supplicant."
    ::= { vtssNasStatisticsRadiusEntry 7 }

vtssNasStatisticsRadiusBackendAuthSuccesses OBJECT-TYPE
    SYNTAX      Unsigned32
    MAX-ACCESS  read-only
    STATUS      current
    DESCRIPTION
        "Numbers of backend Auth Successes."
    ::= { vtssNasStatisticsRadiusEntry 8 }

vtssNasStatisticsRadiusBackendAuthFails OBJECT-TYPE
    SYNTAX      Unsigned32
    MAX-ACCESS  read-only
    STATUS      current
    DESCRIPTION
        "Numbers of backend Auth Fails."
    ::= { vtssNasStatisticsRadiusEntry 9 }

vtssNasMibConformance OBJECT IDENTIFIER
    ::= { vtssNasMib 2 }

vtssNasMibCompliances OBJECT IDENTIFIER
    ::= { vtssNasMibConformance 1 }

vtssNasMibGroups OBJECT IDENTIFIER
    ::= { vtssNasMibConformance 2 }

vtssNasConfigGlobalInfoGroup OBJECT-GROUP
    OBJECTS     { vtssNasConfigGlobalNasMode,
                  vtssNasConfigGlobalReauthenticationMode,
                  vtssNasConfigGlobalReauthenticationPeriod,
                  vtssNasConfigGlobalEapolTimeout,
                  vtssNasConfigGlobalAgingPeriod,
                  vtssNasConfigGlobalAuthFailureHoldTime,
                  vtssNasConfigGlobalRadiusAssignedQosMode,
                  vtssNasConfigGlobalRadiusAssignedVlanMode,
                  vtssNasConfigGlobalGuestVlanMode,
                  vtssNasConfigGlobalGuestVlanId,
                  vtssNasConfigGlobalMaxReauthrequestsCount,
                  vtssNasConfigGlobalGuestVlanAllowEapols }
    STATUS      current
    DESCRIPTION
        "A collection of objects."
    ::= { vtssNasMibGroups 1 }

vtssNasConfigReAuthInfoGroup OBJECT-GROUP
    OBJECTS     { vtssNasConfigReAuthInterfaceNo,
                  vtssNasConfigReAuthAdminState,
                  vtssNasConfigReAuthRadiusAssignedQosState,
                  vtssNasConfigReAuthRadiusAssignedVlanState,
                  vtssNasConfigReAuthGuestVlanState }
    STATUS      current
    DESCRIPTION
        "A collection of objects."
    ::= { vtssNasMibGroups 2 }

vtssNasStatusTableInfoGroup OBJECT-GROUP
    OBJECTS     { vtssNasStatusInterfaceNo, vtssNasStatusStatus,
                  vtssNasStatusQosClass, vtssNasStatusVlanType,
                  vtssNasStatusVlanId, vtssNasStatusAuthCnt,
                  vtssNasStatusUnauthCnt }
    STATUS      current
    DESCRIPTION
        "A collection of objects."
    ::= { vtssNasMibGroups 3 }

vtssNasStatusLastSupplicantInfoGroup OBJECT-GROUP
    OBJECTS     { vtssNasStatusLastSupplicantInterfaceNo,
                  vtssNasStatusLastSupplicantVlanId,
                  vtssNasStatusLastSupplicantMac,
                  vtssNasStatusLastSupplicantIdentity }
    STATUS      current
    DESCRIPTION
        "A collection of objects."
    ::= { vtssNasMibGroups 4 }

vtssNasControlPortInfoGroup OBJECT-GROUP
    OBJECTS     { vtssNasControlPortInterfaceNo,
                  vtssNasControlPortNow }
    STATUS      current
    DESCRIPTION
        "A collection of objects."
    ::= { vtssNasMibGroups 5 }

vtssNasControlStatisticsClearInfoGroup OBJECT-GROUP
    OBJECTS     { vtssNasControlStatisticsClearInterfaceNo,
                  vtssNasControlStatisticsClearClear }
    STATUS      current
    DESCRIPTION
        "A collection of objects."
    ::= { vtssNasMibGroups 6 }

vtssNasStatisticsEapolInfoGroup OBJECT-GROUP
    OBJECTS     { vtssNasStatisticsEapolInterfaceNo,
                  vtssNasStatisticsEapolDot1xAuthEapolFramesRx,
                  vtssNasStatisticsEapolDot1xAuthEapolFramesTx,
                  vtssNasStatisticsEapolDot1xAuthEapolStartFramesRx,
                  vtssNasStatisticsEapolDot1xAuthEapolLogoffFramesRx,
                  vtssNasStatisticsEapolDot1xAuthEapolRespIdFramesRx,
                  vtssNasStatisticsEapolDot1xAuthEapolRespFramesRx,
                  vtssNasStatisticsEapolDot1xAuthEapolReqIdFramesTx,
                  vtssNasStatisticsEapolDot1xAuthEapolReqFramesTx,
                  vtssNasStatisticsEapolDot1xAuthInvalidEapolFramesRx,
                  vtssNasStatisticsEapolDot1xAuthEapLengthErrorFramesRx }
    STATUS      current
    DESCRIPTION
        "A collection of objects."
    ::= { vtssNasMibGroups 7 }

vtssNasStatisticsRadiusInfoGroup OBJECT-GROUP
    OBJECTS     { vtssNasStatisticsRadiusInterfaceNo,
                  vtssNasStatisticsRadiusBackendResponses,
                  vtssNasStatisticsRadiusBackendAccessChallenges,
                  vtssNasStatisticsRadiusBackendOtherRequestsToSupplicant,
                  vtssNasStatisticsRadiusBackendAuthSuccesses,
                  vtssNasStatisticsRadiusBackendAuthFails }
    STATUS      current
    DESCRIPTION
        "A collection of objects."
    ::= { vtssNasMibGroups 8 }

vtssNasMibCompliance MODULE-COMPLIANCE
    STATUS      current
    DESCRIPTION
        "The compliance statement for the implementation."

    MODULE      -- this module

    MANDATORY-GROUPS { vtssNasConfigGlobalInfoGroup,
                       vtssNasConfigReAuthInfoGroup,
                       vtssNasStatusTableInfoGroup,
                       vtssNasStatusLastSupplicantInfoGroup,
                       vtssNasControlPortInfoGroup,
                       vtssNasControlStatisticsClearInfoGroup,
                       vtssNasStatisticsEapolInfoGroup,
                       vtssNasStatisticsRadiusInfoGroup }

    ::= { vtssNasMibCompliances 1 }

END
