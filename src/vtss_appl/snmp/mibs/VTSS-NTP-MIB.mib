-- *****************************************************************
-- NTP-MIB:  Microsemi ENT private MIB
-- ****************************************************************

VTSS-NTP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    TruthValue FROM SNMPv2-TC
    VTSSInetAddress FROM VTSS-TC
    ;

vtssNtpMib MODULE-IDENTITY
    LAST-UPDATED "201410100000Z"
    ORGANIZATION
        "Microsemi Corporation"
    CONTACT-INFO
        "Application support: http://www.microchip.com/support"
    DESCRIPTION
        "This is a private version of NTP"
    REVISION    "201410100000Z"
    DESCRIPTION
        "Editorial changes"
    REVISION    "201407010000Z"
    DESCRIPTION
        "Initial version"
    ::= { vtssSwitchMgmt 57 }


vtssNtpMibObjects OBJECT IDENTIFIER
    ::= { vtssNtpMib 1 }

vtssNtpConfig OBJECT IDENTIFIER
    ::= { vtssNtpMibObjects 2 }

vtssNtpConfigGlobals OBJECT IDENTIFIER
    ::= { vtssNtpConfig 1 }

vtssNtpConfigGlobalsMode OBJECT-TYPE
    SYNTAX      TruthValue
    MAX-ACCESS  read-write
    STATUS      current
    DESCRIPTION
        "Global config mode of NTP. true is to enable NTP function in the system
         and false is to disable it."
    ::= { vtssNtpConfigGlobals 1 }

vtssNtpConfigServerTable OBJECT-TYPE
    SYNTAX      SEQUENCE OF VTSSNtpConfigServerEntry
    MAX-ACCESS  not-accessible
    STATUS      current
    DESCRIPTION
        "This is a table of NTP server."
    ::= { vtssNtpConfig 2 }

vtssNtpConfigServerEntry OBJECT-TYPE
    SYNTAX      VTSSNtpConfigServerEntry
    MAX-ACCESS  not-accessible
    STATUS      current
    DESCRIPTION
        "Each server has a set of parameters."
    INDEX       { vtssNtpConfigServerIndex }
    ::= { vtssNtpConfigServerTable 1 }

VTSSNtpConfigServerEntry ::= SEQUENCE {
    vtssNtpConfigServerIndex    Integer32,
    vtssNtpConfigServerAddress  VTSSInetAddress
}

vtssNtpConfigServerIndex OBJECT-TYPE
    SYNTAX      Integer32 (1..5)
    MAX-ACCESS  accessible-for-notify
    STATUS      current
    DESCRIPTION
        "The index of NTP servers."
    ::= { vtssNtpConfigServerEntry 1 }

vtssNtpConfigServerAddress OBJECT-TYPE
    SYNTAX      VTSSInetAddress
    MAX-ACCESS  read-write
    STATUS      current
    DESCRIPTION
        "Internet address of a NTP server."
    ::= { vtssNtpConfigServerEntry 2 }

vtssNtpMibConformance OBJECT IDENTIFIER
    ::= { vtssNtpMib 2 }

vtssNtpMibCompliances OBJECT IDENTIFIER
    ::= { vtssNtpMibConformance 1 }

vtssNtpMibGroups OBJECT IDENTIFIER
    ::= { vtssNtpMibConformance 2 }

vtssNtpConfigGlobalsInfoGroup OBJECT-GROUP
    OBJECTS     { vtssNtpConfigGlobalsMode }
    STATUS      current
    DESCRIPTION
        "A collection of objects."
    ::= { vtssNtpMibGroups 1 }

vtssNtpConfigServerTableInfoGroup OBJECT-GROUP
    OBJECTS     { vtssNtpConfigServerIndex,
                  vtssNtpConfigServerAddress }
    STATUS      current
    DESCRIPTION
        "A collection of objects."
    ::= { vtssNtpMibGroups 2 }

vtssNtpMibCompliance MODULE-COMPLIANCE
    STATUS      current
    DESCRIPTION
        "The compliance statement for the implementation."

    MODULE      -- this module

    MANDATORY-GROUPS { vtssNtpConfigGlobalsInfoGroup,
                       vtssNtpConfigServerTableInfoGroup }

    ::= { vtssNtpMibCompliances 1 }

END
