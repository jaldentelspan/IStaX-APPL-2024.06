-- *****************************************************************
-- IP-SOURCE-GUARD-MIB:  Microsemi ENT private MIB
-- ****************************************************************

VTSS-IP-SOURCE-GUARD-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    IpAddress FROM SNMPv2-SMI
    Unsigned32 FROM SNMPv2-SMI
    MacAddress FROM SNMPv2-TC
    TruthValue FROM SNMPv2-TC
    VTSSInterfaceIndex FROM VTSS-TC
    VTSSRowEditorState FROM VTSS-TC
    VTSSVlan FROM VTSS-TC
    ;

vtssIpSourceGuardMib MODULE-IDENTITY
    LAST-UPDATED "201412080000Z"
    ORGANIZATION
        "Microsemi Corporation"
    CONTACT-INFO
        "Application support: http://www.microchip.com/support"
    DESCRIPTION
        "This is a private version of the IP source guard MIB"
    REVISION    "201412080000Z"
    DESCRIPTION
        "Initial version"
    ::= { vtssSwitchMgmt 64 }


vtssIpSourceGuardMibObjects OBJECT IDENTIFIER
    ::= { vtssIpSourceGuardMib 1 }

vtssIpSourceGuardCapabilities OBJECT IDENTIFIER
    ::= { vtssIpSourceGuardMibObjects 1 }

vtssIpSourceGuardCapabilitiesStaticIpMask OBJECT-TYPE
    SYNTAX      TruthValue
    MAX-ACCESS  read-only
    STATUS      current
    DESCRIPTION
        "If FALSE, the IP mask of static binding table is only allowed to be
         configured as 255.255.255.255."
    ::= { vtssIpSourceGuardCapabilities 1 }

vtssIpSourceGuardCapabilitiesStaticMacAddress OBJECT-TYPE
    SYNTAX      TruthValue
    MAX-ACCESS  read-only
    STATUS      current
    DESCRIPTION
        "If TRUE, the MAC address of static binding table is configurable."
    ::= { vtssIpSourceGuardCapabilities 2 }

vtssIpSourceGuardConfig OBJECT IDENTIFIER
    ::= { vtssIpSourceGuardMibObjects 2 }

vtssIpSourceGuardConfigGlobals OBJECT IDENTIFIER
    ::= { vtssIpSourceGuardConfig 1 }

vtssIpSourceGuardConfigGlobalsMode OBJECT-TYPE
    SYNTAX      TruthValue
    MAX-ACCESS  read-write
    STATUS      current
    DESCRIPTION
        "Global mode of IP source guard. TRUE is to enable IP source guard and
         FALSE is to disable it."
    ::= { vtssIpSourceGuardConfigGlobals 1 }

vtssIpSourceGuardConfigInterface OBJECT IDENTIFIER
    ::= { vtssIpSourceGuardConfig 2 }

vtssIpSourceGuardConfigInterfaceTable OBJECT-TYPE
    SYNTAX      SEQUENCE OF VTSSIpSourceGuardConfigInterfaceEntry
    MAX-ACCESS  not-accessible
    STATUS      current
    DESCRIPTION
        "This is a table of IP source guard port configuration parameters."
    ::= { vtssIpSourceGuardConfigInterface 1 }

vtssIpSourceGuardConfigInterfaceEntry OBJECT-TYPE
    SYNTAX      VTSSIpSourceGuardConfigInterfaceEntry
    MAX-ACCESS  not-accessible
    STATUS      current
    DESCRIPTION
        "Each port has a set of parameters."
    INDEX       { vtssIpSourceGuardConfigInterfaceIfIndex }
    ::= { vtssIpSourceGuardConfigInterfaceTable 1 }

VTSSIpSourceGuardConfigInterfaceEntry ::= SEQUENCE {
    vtssIpSourceGuardConfigInterfaceIfIndex            VTSSInterfaceIndex,
    vtssIpSourceGuardConfigInterfaceMode               TruthValue,
    vtssIpSourceGuardConfigInterfaceDynamicEntryCount  Unsigned32
}

vtssIpSourceGuardConfigInterfaceIfIndex OBJECT-TYPE
    SYNTAX      VTSSInterfaceIndex
    MAX-ACCESS  accessible-for-notify
    STATUS      current
    DESCRIPTION
        "Logical interface number of the physical port."
    ::= { vtssIpSourceGuardConfigInterfaceEntry 1 }

vtssIpSourceGuardConfigInterfaceMode OBJECT-TYPE
    SYNTAX      TruthValue
    MAX-ACCESS  read-write
    STATUS      current
    DESCRIPTION
        "Port mode of IP source guard. TURE is to enable IP source guard on the
         port and FALSE is to disable it on the port."
    ::= { vtssIpSourceGuardConfigInterfaceEntry 2 }

vtssIpSourceGuardConfigInterfaceDynamicEntryCount OBJECT-TYPE
    SYNTAX      Unsigned32
    MAX-ACCESS  read-write
    STATUS      current
    DESCRIPTION
        "The dynamic entry count is the max number of dynamic entries allowed on
         the port."
    ::= { vtssIpSourceGuardConfigInterfaceEntry 3 }

vtssIpSourceGuardConfigStatic OBJECT IDENTIFIER
    ::= { vtssIpSourceGuardConfig 3 }

vtssIpSourceGuardConfigStaticTable OBJECT-TYPE
    SYNTAX      SEQUENCE OF VTSSIpSourceGuardConfigStaticEntry
    MAX-ACCESS  not-accessible
    STATUS      current
    DESCRIPTION
        "This is a table for managing the static binding table of IP source
         guard."
    ::= { vtssIpSourceGuardConfigStatic 1 }

vtssIpSourceGuardConfigStaticEntry OBJECT-TYPE
    SYNTAX      VTSSIpSourceGuardConfigStaticEntry
    MAX-ACCESS  not-accessible
    STATUS      current
    DESCRIPTION
        "Each entry has a set of parameters."
    INDEX       { vtssIpSourceGuardConfigStaticIfIndex,
                  vtssIpSourceGuardConfigStaticVlanId,
                  vtssIpSourceGuardConfigStaticIpAddress,
                  vtssIpSourceGuardConfigStaticIpMask }
    ::= { vtssIpSourceGuardConfigStaticTable 1 }

VTSSIpSourceGuardConfigStaticEntry ::= SEQUENCE {
    vtssIpSourceGuardConfigStaticIfIndex     VTSSInterfaceIndex,
    vtssIpSourceGuardConfigStaticVlanId      VTSSVlan,
    vtssIpSourceGuardConfigStaticIpAddress   IpAddress,
    vtssIpSourceGuardConfigStaticIpMask      IpAddress,
    vtssIpSourceGuardConfigStaticMacAddress  MacAddress,
    vtssIpSourceGuardConfigStaticAction      VTSSRowEditorState
}

vtssIpSourceGuardConfigStaticIfIndex OBJECT-TYPE
    SYNTAX      VTSSInterfaceIndex
    MAX-ACCESS  accessible-for-notify
    STATUS      current
    DESCRIPTION
        "Logical interface number of the physical port."
    ::= { vtssIpSourceGuardConfigStaticEntry 1 }

vtssIpSourceGuardConfigStaticVlanId OBJECT-TYPE
    SYNTAX      VTSSVlan
    MAX-ACCESS  accessible-for-notify
    STATUS      current
    DESCRIPTION
        "The VLAN ID."
    ::= { vtssIpSourceGuardConfigStaticEntry 2 }

vtssIpSourceGuardConfigStaticIpAddress OBJECT-TYPE
    SYNTAX      IpAddress
    MAX-ACCESS  accessible-for-notify
    STATUS      current
    DESCRIPTION
        "Assigned IP address."
    ::= { vtssIpSourceGuardConfigStaticEntry 3 }

vtssIpSourceGuardConfigStaticIpMask OBJECT-TYPE
    SYNTAX      IpAddress
    MAX-ACCESS  accessible-for-notify
    STATUS      current
    DESCRIPTION
        "Assigned network mask."
    ::= { vtssIpSourceGuardConfigStaticEntry 4 }

vtssIpSourceGuardConfigStaticMacAddress OBJECT-TYPE
    SYNTAX      MacAddress
    MAX-ACCESS  read-write
    STATUS      current
    DESCRIPTION
        "Assigned MAC Address.
         
         This object is only available if the capability object
         'vtssIpSourceGuardCapabilitiesStaticMacAddress' is True."
    ::= { vtssIpSourceGuardConfigStaticEntry 5 }

vtssIpSourceGuardConfigStaticAction OBJECT-TYPE
    SYNTAX      VTSSRowEditorState
    MAX-ACCESS  read-write
    STATUS      current
    DESCRIPTION
        "Action"
    ::= { vtssIpSourceGuardConfigStaticEntry 100 }

vtssIpSourceGuardConfigStaticTableRowEditor OBJECT IDENTIFIER
    ::= { vtssIpSourceGuardConfigStatic 2 }

vtssIpSourceGuardConfigStaticTableRowEditorIfIndex OBJECT-TYPE
    SYNTAX      VTSSInterfaceIndex
    MAX-ACCESS  read-write
    STATUS      current
    DESCRIPTION
        "Logical interface number of the physical port."
    ::= { vtssIpSourceGuardConfigStaticTableRowEditor 1 }

vtssIpSourceGuardConfigStaticTableRowEditorVlanId OBJECT-TYPE
    SYNTAX      VTSSVlan
    MAX-ACCESS  read-write
    STATUS      current
    DESCRIPTION
        "The VLAN ID."
    ::= { vtssIpSourceGuardConfigStaticTableRowEditor 2 }

vtssIpSourceGuardConfigStaticTableRowEditorIpAddress OBJECT-TYPE
    SYNTAX      IpAddress
    MAX-ACCESS  read-write
    STATUS      current
    DESCRIPTION
        "Assigned IP address."
    ::= { vtssIpSourceGuardConfigStaticTableRowEditor 3 }

vtssIpSourceGuardConfigStaticTableRowEditorIpMask OBJECT-TYPE
    SYNTAX      IpAddress
    MAX-ACCESS  read-write
    STATUS      current
    DESCRIPTION
        "Assigned network mask."
    ::= { vtssIpSourceGuardConfigStaticTableRowEditor 4 }

vtssIpSourceGuardConfigStaticTableRowEditorMacAddress OBJECT-TYPE
    SYNTAX      MacAddress
    MAX-ACCESS  read-write
    STATUS      current
    DESCRIPTION
        "Assigned MAC Address.
         
         This object is only available if the capability object
         'vtssIpSourceGuardCapabilitiesStaticMacAddress' is True."
    ::= { vtssIpSourceGuardConfigStaticTableRowEditor 5 }

vtssIpSourceGuardConfigStaticTableRowEditorAction OBJECT-TYPE
    SYNTAX      VTSSRowEditorState
    MAX-ACCESS  read-write
    STATUS      current
    DESCRIPTION
        "Action"
    ::= { vtssIpSourceGuardConfigStaticTableRowEditor 100 }

vtssIpSourceGuardStatus OBJECT IDENTIFIER
    ::= { vtssIpSourceGuardMibObjects 3 }

vtssIpSourceGuardStatusDynamicTable OBJECT-TYPE
    SYNTAX      SEQUENCE OF VTSSIpSourceGuardStatusDynamicEntry
    MAX-ACCESS  not-accessible
    STATUS      current
    DESCRIPTION
        "This is a table provided dynamic binding table of IP source guard."
    ::= { vtssIpSourceGuardStatus 1 }

vtssIpSourceGuardStatusDynamicEntry OBJECT-TYPE
    SYNTAX      VTSSIpSourceGuardStatusDynamicEntry
    MAX-ACCESS  not-accessible
    STATUS      current
    DESCRIPTION
        "Each entry has a set of parameters."
    INDEX       { vtssIpSourceGuardStatusDynamicIfIndex,
                  vtssIpSourceGuardStatusDynamicVlanId,
                  vtssIpSourceGuardStatusDynamicIpAddress }
    ::= { vtssIpSourceGuardStatusDynamicTable 1 }

VTSSIpSourceGuardStatusDynamicEntry ::= SEQUENCE {
    vtssIpSourceGuardStatusDynamicIfIndex     VTSSInterfaceIndex,
    vtssIpSourceGuardStatusDynamicVlanId      VTSSVlan,
    vtssIpSourceGuardStatusDynamicIpAddress   IpAddress,
    vtssIpSourceGuardStatusDynamicMacAddress  MacAddress
}

vtssIpSourceGuardStatusDynamicIfIndex OBJECT-TYPE
    SYNTAX      VTSSInterfaceIndex
    MAX-ACCESS  accessible-for-notify
    STATUS      current
    DESCRIPTION
        "Logical interface number of the physical port."
    ::= { vtssIpSourceGuardStatusDynamicEntry 1 }

vtssIpSourceGuardStatusDynamicVlanId OBJECT-TYPE
    SYNTAX      VTSSVlan
    MAX-ACCESS  accessible-for-notify
    STATUS      current
    DESCRIPTION
        "The VLAN ID."
    ::= { vtssIpSourceGuardStatusDynamicEntry 2 }

vtssIpSourceGuardStatusDynamicIpAddress OBJECT-TYPE
    SYNTAX      IpAddress
    MAX-ACCESS  accessible-for-notify
    STATUS      current
    DESCRIPTION
        "Learned IP address."
    ::= { vtssIpSourceGuardStatusDynamicEntry 3 }

vtssIpSourceGuardStatusDynamicMacAddress OBJECT-TYPE
    SYNTAX      MacAddress
    MAX-ACCESS  read-only
    STATUS      current
    DESCRIPTION
        "Learned MAC Address."
    ::= { vtssIpSourceGuardStatusDynamicEntry 4 }

vtssIpSourceGuardControl OBJECT IDENTIFIER
    ::= { vtssIpSourceGuardMibObjects 4 }

vtssIpSourceGuardControlTranslate OBJECT IDENTIFIER
    ::= { vtssIpSourceGuardControl 1 }

vtssIpSourceGuardControlTranslateTranslateDynamicToStatic OBJECT-TYPE
    SYNTAX      TruthValue
    MAX-ACCESS  read-write
    STATUS      current
    DESCRIPTION
        "Translate all the current dynamic entries to static ones. Set it as
         TRUE to do the action."
    ::= { vtssIpSourceGuardControlTranslate 1 }

vtssIpSourceGuardMibConformance OBJECT IDENTIFIER
    ::= { vtssIpSourceGuardMib 2 }

vtssIpSourceGuardMibCompliances OBJECT IDENTIFIER
    ::= { vtssIpSourceGuardMibConformance 1 }

vtssIpSourceGuardMibGroups OBJECT IDENTIFIER
    ::= { vtssIpSourceGuardMibConformance 2 }

vtssIpSourceGuardCapabilitiesInfoGroup OBJECT-GROUP
    OBJECTS     { vtssIpSourceGuardCapabilitiesStaticIpMask,
                  vtssIpSourceGuardCapabilitiesStaticMacAddress }
    STATUS      current
    DESCRIPTION
        "A collection of objects."
    ::= { vtssIpSourceGuardMibGroups 1 }

vtssIpSourceGuardConfigGlobalsInfoGroup OBJECT-GROUP
    OBJECTS     { vtssIpSourceGuardConfigGlobalsMode }
    STATUS      current
    DESCRIPTION
        "A collection of objects."
    ::= { vtssIpSourceGuardMibGroups 2 }

vtssIpSourceGuardConfigInterfaceInfoGroup OBJECT-GROUP
    OBJECTS     { vtssIpSourceGuardConfigInterfaceIfIndex,
                  vtssIpSourceGuardConfigInterfaceMode,
                  vtssIpSourceGuardConfigInterfaceDynamicEntryCount }
    STATUS      current
    DESCRIPTION
        "A collection of objects."
    ::= { vtssIpSourceGuardMibGroups 3 }

vtssIpSourceGuardConfigStaticTableInfoGroup OBJECT-GROUP
    OBJECTS     { vtssIpSourceGuardConfigStaticIfIndex,
                  vtssIpSourceGuardConfigStaticVlanId,
                  vtssIpSourceGuardConfigStaticIpAddress,
                  vtssIpSourceGuardConfigStaticIpMask,
                  vtssIpSourceGuardConfigStaticMacAddress,
                  vtssIpSourceGuardConfigStaticAction }
    STATUS      current
    DESCRIPTION
        "A collection of objects."
    ::= { vtssIpSourceGuardMibGroups 4 }

vtssIpSourceGuardConfigStaticTableRowEditorInfoGroup OBJECT-GROUP
    OBJECTS     {                   vtssIpSourceGuardConfigStaticTableRowEditorIfIndex,
                  vtssIpSourceGuardConfigStaticTableRowEditorVlanId,
                  vtssIpSourceGuardConfigStaticTableRowEditorIpAddress,
                  vtssIpSourceGuardConfigStaticTableRowEditorIpMask,
                  vtssIpSourceGuardConfigStaticTableRowEditorMacAddress,
                  vtssIpSourceGuardConfigStaticTableRowEditorAction }
    STATUS      current
    DESCRIPTION
        "A collection of objects."
    ::= { vtssIpSourceGuardMibGroups 5 }

vtssIpSourceGuardStatusDynamicInfoGroup OBJECT-GROUP
    OBJECTS     { vtssIpSourceGuardStatusDynamicIfIndex,
                  vtssIpSourceGuardStatusDynamicVlanId,
                  vtssIpSourceGuardStatusDynamicIpAddress,
                  vtssIpSourceGuardStatusDynamicMacAddress }
    STATUS      current
    DESCRIPTION
        "A collection of objects."
    ::= { vtssIpSourceGuardMibGroups 6 }

vtssIpSourceGuardControlTranslateInfoGroup OBJECT-GROUP
    OBJECTS     {                   vtssIpSourceGuardControlTranslateTranslateDynamicToStatic }
    STATUS      current
    DESCRIPTION
        "A collection of objects."
    ::= { vtssIpSourceGuardMibGroups 7 }

vtssIpSourceGuardMibCompliance MODULE-COMPLIANCE
    STATUS      current
    DESCRIPTION
        "The compliance statement for the implementation."

    MODULE      -- this module

    MANDATORY-GROUPS { vtssIpSourceGuardCapabilitiesInfoGroup,
                       vtssIpSourceGuardConfigGlobalsInfoGroup,
                       vtssIpSourceGuardConfigInterfaceInfoGroup,
                       vtssIpSourceGuardConfigStaticTableInfoGroup,
                       vtssIpSourceGuardConfigStaticTableRowEditorInfoGroup,
                       vtssIpSourceGuardStatusDynamicInfoGroup,
                       vtssIpSourceGuardControlTranslateInfoGroup }

    ::= { vtssIpSourceGuardMibCompliances 1 }

END
