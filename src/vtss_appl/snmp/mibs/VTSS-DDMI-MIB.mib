-- *****************************************************************
-- DDMI-MIB:  Microsemi ENT private MIB
-- ****************************************************************

VTSS-DDMI-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    TruthValue FROM SNMPv2-TC
    VTSSDisplayString FROM VTSS-TC
    VTSSInterfaceIndex FROM VTSS-TC
    VTSSSfpTransceiver FROM VTSS-TC
    ;

vtssDdmiMib MODULE-IDENTITY
    LAST-UPDATED "202102240000Z"
    ORGANIZATION
        "Microsemi Corporation"
    CONTACT-INFO
        "Application support: http://www.microchip.com/support"
    DESCRIPTION
        "This is a private version of DDMI"
    REVISION    "202102240000Z"
    DESCRIPTION
        "Renamed a few parameters and added alarm state"
    REVISION    "201711270000Z"
    DESCRIPTION
        "Add IfIndex to DdmiStatusInterfaceTableInfoGroup. Editorial changes"
    REVISION    "201410100000Z"
    DESCRIPTION
        "Editorial changes"
    REVISION    "201407010000Z"
    DESCRIPTION
        "Initial version"
    ::= { vtssSwitchMgmt 121 }


VTSSddmiMonitorState ::= TEXTUAL-CONVENTION
    STATUS      current
    DESCRIPTION
        "This enumeration defines the monitor state for a particular monitor
         type for SFPs."
    SYNTAX      INTEGER { none(0), lowWarn(1), highWarn(2),
                          lowAlarm(3), highAlarm(4) }

vtssDdmiMibObjects OBJECT IDENTIFIER
    ::= { vtssDdmiMib 1 }

vtssDdmiConfig OBJECT IDENTIFIER
    ::= { vtssDdmiMibObjects 2 }

vtssDdmiConfigGlobals OBJECT IDENTIFIER
    ::= { vtssDdmiConfig 1 }

vtssDdmiConfigGlobalsMode OBJECT-TYPE
    SYNTAX      TruthValue
    MAX-ACCESS  read-write
    STATUS      current
    DESCRIPTION
        "Set to true to enable DDMI on all SFP ports."
    ::= { vtssDdmiConfigGlobals 1 }

vtssDdmiStatus OBJECT IDENTIFIER
    ::= { vtssDdmiMibObjects 3 }

vtssDdmiStatusInterfaceTable OBJECT-TYPE
    SYNTAX      SEQUENCE OF VTSSDdmiStatusInterfaceEntry
    MAX-ACCESS  not-accessible
    STATUS      current
    DESCRIPTION
        "This is a DDMI status table of port interface."
    ::= { vtssDdmiStatus 2 }

vtssDdmiStatusInterfaceEntry OBJECT-TYPE
    SYNTAX      VTSSDdmiStatusInterfaceEntry
    MAX-ACCESS  not-accessible
    STATUS      current
    DESCRIPTION
        "Each entry has a set of DDMI status."
    INDEX       { vtssDdmiStatusInterfaceIfIndex }
    ::= { vtssDdmiStatusInterfaceTable 1 }

VTSSDdmiStatusInterfaceEntry ::= SEQUENCE {
    vtssDdmiStatusInterfaceIfIndex                          VTSSInterfaceIndex,
    vtssDdmiStatusInterfaceA0Supported                      TruthValue,
    vtssDdmiStatusInterfaceA0SfpDetected                    TruthValue,
    vtssDdmiStatusInterfaceA0Vendor                         VTSSDisplayString,
    vtssDdmiStatusInterfaceA0PartNumber                     VTSSDisplayString,
    vtssDdmiStatusInterfaceA0SerialNumber                   VTSSDisplayString,
    vtssDdmiStatusInterfaceA0Revision                       VTSSDisplayString,
    vtssDdmiStatusInterfaceA0DateCode                       VTSSDisplayString,
    vtssDdmiStatusInterfaceA0SfpType                        VTSSSfpTransceiver,
    vtssDdmiStatusInterfaceA2Supported                      TruthValue,
    vtssDdmiStatusInterfaceA2TemperatureState               VTSSddmiMonitorState,
    vtssDdmiStatusInterfaceA2TemperatureCurrent             VTSSDisplayString,
    vtssDdmiStatusInterfaceA2TemperatureHighAlarmThreshold  VTSSDisplayString,
    vtssDdmiStatusInterfaceA2TemperatureLowAlarmThreshold   VTSSDisplayString,
    vtssDdmiStatusInterfaceA2TemperatureHighWarnThreshold   VTSSDisplayString,
    vtssDdmiStatusInterfaceA2TemperatureLowWarnThreshold    VTSSDisplayString,
    vtssDdmiStatusInterfaceA2VoltageState                   VTSSddmiMonitorState,
    vtssDdmiStatusInterfaceA2VoltageCurrent                 VTSSDisplayString,
    vtssDdmiStatusInterfaceA2VoltageHighAlarmThreshold      VTSSDisplayString,
    vtssDdmiStatusInterfaceA2VoltageLowAlarmThreshold       VTSSDisplayString,
    vtssDdmiStatusInterfaceA2VoltageHighWarnThreshold       VTSSDisplayString,
    vtssDdmiStatusInterfaceA2VoltageLowWarnThreshold        VTSSDisplayString,
    vtssDdmiStatusInterfaceA2TxBiasState                    VTSSddmiMonitorState,
    vtssDdmiStatusInterfaceA2TxBiasCurrent                  VTSSDisplayString,
    vtssDdmiStatusInterfaceA2TxBiasHighAlarmThreshold       VTSSDisplayString,
    vtssDdmiStatusInterfaceA2TxBiasLowAlarmThreshold        VTSSDisplayString,
    vtssDdmiStatusInterfaceA2TxBiasHighWarnThreshold        VTSSDisplayString,
    vtssDdmiStatusInterfaceA2TxBiasLowWarnThreshold         VTSSDisplayString,
    vtssDdmiStatusInterfaceA2TxPowerState                   VTSSddmiMonitorState,
    vtssDdmiStatusInterfaceA2TxPowerCurrent                 VTSSDisplayString,
    vtssDdmiStatusInterfaceA2TxPowerHighAlarmThreshold      VTSSDisplayString,
    vtssDdmiStatusInterfaceA2TxPowerLowAlarmThreshold       VTSSDisplayString,
    vtssDdmiStatusInterfaceA2TxPowerHighWarnThreshold       VTSSDisplayString,
    vtssDdmiStatusInterfaceA2TxPowerLowWarnThreshold        VTSSDisplayString,
    vtssDdmiStatusInterfaceA2RxPowerState                   VTSSddmiMonitorState,
    vtssDdmiStatusInterfaceA2RxPowerCurrent                 VTSSDisplayString,
    vtssDdmiStatusInterfaceA2RxPowerHighAlarmThreshold      VTSSDisplayString,
    vtssDdmiStatusInterfaceA2RxPowerLowAlarmThreshold       VTSSDisplayString,
    vtssDdmiStatusInterfaceA2RxPowerHighWarnThreshold       VTSSDisplayString,
    vtssDdmiStatusInterfaceA2RxPowerLowWarnThreshold        VTSSDisplayString
}

vtssDdmiStatusInterfaceIfIndex OBJECT-TYPE
    SYNTAX      VTSSInterfaceIndex
    MAX-ACCESS  accessible-for-notify
    STATUS      current
    DESCRIPTION
        "Interface index number."
    ::= { vtssDdmiStatusInterfaceEntry 1 }

vtssDdmiStatusInterfaceA0Supported OBJECT-TYPE
    SYNTAX      TruthValue
    MAX-ACCESS  read-only
    STATUS      current
    DESCRIPTION
        "Support transceiver status information or not. true is to supported and
         false is not supported."
    ::= { vtssDdmiStatusInterfaceEntry 2 }

vtssDdmiStatusInterfaceA0SfpDetected OBJECT-TYPE
    SYNTAX      TruthValue
    MAX-ACCESS  read-only
    STATUS      current
    DESCRIPTION
        "SFP module is detected or not. true is to detected and false is not
         detected."
    ::= { vtssDdmiStatusInterfaceEntry 3 }

vtssDdmiStatusInterfaceA0Vendor OBJECT-TYPE
    SYNTAX      VTSSDisplayString (SIZE(0..16))
    MAX-ACCESS  read-only
    STATUS      current
    DESCRIPTION
        "Vendor name."
    ::= { vtssDdmiStatusInterfaceEntry 4 }

vtssDdmiStatusInterfaceA0PartNumber OBJECT-TYPE
    SYNTAX      VTSSDisplayString (SIZE(0..16))
    MAX-ACCESS  read-only
    STATUS      current
    DESCRIPTION
        "Part number."
    ::= { vtssDdmiStatusInterfaceEntry 5 }

vtssDdmiStatusInterfaceA0SerialNumber OBJECT-TYPE
    SYNTAX      VTSSDisplayString (SIZE(0..16))
    MAX-ACCESS  read-only
    STATUS      current
    DESCRIPTION
        "Serial number."
    ::= { vtssDdmiStatusInterfaceEntry 6 }

vtssDdmiStatusInterfaceA0Revision OBJECT-TYPE
    SYNTAX      VTSSDisplayString (SIZE(0..16))
    MAX-ACCESS  read-only
    STATUS      current
    DESCRIPTION
        "Revision."
    ::= { vtssDdmiStatusInterfaceEntry 7 }

vtssDdmiStatusInterfaceA0DateCode OBJECT-TYPE
    SYNTAX      VTSSDisplayString (SIZE(0..16))
    MAX-ACCESS  read-only
    STATUS      current
    DESCRIPTION
        "Date Code."
    ::= { vtssDdmiStatusInterfaceEntry 8 }

vtssDdmiStatusInterfaceA0SfpType OBJECT-TYPE
    SYNTAX      VTSSSfpTransceiver
    MAX-ACCESS  read-only
    STATUS      current
    DESCRIPTION
        "SFP type."
    ::= { vtssDdmiStatusInterfaceEntry 9 }

vtssDdmiStatusInterfaceA2Supported OBJECT-TYPE
    SYNTAX      TruthValue
    MAX-ACCESS  read-only
    STATUS      current
    DESCRIPTION
        "True if DDMI status information is supported by the SFP."
    ::= { vtssDdmiStatusInterfaceEntry 1002 }

vtssDdmiStatusInterfaceA2TemperatureState OBJECT-TYPE
    SYNTAX      VTSSddmiMonitorState
    MAX-ACCESS  read-only
    STATUS      current
    DESCRIPTION
        "Current Temperature monitor state"
    ::= { vtssDdmiStatusInterfaceEntry 1003 }

vtssDdmiStatusInterfaceA2TemperatureCurrent OBJECT-TYPE
    SYNTAX      VTSSDisplayString (SIZE(0..16))
    MAX-ACCESS  read-only
    STATUS      current
    DESCRIPTION
        "Current Temperature in degrees Celsius."
    ::= { vtssDdmiStatusInterfaceEntry 1004 }

vtssDdmiStatusInterfaceA2TemperatureHighAlarmThreshold OBJECT-TYPE
    SYNTAX      VTSSDisplayString (SIZE(0..16))
    MAX-ACCESS  read-only
    STATUS      current
    DESCRIPTION
        "Temperature high alarm threshold in degrees Celsius."
    ::= { vtssDdmiStatusInterfaceEntry 1005 }

vtssDdmiStatusInterfaceA2TemperatureLowAlarmThreshold OBJECT-TYPE
    SYNTAX      VTSSDisplayString (SIZE(0..16))
    MAX-ACCESS  read-only
    STATUS      current
    DESCRIPTION
        "Temperature low alarm threshold in degrees Celsius."
    ::= { vtssDdmiStatusInterfaceEntry 1006 }

vtssDdmiStatusInterfaceA2TemperatureHighWarnThreshold OBJECT-TYPE
    SYNTAX      VTSSDisplayString (SIZE(0..16))
    MAX-ACCESS  read-only
    STATUS      current
    DESCRIPTION
        "Temperature high warning threshold in degrees Celsius."
    ::= { vtssDdmiStatusInterfaceEntry 1007 }

vtssDdmiStatusInterfaceA2TemperatureLowWarnThreshold OBJECT-TYPE
    SYNTAX      VTSSDisplayString (SIZE(0..16))
    MAX-ACCESS  read-only
    STATUS      current
    DESCRIPTION
        "Temperature low warning threshold in degrees Celsius."
    ::= { vtssDdmiStatusInterfaceEntry 1008 }

vtssDdmiStatusInterfaceA2VoltageState OBJECT-TYPE
    SYNTAX      VTSSddmiMonitorState
    MAX-ACCESS  read-only
    STATUS      current
    DESCRIPTION
        "Current Voltage monitor state"
    ::= { vtssDdmiStatusInterfaceEntry 1009 }

vtssDdmiStatusInterfaceA2VoltageCurrent OBJECT-TYPE
    SYNTAX      VTSSDisplayString (SIZE(0..16))
    MAX-ACCESS  read-only
    STATUS      current
    DESCRIPTION
        "Current Voltage in Volts."
    ::= { vtssDdmiStatusInterfaceEntry 1010 }

vtssDdmiStatusInterfaceA2VoltageHighAlarmThreshold OBJECT-TYPE
    SYNTAX      VTSSDisplayString (SIZE(0..16))
    MAX-ACCESS  read-only
    STATUS      current
    DESCRIPTION
        "Voltage high alarm threshold in Volts."
    ::= { vtssDdmiStatusInterfaceEntry 1011 }

vtssDdmiStatusInterfaceA2VoltageLowAlarmThreshold OBJECT-TYPE
    SYNTAX      VTSSDisplayString (SIZE(0..16))
    MAX-ACCESS  read-only
    STATUS      current
    DESCRIPTION
        "Voltage low alarm threshold in Volts."
    ::= { vtssDdmiStatusInterfaceEntry 1012 }

vtssDdmiStatusInterfaceA2VoltageHighWarnThreshold OBJECT-TYPE
    SYNTAX      VTSSDisplayString (SIZE(0..16))
    MAX-ACCESS  read-only
    STATUS      current
    DESCRIPTION
        "Voltage high warning threshold in Volts."
    ::= { vtssDdmiStatusInterfaceEntry 1013 }

vtssDdmiStatusInterfaceA2VoltageLowWarnThreshold OBJECT-TYPE
    SYNTAX      VTSSDisplayString (SIZE(0..16))
    MAX-ACCESS  read-only
    STATUS      current
    DESCRIPTION
        "Voltage low warning threshold in Volts."
    ::= { vtssDdmiStatusInterfaceEntry 1014 }

vtssDdmiStatusInterfaceA2TxBiasState OBJECT-TYPE
    SYNTAX      VTSSddmiMonitorState
    MAX-ACCESS  read-only
    STATUS      current
    DESCRIPTION
        "Current TxBias monitor state"
    ::= { vtssDdmiStatusInterfaceEntry 1015 }

vtssDdmiStatusInterfaceA2TxBiasCurrent OBJECT-TYPE
    SYNTAX      VTSSDisplayString (SIZE(0..16))
    MAX-ACCESS  read-only
    STATUS      current
    DESCRIPTION
        "Current TxBias in mA."
    ::= { vtssDdmiStatusInterfaceEntry 1016 }

vtssDdmiStatusInterfaceA2TxBiasHighAlarmThreshold OBJECT-TYPE
    SYNTAX      VTSSDisplayString (SIZE(0..16))
    MAX-ACCESS  read-only
    STATUS      current
    DESCRIPTION
        "TxBias high alarm threshold in mA."
    ::= { vtssDdmiStatusInterfaceEntry 1017 }

vtssDdmiStatusInterfaceA2TxBiasLowAlarmThreshold OBJECT-TYPE
    SYNTAX      VTSSDisplayString (SIZE(0..16))
    MAX-ACCESS  read-only
    STATUS      current
    DESCRIPTION
        "TxBias low alarm threshold in mA."
    ::= { vtssDdmiStatusInterfaceEntry 1018 }

vtssDdmiStatusInterfaceA2TxBiasHighWarnThreshold OBJECT-TYPE
    SYNTAX      VTSSDisplayString (SIZE(0..16))
    MAX-ACCESS  read-only
    STATUS      current
    DESCRIPTION
        "TxBias high warning threshold in mA."
    ::= { vtssDdmiStatusInterfaceEntry 1019 }

vtssDdmiStatusInterfaceA2TxBiasLowWarnThreshold OBJECT-TYPE
    SYNTAX      VTSSDisplayString (SIZE(0..16))
    MAX-ACCESS  read-only
    STATUS      current
    DESCRIPTION
        "TxBias low warning threshold in mA."
    ::= { vtssDdmiStatusInterfaceEntry 1020 }

vtssDdmiStatusInterfaceA2TxPowerState OBJECT-TYPE
    SYNTAX      VTSSddmiMonitorState
    MAX-ACCESS  read-only
    STATUS      current
    DESCRIPTION
        "Current TxPower monitor state"
    ::= { vtssDdmiStatusInterfaceEntry 1021 }

vtssDdmiStatusInterfaceA2TxPowerCurrent OBJECT-TYPE
    SYNTAX      VTSSDisplayString (SIZE(0..16))
    MAX-ACCESS  read-only
    STATUS      current
    DESCRIPTION
        "Current TxPower in mW."
    ::= { vtssDdmiStatusInterfaceEntry 1022 }

vtssDdmiStatusInterfaceA2TxPowerHighAlarmThreshold OBJECT-TYPE
    SYNTAX      VTSSDisplayString (SIZE(0..16))
    MAX-ACCESS  read-only
    STATUS      current
    DESCRIPTION
        "TxPower high alarm threshold in mW."
    ::= { vtssDdmiStatusInterfaceEntry 1023 }

vtssDdmiStatusInterfaceA2TxPowerLowAlarmThreshold OBJECT-TYPE
    SYNTAX      VTSSDisplayString (SIZE(0..16))
    MAX-ACCESS  read-only
    STATUS      current
    DESCRIPTION
        "TxPower low alarm threshold in mW."
    ::= { vtssDdmiStatusInterfaceEntry 1024 }

vtssDdmiStatusInterfaceA2TxPowerHighWarnThreshold OBJECT-TYPE
    SYNTAX      VTSSDisplayString (SIZE(0..16))
    MAX-ACCESS  read-only
    STATUS      current
    DESCRIPTION
        "TxPower high warning threshold in mW."
    ::= { vtssDdmiStatusInterfaceEntry 1025 }

vtssDdmiStatusInterfaceA2TxPowerLowWarnThreshold OBJECT-TYPE
    SYNTAX      VTSSDisplayString (SIZE(0..16))
    MAX-ACCESS  read-only
    STATUS      current
    DESCRIPTION
        "TxPower low warning threshold in mW."
    ::= { vtssDdmiStatusInterfaceEntry 1026 }

vtssDdmiStatusInterfaceA2RxPowerState OBJECT-TYPE
    SYNTAX      VTSSddmiMonitorState
    MAX-ACCESS  read-only
    STATUS      current
    DESCRIPTION
        "Current RxPower monitor state"
    ::= { vtssDdmiStatusInterfaceEntry 1027 }

vtssDdmiStatusInterfaceA2RxPowerCurrent OBJECT-TYPE
    SYNTAX      VTSSDisplayString (SIZE(0..16))
    MAX-ACCESS  read-only
    STATUS      current
    DESCRIPTION
        "Current RxPower in mW."
    ::= { vtssDdmiStatusInterfaceEntry 1028 }

vtssDdmiStatusInterfaceA2RxPowerHighAlarmThreshold OBJECT-TYPE
    SYNTAX      VTSSDisplayString (SIZE(0..16))
    MAX-ACCESS  read-only
    STATUS      current
    DESCRIPTION
        "RxPower high alarm threshold in mW."
    ::= { vtssDdmiStatusInterfaceEntry 1029 }

vtssDdmiStatusInterfaceA2RxPowerLowAlarmThreshold OBJECT-TYPE
    SYNTAX      VTSSDisplayString (SIZE(0..16))
    MAX-ACCESS  read-only
    STATUS      current
    DESCRIPTION
        "RxPower low alarm threshold in mW."
    ::= { vtssDdmiStatusInterfaceEntry 1030 }

vtssDdmiStatusInterfaceA2RxPowerHighWarnThreshold OBJECT-TYPE
    SYNTAX      VTSSDisplayString (SIZE(0..16))
    MAX-ACCESS  read-only
    STATUS      current
    DESCRIPTION
        "RxPower high warning threshold in mW."
    ::= { vtssDdmiStatusInterfaceEntry 1031 }

vtssDdmiStatusInterfaceA2RxPowerLowWarnThreshold OBJECT-TYPE
    SYNTAX      VTSSDisplayString (SIZE(0..16))
    MAX-ACCESS  read-only
    STATUS      current
    DESCRIPTION
        "RxPower low warning threshold in mW."
    ::= { vtssDdmiStatusInterfaceEntry 1032 }

vtssDdmiMibConformance OBJECT IDENTIFIER
    ::= { vtssDdmiMib 2 }

vtssDdmiMibCompliances OBJECT IDENTIFIER
    ::= { vtssDdmiMibConformance 1 }

vtssDdmiMibGroups OBJECT IDENTIFIER
    ::= { vtssDdmiMibConformance 2 }

vtssDdmiConfigGlobalsInfoGroup OBJECT-GROUP
    OBJECTS     { vtssDdmiConfigGlobalsMode }
    STATUS      current
    DESCRIPTION
        "A collection of objects."
    ::= { vtssDdmiMibGroups 1 }

vtssDdmiStatusInterfaceTableInfoGroup OBJECT-GROUP
    OBJECTS     { vtssDdmiStatusInterfaceIfIndex,
                  vtssDdmiStatusInterfaceA0Supported,
                  vtssDdmiStatusInterfaceA0SfpDetected,
                  vtssDdmiStatusInterfaceA0Vendor,
                  vtssDdmiStatusInterfaceA0PartNumber,
                  vtssDdmiStatusInterfaceA0SerialNumber,
                  vtssDdmiStatusInterfaceA0Revision,
                  vtssDdmiStatusInterfaceA0DateCode,
                  vtssDdmiStatusInterfaceA0SfpType,
                  vtssDdmiStatusInterfaceA2Supported,
                  vtssDdmiStatusInterfaceA2TemperatureState,
                  vtssDdmiStatusInterfaceA2TemperatureCurrent,
                  vtssDdmiStatusInterfaceA2TemperatureHighAlarmThreshold,
                  vtssDdmiStatusInterfaceA2TemperatureLowAlarmThreshold,
                  vtssDdmiStatusInterfaceA2TemperatureHighWarnThreshold,
                  vtssDdmiStatusInterfaceA2TemperatureLowWarnThreshold,
                  vtssDdmiStatusInterfaceA2VoltageState,
                  vtssDdmiStatusInterfaceA2VoltageCurrent,
                  vtssDdmiStatusInterfaceA2VoltageHighAlarmThreshold,
                  vtssDdmiStatusInterfaceA2VoltageLowAlarmThreshold,
                  vtssDdmiStatusInterfaceA2VoltageHighWarnThreshold,
                  vtssDdmiStatusInterfaceA2VoltageLowWarnThreshold,
                  vtssDdmiStatusInterfaceA2TxBiasState,
                  vtssDdmiStatusInterfaceA2TxBiasCurrent,
                  vtssDdmiStatusInterfaceA2TxBiasHighAlarmThreshold,
                  vtssDdmiStatusInterfaceA2TxBiasLowAlarmThreshold,
                  vtssDdmiStatusInterfaceA2TxBiasHighWarnThreshold,
                  vtssDdmiStatusInterfaceA2TxBiasLowWarnThreshold,
                  vtssDdmiStatusInterfaceA2TxPowerState,
                  vtssDdmiStatusInterfaceA2TxPowerCurrent,
                  vtssDdmiStatusInterfaceA2TxPowerHighAlarmThreshold,
                  vtssDdmiStatusInterfaceA2TxPowerLowAlarmThreshold,
                  vtssDdmiStatusInterfaceA2TxPowerHighWarnThreshold,
                  vtssDdmiStatusInterfaceA2TxPowerLowWarnThreshold,
                  vtssDdmiStatusInterfaceA2RxPowerState,
                  vtssDdmiStatusInterfaceA2RxPowerCurrent,
                  vtssDdmiStatusInterfaceA2RxPowerHighAlarmThreshold,
                  vtssDdmiStatusInterfaceA2RxPowerLowAlarmThreshold,
                  vtssDdmiStatusInterfaceA2RxPowerHighWarnThreshold,
                  vtssDdmiStatusInterfaceA2RxPowerLowWarnThreshold }
    STATUS      current
    DESCRIPTION
        "A collection of objects."
    ::= { vtssDdmiMibGroups 2 }

vtssDdmiMibCompliance MODULE-COMPLIANCE
    STATUS      current
    DESCRIPTION
        "The compliance statement for the implementation."

    MODULE      -- this module

    MANDATORY-GROUPS { vtssDdmiConfigGlobalsInfoGroup,
                       vtssDdmiStatusInterfaceTableInfoGroup }

    ::= { vtssDdmiMibCompliances 1 }

END
