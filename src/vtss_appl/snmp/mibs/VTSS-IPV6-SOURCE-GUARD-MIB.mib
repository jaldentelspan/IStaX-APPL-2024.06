-- *****************************************************************
-- IPV6-SOURCE-GUARD-MIB:  Microsemi ENT private MIB
-- ****************************************************************

VTSS-IPV6-SOURCE-GUARD-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    Unsigned32 FROM SNMPv2-SMI
    MacAddress FROM SNMPv2-TC
    TruthValue FROM SNMPv2-TC
    VTSSInterfaceIndex FROM VTSS-TC
    VTSSRowEditorState FROM VTSS-TC
    VTSSVlan FROM VTSS-TC
    ;

vtssIpv6SourceGuardMib MODULE-IDENTITY
    LAST-UPDATED "201805230000Z"
    ORGANIZATION
        "Microsemi Corporation"
    CONTACT-INFO
        "Application support: http://www.microchip.com/support"
    DESCRIPTION
        "This is a private version of the IPv6 Source Guard MIB"
    REVISION    "201805230000Z"
    DESCRIPTION
        "Initial version"
    ::= { vtssSwitchMgmt 147 }


vtssIpv6SourceGuardMibObjects OBJECT IDENTIFIER
    ::= { vtssIpv6SourceGuardMib 1 }

vtssIpv6SourceGuardConfig OBJECT IDENTIFIER
    ::= { vtssIpv6SourceGuardMibObjects 2 }

vtssIpv6SourceGuardConfigGlobals OBJECT IDENTIFIER
    ::= { vtssIpv6SourceGuardConfig 1 }

vtssIpv6SourceGuardConfigGlobalsEnabled OBJECT-TYPE
    SYNTAX      TruthValue
    MAX-ACCESS  read-write
    STATUS      current
    DESCRIPTION
        "Global config of IPv6 source guard. TRUE is to enable IP source guard
         and FALSE is to disable it."
    ::= { vtssIpv6SourceGuardConfigGlobals 1 }

vtssIpv6SourceGuardConfigInterface OBJECT IDENTIFIER
    ::= { vtssIpv6SourceGuardConfig 2 }

vtssIpv6SourceGuardConfigInterfaceTable OBJECT-TYPE
    SYNTAX      SEQUENCE OF VTSSIpv6SourceGuardConfigInterfaceEntry
    MAX-ACCESS  not-accessible
    STATUS      current
    DESCRIPTION
        "This is a table to configure IPv6 Source Guard for a specific port."
    ::= { vtssIpv6SourceGuardConfigInterface 1 }

vtssIpv6SourceGuardConfigInterfaceEntry OBJECT-TYPE
    SYNTAX      VTSSIpv6SourceGuardConfigInterfaceEntry
    MAX-ACCESS  not-accessible
    STATUS      current
    DESCRIPTION
        "Each port interface can be configured for ipv6 source guard"
    INDEX       { vtssIpv6SourceGuardConfigInterfaceIfIndex }
    ::= { vtssIpv6SourceGuardConfigInterfaceTable 1 }

VTSSIpv6SourceGuardConfigInterfaceEntry ::= SEQUENCE {
    vtssIpv6SourceGuardConfigInterfaceIfIndex            VTSSInterfaceIndex,
    vtssIpv6SourceGuardConfigInterfaceEnabled            TruthValue,
    vtssIpv6SourceGuardConfigInterfaceMaxDynamicEntries  Unsigned32
}

vtssIpv6SourceGuardConfigInterfaceIfIndex OBJECT-TYPE
    SYNTAX      VTSSInterfaceIndex
    MAX-ACCESS  accessible-for-notify
    STATUS      current
    DESCRIPTION
        "Logical interface number of the physical port."
    ::= { vtssIpv6SourceGuardConfigInterfaceEntry 1 }

vtssIpv6SourceGuardConfigInterfaceEnabled OBJECT-TYPE
    SYNTAX      TruthValue
    MAX-ACCESS  read-write
    STATUS      current
    DESCRIPTION
        "True means that ipv6 source guard is enabled on port."
    ::= { vtssIpv6SourceGuardConfigInterfaceEntry 2 }

vtssIpv6SourceGuardConfigInterfaceMaxDynamicEntries OBJECT-TYPE
    SYNTAX      Unsigned32
    MAX-ACCESS  read-write
    STATUS      current
    DESCRIPTION
        "Max number of allowed dynamic entries per port."
    ::= { vtssIpv6SourceGuardConfigInterfaceEntry 3 }

vtssIpv6SourceGuardConfigStatic OBJECT IDENTIFIER
    ::= { vtssIpv6SourceGuardConfig 3 }

vtssIpv6SourceGuardConfigStaticTable OBJECT-TYPE
    SYNTAX      SEQUENCE OF VTSSIpv6SourceGuardConfigStaticEntry
    MAX-ACCESS  not-accessible
    STATUS      current
    DESCRIPTION
        "This is a table for managing the static binding entries of IPv6 source
         guard."
    ::= { vtssIpv6SourceGuardConfigStatic 1 }

vtssIpv6SourceGuardConfigStaticEntry OBJECT-TYPE
    SYNTAX      VTSSIpv6SourceGuardConfigStaticEntry
    MAX-ACCESS  not-accessible
    STATUS      current
    DESCRIPTION
        "Each entry has a set of parameters."
    INDEX       { vtssIpv6SourceGuardConfigStaticIfindex,
                  vtssIpv6SourceGuardConfigStaticVlanId,
                  vtssIpv6SourceGuardConfigStaticIpv6Address }
    ::= { vtssIpv6SourceGuardConfigStaticTable 1 }

VTSSIpv6SourceGuardConfigStaticEntry ::= SEQUENCE {
    vtssIpv6SourceGuardConfigStaticIfindex      VTSSInterfaceIndex,
    vtssIpv6SourceGuardConfigStaticVlanId       VTSSVlan,
    vtssIpv6SourceGuardConfigStaticIpv6Address  InetAddressIPv6,
    vtssIpv6SourceGuardConfigStaticMacAddress   MacAddress,
    vtssIpv6SourceGuardConfigStaticAction       VTSSRowEditorState
}

vtssIpv6SourceGuardConfigStaticIfindex OBJECT-TYPE
    SYNTAX      VTSSInterfaceIndex
    MAX-ACCESS  accessible-for-notify
    STATUS      current
    DESCRIPTION
        "Logical interface number of the physical port entry is bound to."
    ::= { vtssIpv6SourceGuardConfigStaticEntry 1 }

vtssIpv6SourceGuardConfigStaticVlanId OBJECT-TYPE
    SYNTAX      VTSSVlan
    MAX-ACCESS  accessible-for-notify
    STATUS      current
    DESCRIPTION
        "The VLAN ID. 0 means no vlan id is needed."
    ::= { vtssIpv6SourceGuardConfigStaticEntry 2 }

vtssIpv6SourceGuardConfigStaticIpv6Address OBJECT-TYPE
    SYNTAX      InetAddressIPv6
    MAX-ACCESS  accessible-for-notify
    STATUS      current
    DESCRIPTION
        "Entry's IPv6 address."
    ::= { vtssIpv6SourceGuardConfigStaticEntry 3 }

vtssIpv6SourceGuardConfigStaticMacAddress OBJECT-TYPE
    SYNTAX      MacAddress
    MAX-ACCESS  read-write
    STATUS      current
    DESCRIPTION
        "Assigned MAC Address."
    ::= { vtssIpv6SourceGuardConfigStaticEntry 4 }

vtssIpv6SourceGuardConfigStaticAction OBJECT-TYPE
    SYNTAX      VTSSRowEditorState
    MAX-ACCESS  read-write
    STATUS      current
    DESCRIPTION
        "Action"
    ::= { vtssIpv6SourceGuardConfigStaticEntry 100 }

vtssIpv6SourceGuardConfigStaticTableRowEditor OBJECT IDENTIFIER
    ::= { vtssIpv6SourceGuardConfigStatic 5 }

vtssIpv6SourceGuardConfigStaticTableRowEditorIfindex OBJECT-TYPE
    SYNTAX      VTSSInterfaceIndex
    MAX-ACCESS  read-write
    STATUS      current
    DESCRIPTION
        "Logical interface number of the physical port entry is bound to."
    ::= { vtssIpv6SourceGuardConfigStaticTableRowEditor 1 }

vtssIpv6SourceGuardConfigStaticTableRowEditorVlanId OBJECT-TYPE
    SYNTAX      VTSSVlan
    MAX-ACCESS  read-write
    STATUS      current
    DESCRIPTION
        "The VLAN ID. 0 means no vlan id is needed."
    ::= { vtssIpv6SourceGuardConfigStaticTableRowEditor 2 }

vtssIpv6SourceGuardConfigStaticTableRowEditorIpv6Address OBJECT-TYPE
    SYNTAX      InetAddressIPv6
    MAX-ACCESS  read-write
    STATUS      current
    DESCRIPTION
        "Entry's IPv6 address."
    ::= { vtssIpv6SourceGuardConfigStaticTableRowEditor 3 }

vtssIpv6SourceGuardConfigStaticTableRowEditorMacAddress OBJECT-TYPE
    SYNTAX      MacAddress
    MAX-ACCESS  read-write
    STATUS      current
    DESCRIPTION
        "Assigned MAC Address."
    ::= { vtssIpv6SourceGuardConfigStaticTableRowEditor 4 }

vtssIpv6SourceGuardConfigStaticTableRowEditorAction OBJECT-TYPE
    SYNTAX      VTSSRowEditorState
    MAX-ACCESS  read-write
    STATUS      current
    DESCRIPTION
        "Action"
    ::= { vtssIpv6SourceGuardConfigStaticTableRowEditor 100 }

vtssIpv6SourceGuardStatus OBJECT IDENTIFIER
    ::= { vtssIpv6SourceGuardMibObjects 3 }

vtssIpv6SourceGuardStatusDynamicTable OBJECT-TYPE
    SYNTAX      SEQUENCE OF VTSSIpv6SourceGuardStatusDynamicEntry
    MAX-ACCESS  not-accessible
    STATUS      current
    DESCRIPTION
        "This is a table for managing the static binding entries of IPv6 source
         guard."
    ::= { vtssIpv6SourceGuardStatus 1 }

vtssIpv6SourceGuardStatusDynamicEntry OBJECT-TYPE
    SYNTAX      VTSSIpv6SourceGuardStatusDynamicEntry
    MAX-ACCESS  not-accessible
    STATUS      current
    DESCRIPTION
        "Each entry has a set of parameters."
    INDEX       { vtssIpv6SourceGuardStatusDynamicIfindex,
                  vtssIpv6SourceGuardStatusDynamicVlanId,
                  vtssIpv6SourceGuardStatusDynamicIpv6Address }
    ::= { vtssIpv6SourceGuardStatusDynamicTable 1 }

VTSSIpv6SourceGuardStatusDynamicEntry ::= SEQUENCE {
    vtssIpv6SourceGuardStatusDynamicIfindex      VTSSInterfaceIndex,
    vtssIpv6SourceGuardStatusDynamicVlanId       VTSSVlan,
    vtssIpv6SourceGuardStatusDynamicIpv6Address  InetAddressIPv6,
    vtssIpv6SourceGuardStatusDynamicMacAddress   MacAddress
}

vtssIpv6SourceGuardStatusDynamicIfindex OBJECT-TYPE
    SYNTAX      VTSSInterfaceIndex
    MAX-ACCESS  accessible-for-notify
    STATUS      current
    DESCRIPTION
        "Logical interface number of the physical port entry is bound to."
    ::= { vtssIpv6SourceGuardStatusDynamicEntry 1 }

vtssIpv6SourceGuardStatusDynamicVlanId OBJECT-TYPE
    SYNTAX      VTSSVlan
    MAX-ACCESS  accessible-for-notify
    STATUS      current
    DESCRIPTION
        "The VLAN ID. 0 means no vlan id is needed."
    ::= { vtssIpv6SourceGuardStatusDynamicEntry 2 }

vtssIpv6SourceGuardStatusDynamicIpv6Address OBJECT-TYPE
    SYNTAX      InetAddressIPv6
    MAX-ACCESS  accessible-for-notify
    STATUS      current
    DESCRIPTION
        "Entry's IPv6 address."
    ::= { vtssIpv6SourceGuardStatusDynamicEntry 3 }

vtssIpv6SourceGuardStatusDynamicMacAddress OBJECT-TYPE
    SYNTAX      MacAddress
    MAX-ACCESS  read-only
    STATUS      current
    DESCRIPTION
        "Assigned MAC Address."
    ::= { vtssIpv6SourceGuardStatusDynamicEntry 4 }

vtssIpv6SourceGuardControl OBJECT IDENTIFIER
    ::= { vtssIpv6SourceGuardMibObjects 4 }

vtssIpv6SourceGuardControlTranslate OBJECT IDENTIFIER
    ::= { vtssIpv6SourceGuardControl 1 }

vtssIpv6SourceGuardControlTranslateTranslateDynamicToStatic OBJECT-TYPE
    SYNTAX      TruthValue
    MAX-ACCESS  read-write
    STATUS      current
    DESCRIPTION
        "Translate all the current dynamic entries to static ones. Set it as
         TRUE to do the action."
    ::= { vtssIpv6SourceGuardControlTranslate 1 }

vtssIpv6SourceGuardStatistics OBJECT IDENTIFIER
    ::= { vtssIpv6SourceGuardMibObjects 5 }

vtssIpv6SourceGuardMibConformance OBJECT IDENTIFIER
    ::= { vtssIpv6SourceGuardMib 2 }

vtssIpv6SourceGuardMibCompliances OBJECT IDENTIFIER
    ::= { vtssIpv6SourceGuardMibConformance 1 }

vtssIpv6SourceGuardMibGroups OBJECT IDENTIFIER
    ::= { vtssIpv6SourceGuardMibConformance 2 }

vtssIpv6SourceGuardConfigGlobalsInfoGroup OBJECT-GROUP
    OBJECTS     { vtssIpv6SourceGuardConfigGlobalsEnabled }
    STATUS      current
    DESCRIPTION
        "A collection of objects."
    ::= { vtssIpv6SourceGuardMibGroups 1 }

vtssIpv6SourceGuardConfigInterfaceInfoGroup OBJECT-GROUP
    OBJECTS     { vtssIpv6SourceGuardConfigInterfaceIfIndex,
                  vtssIpv6SourceGuardConfigInterfaceEnabled,
                  vtssIpv6SourceGuardConfigInterfaceMaxDynamicEntries }
    STATUS      current
    DESCRIPTION
        "A collection of objects."
    ::= { vtssIpv6SourceGuardMibGroups 2 }

vtssIpv6SourceGuardConfigStaticTableInfoGroup OBJECT-GROUP
    OBJECTS     { vtssIpv6SourceGuardConfigStaticIfindex,
                  vtssIpv6SourceGuardConfigStaticVlanId,
                  vtssIpv6SourceGuardConfigStaticIpv6Address,
                  vtssIpv6SourceGuardConfigStaticMacAddress,
                  vtssIpv6SourceGuardConfigStaticAction }
    STATUS      current
    DESCRIPTION
        "A collection of objects."
    ::= { vtssIpv6SourceGuardMibGroups 3 }

vtssIpv6SourceGuardConfigStaticTableRowEditorInfoGroup OBJECT-GROUP
    OBJECTS     {                   vtssIpv6SourceGuardConfigStaticTableRowEditorIfindex,
                  vtssIpv6SourceGuardConfigStaticTableRowEditorVlanId,
                  vtssIpv6SourceGuardConfigStaticTableRowEditorIpv6Address,
                  vtssIpv6SourceGuardConfigStaticTableRowEditorMacAddress,
                  vtssIpv6SourceGuardConfigStaticTableRowEditorAction }
    STATUS      current
    DESCRIPTION
        "A collection of objects."
    ::= { vtssIpv6SourceGuardMibGroups 4 }

vtssIpv6SourceGuardStatusDynamicInfoGroup OBJECT-GROUP
    OBJECTS     { vtssIpv6SourceGuardStatusDynamicIfindex,
                  vtssIpv6SourceGuardStatusDynamicVlanId,
                  vtssIpv6SourceGuardStatusDynamicIpv6Address,
                  vtssIpv6SourceGuardStatusDynamicMacAddress }
    STATUS      current
    DESCRIPTION
        "A collection of objects."
    ::= { vtssIpv6SourceGuardMibGroups 5 }

vtssIpv6SourceGuardControlTranslateInfoGroup OBJECT-GROUP
    OBJECTS     {                   vtssIpv6SourceGuardControlTranslateTranslateDynamicToStatic }
    STATUS      current
    DESCRIPTION
        "A collection of objects."
    ::= { vtssIpv6SourceGuardMibGroups 6 }

vtssIpv6SourceGuardMibCompliance MODULE-COMPLIANCE
    STATUS      current
    DESCRIPTION
        "The compliance statement for the implementation."

    MODULE      -- this module

    MANDATORY-GROUPS { vtssIpv6SourceGuardConfigGlobalsInfoGroup,
                       vtssIpv6SourceGuardConfigInterfaceInfoGroup,
                       vtssIpv6SourceGuardConfigStaticTableInfoGroup,
                       vtssIpv6SourceGuardConfigStaticTableRowEditorInfoGroup,
                       vtssIpv6SourceGuardStatusDynamicInfoGroup,
                       vtssIpv6SourceGuardControlTranslateInfoGroup }

    ::= { vtssIpv6SourceGuardMibCompliances 1 }

END
