-- *****************************************************************
-- ACL-MIB:  Microsemi ENT private MIB
-- ****************************************************************

VTSS-ACL-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    Integer32 FROM SNMPv2-SMI
    IpAddress FROM SNMPv2-SMI
    Unsigned32 FROM SNMPv2-SMI
    MacAddress FROM SNMPv2-TC
    TruthValue FROM SNMPv2-TC
    VTSSASRType FROM VTSS-TC
    VTSSASType FROM VTSS-TC
    VTSSAdvDestMacType FROM VTSS-TC
    VTSSBitType FROM VTSS-TC
    VTSSDisplayString FROM VTSS-TC
    VTSSInterfaceIndex FROM VTSS-TC
    VTSSPortList FROM VTSS-TC
    VTSSRowEditorState FROM VTSS-TC
    VTSSUnsigned16 FROM VTSS-TC
    VTSSUnsigned8 FROM VTSS-TC
    VTSSVlanTagPriority FROM VTSS-TC
    ;

vtssAclMib MODULE-IDENTITY
    LAST-UPDATED "201904050000Z"
    ORGANIZATION
        "Microsemi Corporation"
    CONTACT-INFO
        "Application support: http://www.microchip.com/support"
    DESCRIPTION
        "This is a private version of ACL"
    REVISION    "201904050000Z"
    DESCRIPTION
        "Obsoleted EvcPolicerId"
    REVISION    "201501120000Z"
    DESCRIPTION
        "Add ACE parameters for stacking device"
    REVISION    "201411130000Z"
    DESCRIPTION
        "Add ACE Ingress parameters"
    REVISION    "201408050000Z"
    DESCRIPTION
        "Initial version"
    ::= { vtssSwitchMgmt 17 }


VTSSAclAceArpOp ::= TEXTUAL-CONVENTION
    STATUS      current
    DESCRIPTION
        "ARP opcode."
    SYNTAX      INTEGER { any(0), arp(1), rarp(2), other(3) }

VTSSAclAceFrameType ::= TEXTUAL-CONVENTION
    STATUS      current
    DESCRIPTION
        "The frame type of the ACE."
    SYNTAX      INTEGER { any(0), etype(1), arp(4), ipv4(5), ipv6(6) }

VTSSAclAceIngressPortListMode ::= TEXTUAL-CONVENTION
    STATUS      current
    DESCRIPTION
        "The ingress port list mode of the ACE."
    SYNTAX      INTEGER { any(0), specific(1), switch(2),
                          switchport(3) }

VTSSAclAceVlanTagged ::= TEXTUAL-CONVENTION
    STATUS      current
    DESCRIPTION
        "VLAN tagged/untagged."
    SYNTAX      INTEGER { any(0), untagged(1), tagged(2) }

VTSSAclHitAction ::= TEXTUAL-CONVENTION
    STATUS      current
    DESCRIPTION
        "The hit action."
    SYNTAX      INTEGER { permit(0), deny(1), redirect(2), egress(3) }

vtssAclMibObjects OBJECT IDENTIFIER
    ::= { vtssAclMib 1 }

vtssAclCapabilities OBJECT IDENTIFIER
    ::= { vtssAclMibObjects 1 }

vtssAclCapabilitiesAceIdMax OBJECT-TYPE
    SYNTAX      Unsigned32
    MAX-ACCESS  read-only
    STATUS      current
    DESCRIPTION
        "Maximum ID of ACE."
    ::= { vtssAclCapabilities 1 }

vtssAclCapabilitiesPolicyIdMax OBJECT-TYPE
    SYNTAX      Unsigned32
    MAX-ACCESS  read-only
    STATUS      current
    DESCRIPTION
        "Maximum ID of policy."
    ::= { vtssAclCapabilities 2 }

vtssAclCapabilitiesRateLimiterIdMax OBJECT-TYPE
    SYNTAX      Unsigned32
    MAX-ACCESS  read-only
    STATUS      current
    DESCRIPTION
        "Maximum ID of rate limiter."
    ::= { vtssAclCapabilities 3 }

vtssAclCapabilitiesEvcPolicerIdMax OBJECT-TYPE
    SYNTAX      Unsigned32
    MAX-ACCESS  read-only
    STATUS      current
    DESCRIPTION
        "Maximum ID of EVC policer (obsolete. Always 0)."
    ::= { vtssAclCapabilities 4 }

vtssAclCapabilitiesRateLimiterBitRateSupported OBJECT-TYPE
    SYNTAX      TruthValue
    MAX-ACCESS  read-only
    STATUS      current
    DESCRIPTION
        "If true, the rate limiter can be configured by bit rate."
    ::= { vtssAclCapabilities 5 }

vtssAclCapabilitiesEvcPolicerSupported OBJECT-TYPE
    SYNTAX      TruthValue
    MAX-ACCESS  read-only
    STATUS      current
    DESCRIPTION
        "If true, EVC policer can be configured (obsolete. Always false)."
    ::= { vtssAclCapabilities 6 }

vtssAclCapabilitiesMirrorSupported OBJECT-TYPE
    SYNTAX      TruthValue
    MAX-ACCESS  read-only
    STATUS      current
    DESCRIPTION
        "If true, mirror action is supported."
    ::= { vtssAclCapabilities 7 }

vtssAclCapabilitiesMultipleRedirectPortsSupported OBJECT-TYPE
    SYNTAX      TruthValue
    MAX-ACCESS  read-only
    STATUS      current
    DESCRIPTION
        "If true, redirect port list can be configured with multiple ports. If
         false, redirect port list can be configured with only one single port."
    ::= { vtssAclCapabilities 8 }

vtssAclCapabilitiesSecondLookupSupported OBJECT-TYPE
    SYNTAX      TruthValue
    MAX-ACCESS  read-only
    STATUS      current
    DESCRIPTION
        "If true, second lookup can be configured."
    ::= { vtssAclCapabilities 9 }

vtssAclCapabilitiesMultipleIngressPortsSupported OBJECT-TYPE
    SYNTAX      TruthValue
    MAX-ACCESS  read-only
    STATUS      current
    DESCRIPTION
        "If true, ingress port list can be configured with multiple ports. If
         false, ingress port list can be configured with only one single port."
    ::= { vtssAclCapabilities 10 }

vtssAclCapabilitiesEgressPortSupported OBJECT-TYPE
    SYNTAX      TruthValue
    MAX-ACCESS  read-only
    STATUS      current
    DESCRIPTION
        "If true, egress port list can be configured."
    ::= { vtssAclCapabilities 11 }

vtssAclCapabilitiesVlanTaggedSupported OBJECT-TYPE
    SYNTAX      TruthValue
    MAX-ACCESS  read-only
    STATUS      current
    DESCRIPTION
        "If true, VLAN tagged can be configured."
    ::= { vtssAclCapabilities 12 }

vtssAclCapabilitiesStackableAceSupported OBJECT-TYPE
    SYNTAX      TruthValue
    MAX-ACCESS  read-only
    STATUS      current
    DESCRIPTION
        "If true, stackable ACE is supported. The 'switch' and 'switchport' ACE
         ingress type can be configured. Otherwize, only 'any' and 'specific'
         ACE ingress type can be configured."
    ::= { vtssAclCapabilities 13 }

vtssAclConfig OBJECT IDENTIFIER
    ::= { vtssAclMibObjects 2 }

vtssAclConfigInterface OBJECT IDENTIFIER
    ::= { vtssAclConfig 2 }

vtssAclConfigInterfaceConfigTable OBJECT-TYPE
    SYNTAX      SEQUENCE OF VTSSAclConfigInterfaceConfigEntry
    MAX-ACCESS  not-accessible
    STATUS      current
    DESCRIPTION
        "This is a table of interface configuration"
    ::= { vtssAclConfigInterface 1 }

vtssAclConfigInterfaceConfigEntry OBJECT-TYPE
    SYNTAX      VTSSAclConfigInterfaceConfigEntry
    MAX-ACCESS  not-accessible
    STATUS      current
    DESCRIPTION
        "Each interface has a set of parameters"
    INDEX       { vtssAclConfigInterfaceConfigIfIndex }
    ::= { vtssAclConfigInterfaceConfigTable 1 }

VTSSAclConfigInterfaceConfigEntry ::= SEQUENCE {
    vtssAclConfigInterfaceConfigIfIndex           VTSSInterfaceIndex,
    vtssAclConfigInterfaceConfigPolicyId          Unsigned32,
    vtssAclConfigInterfaceConfigHitAction         VTSSAclHitAction,
    vtssAclConfigInterfaceConfigRedirectPortList  VTSSPortList,
    vtssAclConfigInterfaceConfigRateLimiterId     Unsigned32,
    vtssAclConfigInterfaceConfigEvcPolicerId      VTSSUnsigned16,
    vtssAclConfigInterfaceConfigMirror            TruthValue,
    vtssAclConfigInterfaceConfigLogging           TruthValue,
    vtssAclConfigInterfaceConfigShutdown          TruthValue
}

vtssAclConfigInterfaceConfigIfIndex OBJECT-TYPE
    SYNTAX      VTSSInterfaceIndex
    MAX-ACCESS  accessible-for-notify
    STATUS      current
    DESCRIPTION
        "The index of logical interface."
    ::= { vtssAclConfigInterfaceConfigEntry 1 }

vtssAclConfigInterfaceConfigPolicyId OBJECT-TYPE
    SYNTAX      Unsigned32
    MAX-ACCESS  read-write
    STATUS      current
    DESCRIPTION
        "The policy ID."
    ::= { vtssAclConfigInterfaceConfigEntry 2 }

vtssAclConfigInterfaceConfigHitAction OBJECT-TYPE
    SYNTAX      VTSSAclHitAction
    MAX-ACCESS  read-write
    STATUS      current
    DESCRIPTION
        "The hit action operation for this interface. egress(2) is not
         supported."
    ::= { vtssAclConfigInterfaceConfigEntry 101 }

vtssAclConfigInterfaceConfigRedirectPortList OBJECT-TYPE
    SYNTAX      VTSSPortList
    MAX-ACCESS  read-write
    STATUS      current
    DESCRIPTION
        "The redirect port list for this interface."
    ::= { vtssAclConfigInterfaceConfigEntry 102 }

vtssAclConfigInterfaceConfigRateLimiterId OBJECT-TYPE
    SYNTAX      Unsigned32
    MAX-ACCESS  read-write
    STATUS      current
    DESCRIPTION
        "The rate limiter ID. 0 means to be disabled."
    ::= { vtssAclConfigInterfaceConfigEntry 103 }

vtssAclConfigInterfaceConfigEvcPolicerId OBJECT-TYPE
    SYNTAX      VTSSUnsigned16
    MAX-ACCESS  read-write
    STATUS      obsolete
    DESCRIPTION
        "The EVC policer ID. 0 means to be disabled. Obsolete.
         
         This object is only available if the capability object
         'vtssAclCapabilitiesEvcPolicerSupported' is True."
    ::= { vtssAclConfigInterfaceConfigEntry 104 }

vtssAclConfigInterfaceConfigMirror OBJECT-TYPE
    SYNTAX      TruthValue
    MAX-ACCESS  read-write
    STATUS      current
    DESCRIPTION
        "The mirror operation. Frames matching this interface rule are mirrored
         to the destination mirror port that is configured in the mirror
         modules.
         
         This object is only available if the capability object
         'vtssAclCapabilitiesMirrorSupported' is True."
    ::= { vtssAclConfigInterfaceConfigEntry 105 }

vtssAclConfigInterfaceConfigLogging OBJECT-TYPE
    SYNTAX      TruthValue
    MAX-ACCESS  read-write
    STATUS      current
    DESCRIPTION
        "Specify the logging operation of the interface. Notice that the logging
         message doesn't include the 4 bytes CRC information. The allowed values
         are: True - Frames matching the ACE are stored in the System Log. False
         - Frames matching the ACE are not logged. Note: The logging feature
         only works when the packet length is less than 1518(without VLAN tags)
         and the System Log memory size and logging rate is limited."
    ::= { vtssAclConfigInterfaceConfigEntry 106 }

vtssAclConfigInterfaceConfigShutdown OBJECT-TYPE
    SYNTAX      TruthValue
    MAX-ACCESS  read-write
    STATUS      current
    DESCRIPTION
        "Specify the port shut down operation of the interface. The allowed
         values are: True - If a frame matches the interface rule, the ingress
         port will be disabled. False - Port shut down is disabled for the
         interface. Note: The shutdown feature only works when the packet length
         is less than 1518(without VLAN tags)."
    ::= { vtssAclConfigInterfaceConfigEntry 107 }

vtssAclConfigRateLimiterTable OBJECT-TYPE
    SYNTAX      SEQUENCE OF VTSSAclConfigRateLimiterEntry
    MAX-ACCESS  not-accessible
    STATUS      current
    DESCRIPTION
        "This is a table of rate limiter configuration"
    ::= { vtssAclConfig 3 }

vtssAclConfigRateLimiterEntry OBJECT-TYPE
    SYNTAX      VTSSAclConfigRateLimiterEntry
    MAX-ACCESS  not-accessible
    STATUS      current
    DESCRIPTION
        "Each rate limiter has a set of parameters"
    INDEX       { vtssAclConfigRateLimiterRateLimiterId }
    ::= { vtssAclConfigRateLimiterTable 1 }

VTSSAclConfigRateLimiterEntry ::= SEQUENCE {
    vtssAclConfigRateLimiterRateLimiterId  Integer32,
    vtssAclConfigRateLimiterBitRateEnable  TruthValue,
    vtssAclConfigRateLimiterBitRate        Unsigned32,
    vtssAclConfigRateLimiterPacketRate     Unsigned32
}

vtssAclConfigRateLimiterRateLimiterId OBJECT-TYPE
    SYNTAX      Integer32 (0..2147483647)
    MAX-ACCESS  accessible-for-notify
    STATUS      current
    DESCRIPTION
        "The rate limter ID."
    ::= { vtssAclConfigRateLimiterEntry 1 }

vtssAclConfigRateLimiterBitRateEnable OBJECT-TYPE
    SYNTAX      TruthValue
    MAX-ACCESS  read-write
    STATUS      current
    DESCRIPTION
        "Use bit rate policing instead of packet rate. True means bit rate is
         used and false means packet rate is used.
         
         This object is only available if the capability object
         'vtssAclCapabilitiesRateLimiterBitRateSupported' is True."
    ::= { vtssAclConfigRateLimiterEntry 2 }

vtssAclConfigRateLimiterBitRate OBJECT-TYPE
    SYNTAX      Unsigned32
    MAX-ACCESS  read-write
    STATUS      current
    DESCRIPTION
        "Bit rate in kbps.
         
         This object is only available if the capability object
         'vtssAclCapabilitiesRateLimiterBitRateSupported' is True."
    ::= { vtssAclConfigRateLimiterEntry 3 }

vtssAclConfigRateLimiterPacketRate OBJECT-TYPE
    SYNTAX      Unsigned32
    MAX-ACCESS  read-write
    STATUS      current
    DESCRIPTION
        "Packet rate in pps."
    ::= { vtssAclConfigRateLimiterEntry 4 }

vtssAclConfigAce OBJECT IDENTIFIER
    ::= { vtssAclConfig 4 }

vtssAclConfigAceTable OBJECT-TYPE
    SYNTAX      SEQUENCE OF VTSSAclConfigAceEntry
    MAX-ACCESS  not-accessible
    STATUS      current
    DESCRIPTION
        "The ACL ACE configuration table."
    ::= { vtssAclConfigAce 1 }

vtssAclConfigAceEntry OBJECT-TYPE
    SYNTAX      VTSSAclConfigAceEntry
    MAX-ACCESS  not-accessible
    STATUS      current
    DESCRIPTION
        "Each row contains a set of parameters."
    INDEX       { vtssAclConfigAceAceId }
    ::= { vtssAclConfigAceTable 1 }

VTSSAclConfigAceEntry ::= SEQUENCE {
    vtssAclConfigAceAceId                       Integer32,
    vtssAclConfigAceNextAceId                   Unsigned32,
    vtssAclConfigAceHitAction                   VTSSAclHitAction,
    vtssAclConfigAceRedirectPortList            VTSSPortList,
    vtssAclConfigAceRedirectPortListSwitchPort  Unsigned32,
    vtssAclConfigAceEgressPortList              VTSSPortList,
    vtssAclConfigAceRateLimiterId               Unsigned32,
    vtssAclConfigAceEvcPolicerId                VTSSUnsigned16,
    vtssAclConfigAceMirror                      TruthValue,
    vtssAclConfigAceLogging                     TruthValue,
    vtssAclConfigAceShutdown                    TruthValue,
    vtssAclConfigAceIngressPortListMode         VTSSAclAceIngressPortListMode,
    vtssAclConfigAceIngressPortList             VTSSPortList,
    vtssAclConfigAceIngressPortListSwitch       Unsigned32,
    vtssAclConfigAceIngressPortListSwitchPort   Unsigned32,
    vtssAclConfigAcePolicyValue                 VTSSUnsigned8,
    vtssAclConfigAcePolicyMask                  VTSSUnsigned8,
    vtssAclConfigAceSecondLookup                TruthValue,
    vtssAclConfigAceVlanId                      VTSSUnsigned16,
    vtssAclConfigAceVlanTagPriority             VTSSVlanTagPriority,
    vtssAclConfigAceVlanTagged                  VTSSAclAceVlanTagged,
    vtssAclConfigAceFrameType                   VTSSAclAceFrameType,
    vtssAclConfigAceDestMacOp                   VTSSAdvDestMacType,
    vtssAclConfigAceEtherSrcMacOp               VTSSASType,
    vtssAclConfigAceEtherSrcMac                 MacAddress,
    vtssAclConfigAceEtherDestMac                MacAddress,
    vtssAclConfigAceEtherType                   VTSSUnsigned16,
    vtssAclConfigAceArpSrcMacOp                 VTSSASType,
    vtssAclConfigAceArpSrcMac                   MacAddress,
    vtssAclConfigAceArpSenderIp                 IpAddress,
    vtssAclConfigAceArpSenderIpMask             IpAddress,
    vtssAclConfigAceArpTargetIp                 IpAddress,
    vtssAclConfigAceArpTargetIpMask             IpAddress,
    vtssAclConfigAceArpOpcode                   VTSSAclAceArpOp,
    vtssAclConfigAceArpFlagReq                  VTSSBitType,
    vtssAclConfigAceArpFlagSha                  VTSSBitType,
    vtssAclConfigAceArpFlagTha                  VTSSBitType,
    vtssAclConfigAceArpFlagHln                  VTSSBitType,
    vtssAclConfigAceArpFlagHrd                  VTSSBitType,
    vtssAclConfigAceArpFlagPro                  VTSSBitType,
    vtssAclConfigAceIpv4ProtocolOp              VTSSASType,
    vtssAclConfigAceIpv4Protocol                VTSSUnsigned8,
    vtssAclConfigAceIpv4SrcIp                   IpAddress,
    vtssAclConfigAceIpv4SrcIpMask               IpAddress,
    vtssAclConfigAceIpv4DestIp                  IpAddress,
    vtssAclConfigAceIpv4DestIpMask              IpAddress,
    vtssAclConfigAceIpv4IcmpTypeOp              VTSSASType,
    vtssAclConfigAceIpv4IcmpType                VTSSUnsigned8,
    vtssAclConfigAceIpv4IcmpCodeOp              VTSSASType,
    vtssAclConfigAceIpv4IcmpCode                VTSSUnsigned8,
    vtssAclConfigAceIpv4SrcPortOp               VTSSASRType,
    vtssAclConfigAceIpv4SrcPort                 VTSSUnsigned16,
    vtssAclConfigAceIpv4SrcPortRange            VTSSUnsigned16,
    vtssAclConfigAceIpv4DestPortOp              VTSSASRType,
    vtssAclConfigAceIpv4DestPort                VTSSUnsigned16,
    vtssAclConfigAceIpv4DestPortRange           VTSSUnsigned16,
    vtssAclConfigAceIpv4FlagTtl                 VTSSBitType,
    vtssAclConfigAceIpv4FlagFragment            VTSSBitType,
    vtssAclConfigAceIpv4FlagIpOption            VTSSBitType,
    vtssAclConfigAceIpv4TcpFlagFin              VTSSBitType,
    vtssAclConfigAceIpv4TcpFlagSyn              VTSSBitType,
    vtssAclConfigAceIpv4TcpFlagRst              VTSSBitType,
    vtssAclConfigAceIpv4TcpFlagPsh              VTSSBitType,
    vtssAclConfigAceIpv4TcpFlagAck              VTSSBitType,
    vtssAclConfigAceIpv4TcpFlagUrg              VTSSBitType,
    vtssAclConfigAceIpv6NextHeaderOp            VTSSASType,
    vtssAclConfigAceIpv6NextHeader              VTSSUnsigned8,
    vtssAclConfigAceIpv6Icmpv6TypeOp            VTSSASType,
    vtssAclConfigAceIpv6Icmpv6Type              VTSSUnsigned8,
    vtssAclConfigAceIpv6Icmpv6CodeOp            VTSSASType,
    vtssAclConfigAceIpv6Icmpv6Code              VTSSUnsigned8,
    vtssAclConfigAceIpv6SrcIp                   InetAddressIPv6,
    vtssAclConfigAceIpv6SrcIpMask               InetAddressIPv6,
    vtssAclConfigAceIpv6SrcPortOp               VTSSASRType,
    vtssAclConfigAceIpv6SrcPort                 VTSSUnsigned16,
    vtssAclConfigAceIpv6SrcPortRange            VTSSUnsigned16,
    vtssAclConfigAceIpv6DestPortOp              VTSSASRType,
    vtssAclConfigAceIpv6DestPort                VTSSUnsigned16,
    vtssAclConfigAceIpv6DestPortRange           VTSSUnsigned16,
    vtssAclConfigAceIpv6FlagTtl                 VTSSBitType,
    vtssAclConfigAceIpv6TcpFlagFin              VTSSBitType,
    vtssAclConfigAceIpv6TcpFlagSyn              VTSSBitType,
    vtssAclConfigAceIpv6TcpFlagRst              VTSSBitType,
    vtssAclConfigAceIpv6TcpFlagPsh              VTSSBitType,
    vtssAclConfigAceIpv6TcpFlagAck              VTSSBitType,
    vtssAclConfigAceIpv6TcpFlagUrg              VTSSBitType,
    vtssAclConfigAceAction                      VTSSRowEditorState
}

vtssAclConfigAceAceId OBJECT-TYPE
    SYNTAX      Integer32 (0..2147483647)
    MAX-ACCESS  accessible-for-notify
    STATUS      current
    DESCRIPTION
        "The ACE ID."
    ::= { vtssAclConfigAceEntry 1 }

vtssAclConfigAceNextAceId OBJECT-TYPE
    SYNTAX      Unsigned32
    MAX-ACCESS  read-write
    STATUS      current
    DESCRIPTION
        "The ID of ACE next to this ACE."
    ::= { vtssAclConfigAceEntry 2 }

vtssAclConfigAceHitAction OBJECT-TYPE
    SYNTAX      VTSSAclHitAction
    MAX-ACCESS  read-write
    STATUS      current
    DESCRIPTION
        "The hit action operation for this ACE."
    ::= { vtssAclConfigAceEntry 101 }

vtssAclConfigAceRedirectPortList OBJECT-TYPE
    SYNTAX      VTSSPortList
    MAX-ACCESS  read-write
    STATUS      current
    DESCRIPTION
        "The redirect port list for this ACE."
    ::= { vtssAclConfigAceEntry 102 }

vtssAclConfigAceRedirectPortListSwitchPort OBJECT-TYPE
    SYNTAX      Unsigned32
    MAX-ACCESS  read-write
    STATUS      current
    DESCRIPTION
        "The redirect switch port for this ACE. The object is only abaliable if
         AclAceIngressPortListMode is switchport. And it is used when this ACE
         is applied on specific switch port of all switches in stackable
         devices.
         
         This object is only available if the capability object
         'vtssAclCapabilitiesStackableAceSupported' is True."
    ::= { vtssAclConfigAceEntry 103 }

vtssAclConfigAceEgressPortList OBJECT-TYPE
    SYNTAX      VTSSPortList
    MAX-ACCESS  read-write
    STATUS      current
    DESCRIPTION
        "The egress port list. The port list is to define what ports are allowed
         to be egress ports. If the egress port of an incoming frame is in the
         port list then the frame will be forwared to that port. Otherwise, if
         the egress port is not in the port list then the egress port is not
         allowed and the incoming frame will be dropped.
         
         This object is only available if the capability object
         'vtssAclCapabilitiesEgressPortSupported' is True."
    ::= { vtssAclConfigAceEntry 104 }

vtssAclConfigAceRateLimiterId OBJECT-TYPE
    SYNTAX      Unsigned32
    MAX-ACCESS  read-write
    STATUS      current
    DESCRIPTION
        "The rate limiter ID. 0 means to be disabled."
    ::= { vtssAclConfigAceEntry 105 }

vtssAclConfigAceEvcPolicerId OBJECT-TYPE
    SYNTAX      VTSSUnsigned16
    MAX-ACCESS  read-write
    STATUS      obsolete
    DESCRIPTION
        "The EVC policer ID. 0 means to be disabled. Obsolete.
         
         This object is only available if the capability object
         'vtssAclCapabilitiesEvcPolicerSupported' is True."
    ::= { vtssAclConfigAceEntry 106 }

vtssAclConfigAceMirror OBJECT-TYPE
    SYNTAX      TruthValue
    MAX-ACCESS  read-write
    STATUS      current
    DESCRIPTION
        "The mirror operation. Frames matching this ACE are mirrored to the
         destination mirror port that is configured in the mirror module.
         
         This object is only available if the capability object
         'vtssAclCapabilitiesMirrorSupported' is True."
    ::= { vtssAclConfigAceEntry 107 }

vtssAclConfigAceLogging OBJECT-TYPE
    SYNTAX      TruthValue
    MAX-ACCESS  read-write
    STATUS      current
    DESCRIPTION
        "Specify the logging operation of the ACE. Notice that the logging
         message doesn't include the 4 bytes CRC information. The allowed values
         are: True - Frames matching the ACE are stored in the System Log. False
         - Frames matching the ACE are not logged. Note: The logging feature
         only works when the packet length is less than 1518(without VLAN tags)
         and the system log memory size and logging rate is limited."
    ::= { vtssAclConfigAceEntry 108 }

vtssAclConfigAceShutdown OBJECT-TYPE
    SYNTAX      TruthValue
    MAX-ACCESS  read-write
    STATUS      current
    DESCRIPTION
        "Specify the port shut down operation of the ACE. The allowed values
         are: True: If a frame matches the ACE, the ingress port will be shuted
         down. False: Port shut down is disabled for the ACE. Note: The shutdown
         feature only works when the packet length is less than 1518(without
         VLAN tags)."
    ::= { vtssAclConfigAceEntry 109 }

vtssAclConfigAceIngressPortListMode OBJECT-TYPE
    SYNTAX      VTSSAclAceIngressPortListMode
    MAX-ACCESS  read-write
    STATUS      current
    DESCRIPTION
        "The ingress port list mode for this ACE. The possible mode are: 'any':
         Indicates this ACE is applied on all switches and all ports.
         'specific': Indicates this ACE is applied on specific switch and
         specific ports. 'switch': Indicates this ACE is applied on all ports of
         specific switch in stackable devices. 'switchport': Indicates this ACE
         is applied on specific switch port of all switches in stackable
         devices."
    ::= { vtssAclConfigAceEntry 201 }

vtssAclConfigAceIngressPortList OBJECT-TYPE
    SYNTAX      VTSSPortList
    MAX-ACCESS  read-write
    STATUS      current
    DESCRIPTION
        "The ingress port list for this ACE. The object is only abaliable if
         AclAceIngressPortListMode is specific. And it is used when this ACE is
         applied on specific switch and specific ports."
    ::= { vtssAclConfigAceEntry 202 }

vtssAclConfigAceIngressPortListSwitch OBJECT-TYPE
    SYNTAX      Unsigned32
    MAX-ACCESS  read-write
    STATUS      current
    DESCRIPTION
        "The ingress switch ID for this ACE. The object is only abaliable if
         AclAceIngressPortListMode is switch. And it is used when this ACE is
         applied on specific switch port of all switches in stackable devices.
         
         This object is only available if the capability object
         'vtssAclCapabilitiesStackableAceSupported' is True."
    ::= { vtssAclConfigAceEntry 203 }

vtssAclConfigAceIngressPortListSwitchPort OBJECT-TYPE
    SYNTAX      Unsigned32
    MAX-ACCESS  read-write
    STATUS      current
    DESCRIPTION
        "The ingress switch port for this ACE. The object is only abaliable if
         AclAceIngressPortListMode is switchport. And it is used when this ACE
         is applied on specific switch port of all switches in stackable
         devices.
         
         This object is only available if the capability object
         'vtssAclCapabilitiesStackableAceSupported' is True."
    ::= { vtssAclConfigAceEntry 204 }

vtssAclConfigAcePolicyValue OBJECT-TYPE
    SYNTAX      VTSSUnsigned8
    MAX-ACCESS  read-write
    STATUS      current
    DESCRIPTION
        "The policy number for this ACE."
    ::= { vtssAclConfigAceEntry 205 }

vtssAclConfigAcePolicyMask OBJECT-TYPE
    SYNTAX      VTSSUnsigned8
    MAX-ACCESS  read-write
    STATUS      current
    DESCRIPTION
        "The policy mask for this ACE. The allowed range is 0x0 to 0xff. If the
         binary bit value is '0', it means this bit is don't-care. The real
         matched pattern is [policy_value & policy_bitmask]. For example, if the
         policy value is 3 and the policy bitmask is 0x10(bit 0 is don't-care
         bit), then policy 2 and 3 are applied to this rule."
    ::= { vtssAclConfigAceEntry 206 }

vtssAclConfigAceSecondLookup OBJECT-TYPE
    SYNTAX      TruthValue
    MAX-ACCESS  read-write
    STATUS      current
    DESCRIPTION
        "The second lookup operation for this ACE.
         
         This object is only available if the capability object
         'vtssAclCapabilitiesSecondLookupSupported' is True."
    ::= { vtssAclConfigAceEntry 207 }

vtssAclConfigAceVlanId OBJECT-TYPE
    SYNTAX      VTSSUnsigned16
    MAX-ACCESS  read-write
    STATUS      current
    DESCRIPTION
        "The VLAN ID for this ACE. Possible values are: 0(disabled), 1-4095."
    ::= { vtssAclConfigAceEntry 301 }

vtssAclConfigAceVlanTagPriority OBJECT-TYPE
    SYNTAX      VTSSVlanTagPriority
    MAX-ACCESS  read-write
    STATUS      current
    DESCRIPTION
        "The VLAN tag priority for this ACE."
    ::= { vtssAclConfigAceEntry 302 }

vtssAclConfigAceVlanTagged OBJECT-TYPE
    SYNTAX      VTSSAclAceVlanTagged
    MAX-ACCESS  read-write
    STATUS      current
    DESCRIPTION
        "The 802.1Q VLAN tagged for this ACE.
         
         This object is only available if the capability object
         'vtssAclCapabilitiesVlanTaggedSupported' is True."
    ::= { vtssAclConfigAceEntry 303 }

vtssAclConfigAceFrameType OBJECT-TYPE
    SYNTAX      VTSSAclAceFrameType
    MAX-ACCESS  read-write
    STATUS      current
    DESCRIPTION
        "The frame type for this ACE."
    ::= { vtssAclConfigAceEntry 401 }

vtssAclConfigAceDestMacOp OBJECT-TYPE
    SYNTAX      VTSSAdvDestMacType
    MAX-ACCESS  read-write
    STATUS      current
    DESCRIPTION
        "Indicates how a packet's destination MAC address to be matched."
    ::= { vtssAclConfigAceEntry 402 }

vtssAclConfigAceEtherSrcMacOp OBJECT-TYPE
    SYNTAX      VTSSASType
    MAX-ACCESS  read-write
    STATUS      current
    DESCRIPTION
        "Indicates how a Ethernet type packet's source MAC address to be
         matched. This object is only available if FrameType is ether(1)."
    ::= { vtssAclConfigAceEntry 501 }

vtssAclConfigAceEtherSrcMac OBJECT-TYPE
    SYNTAX      MacAddress
    MAX-ACCESS  read-write
    STATUS      current
    DESCRIPTION
        "Indicates the 48 bits source MAC address. This object is only available
         if FrameType is ether(1) and EtherSrcMacOp is specific(1)."
    ::= { vtssAclConfigAceEntry 502 }

vtssAclConfigAceEtherDestMac OBJECT-TYPE
    SYNTAX      MacAddress
    MAX-ACCESS  read-write
    STATUS      current
    DESCRIPTION
        "Indicates the 48 bits destination MAC address. This object is only
         available if FrameType is ether(1) and EtherDestMacOp is specific(1)."
    ::= { vtssAclConfigAceEntry 503 }

vtssAclConfigAceEtherType OBJECT-TYPE
    SYNTAX      VTSSUnsigned16
    MAX-ACCESS  read-write
    STATUS      current
    DESCRIPTION
        "Indicates the packet's 16 bit Ethernet type field. Possible values are:
         0(disabled), 0x600-0xFFFF but excluding 0x800(IPv4), 0x806(ARP) and
         0x86DD(IPv6). This object is only available if FrameType is ether(1)
         and EtherDestMacOp is specific(1)."
    ::= { vtssAclConfigAceEntry 504 }

vtssAclConfigAceArpSrcMacOp OBJECT-TYPE
    SYNTAX      VTSSASType
    MAX-ACCESS  read-write
    STATUS      current
    DESCRIPTION
        "Indicates how a ARP packet's source MAC address to be matched. This
         object is only available if FrameType is arp(4)."
    ::= { vtssAclConfigAceEntry 601 }

vtssAclConfigAceArpSrcMac OBJECT-TYPE
    SYNTAX      MacAddress
    MAX-ACCESS  read-write
    STATUS      current
    DESCRIPTION
        "Indicates the 48 bits source MAC address. This object is only available
         if FrameType is arp(4) and ArpSrcMacOp is specific(1)."
    ::= { vtssAclConfigAceEntry 602 }

vtssAclConfigAceArpSenderIp OBJECT-TYPE
    SYNTAX      IpAddress
    MAX-ACCESS  read-write
    STATUS      current
    DESCRIPTION
        "The specified ARP sender IP address. The packet's sender address is
         AND-ed with the value of ArpSenderIpMask and then compared with the
         value of this object. If ArpSenderIp and ArpSrcIpMask are 0.0.0.0, this
         entry matches any sender IP address. This object is only available if
         FrameType is arp(4)."
    ::= { vtssAclConfigAceEntry 603 }

vtssAclConfigAceArpSenderIpMask OBJECT-TYPE
    SYNTAX      IpAddress
    MAX-ACCESS  read-write
    STATUS      current
    DESCRIPTION
        "The specified ARP sender IP address mask. This object is only available
         if FrameType is arp(4)."
    ::= { vtssAclConfigAceEntry 604 }

vtssAclConfigAceArpTargetIp OBJECT-TYPE
    SYNTAX      IpAddress
    MAX-ACCESS  read-write
    STATUS      current
    DESCRIPTION
        "The specified ARP target IP address. The packet's target address is
         AND-ed with the value of ArpTragetIpMask and then compared with the
         value of this object. If ArpTragetIp and ArpSrcIpMask are 0.0.0.0, this
         entry matches any target IP address. This object is only available if
         FrameType is arp(4)."
    ::= { vtssAclConfigAceEntry 605 }

vtssAclConfigAceArpTargetIpMask OBJECT-TYPE
    SYNTAX      IpAddress
    MAX-ACCESS  read-write
    STATUS      current
    DESCRIPTION
        "The specified ARP target IP address mask. This object is only available
         if FrameType is arp(4)."
    ::= { vtssAclConfigAceEntry 606 }

vtssAclConfigAceArpOpcode OBJECT-TYPE
    SYNTAX      VTSSAclAceArpOp
    MAX-ACCESS  read-write
    STATUS      current
    DESCRIPTION
        "Indicates how a ARP packet's opcode to be matched. This object is only
         available if FrameType is arp(4)."
    ::= { vtssAclConfigAceEntry 607 }

vtssAclConfigAceArpFlagReq OBJECT-TYPE
    SYNTAX      VTSSBitType
    MAX-ACCESS  read-write
    STATUS      current
    DESCRIPTION
        "Indicates how a ARP packet's request/reply opcode is to be compared.
         This object is only available if FrameType is arp(4)."
    ::= { vtssAclConfigAceEntry 608 }

vtssAclConfigAceArpFlagSha OBJECT-TYPE
    SYNTAX      VTSSBitType
    MAX-ACCESS  read-write
    STATUS      current
    DESCRIPTION
        "Indicates how a ARP packet's sender hardware address field (SHA) to be
         compared. This object is only available if FrameType is arp(4)."
    ::= { vtssAclConfigAceEntry 609 }

vtssAclConfigAceArpFlagTha OBJECT-TYPE
    SYNTAX      VTSSBitType
    MAX-ACCESS  read-write
    STATUS      current
    DESCRIPTION
        "Indicates how a ARP packet's target hardware address field (THA) is to
         be compared. This object is only available if FrameType is arp(4)."
    ::= { vtssAclConfigAceEntry 610 }

vtssAclConfigAceArpFlagHln OBJECT-TYPE
    SYNTAX      VTSSBitType
    MAX-ACCESS  read-write
    STATUS      current
    DESCRIPTION
        "Indicates how a ARP packet's s hardware address length field (HLN) is
         to be compared. The value 0 means any HLN value is allowed (don't-care
         field), value 1 means HLN is not equal to Ethernet (0x06) or the (PLN)
         is not equal to IPv4 (0x04) and value 2 means HLN is equal to Ethernet
         (0x06) or the (PLN) is not equal to IPv4 (0x04). This object is only
         available if FrameType is arp(4)."
    ::= { vtssAclConfigAceEntry 611 }

vtssAclConfigAceArpFlagHrd OBJECT-TYPE
    SYNTAX      VTSSBitType
    MAX-ACCESS  read-write
    STATUS      current
    DESCRIPTION
        "Indicates how a ARP packet's hardware address space field (HRD) is to
         be compared. The value 0 means any HRD value is allowed (don't-care
         field), value 1 means HRD is not equal to Ethernet (1) and value 2
         means HRD is equal to Ethernet (1). This object is only available if
         FrameType is arp(4)."
    ::= { vtssAclConfigAceEntry 612 }

vtssAclConfigAceArpFlagPro OBJECT-TYPE
    SYNTAX      VTSSBitType
    MAX-ACCESS  read-write
    STATUS      current
    DESCRIPTION
        "Indicates how a ARP packet's protocol address space field (PRO) is to
         be compared. The value 0 means any PRO value is allowed (don't-care
         field), value 1 means PRO is not equal to IP (0x800) and value 2 means
         PRO is equal to IP (0x800). This object is only available if FrameType
         is arp(4)."
    ::= { vtssAclConfigAceEntry 613 }

vtssAclConfigAceIpv4ProtocolOp OBJECT-TYPE
    SYNTAX      VTSSASType
    MAX-ACCESS  read-write
    STATUS      current
    DESCRIPTION
        "Indicates how a IPv4 packet's protocol field is to be compared. This
         object is only available if FrameType is ipv4(5)."
    ::= { vtssAclConfigAceEntry 701 }

vtssAclConfigAceIpv4Protocol OBJECT-TYPE
    SYNTAX      VTSSUnsigned8
    MAX-ACCESS  read-write
    STATUS      current
    DESCRIPTION
        "The protocol number field in the IPv4 header used to indicate a higher
         layer protocol. Possible values are 0-255. This object is only
         available if FrameType is ipv4(5) and Ipv4ProtocolOp is specific(1)."
    ::= { vtssAclConfigAceEntry 702 }

vtssAclConfigAceIpv4SrcIp OBJECT-TYPE
    SYNTAX      IpAddress
    MAX-ACCESS  read-write
    STATUS      current
    DESCRIPTION
        "The specified source IPv4 address. The packet's sender address is
         AND-ed with the value of Ipv4SrcIpMask and then compared with the value
         of this object. If Ipv4SrcIp and Ipv4SrcIpMask are 0.0.0.0, this entry
         matches any source IP address. This object is only available if
         FrameType is ipv4(5)."
    ::= { vtssAclConfigAceEntry 703 }

vtssAclConfigAceIpv4SrcIpMask OBJECT-TYPE
    SYNTAX      IpAddress
    MAX-ACCESS  read-write
    STATUS      current
    DESCRIPTION
        "The specified source IPv4 address mask. This object is only available
         if FrameType is ipv4(5)."
    ::= { vtssAclConfigAceEntry 704 }

vtssAclConfigAceIpv4DestIp OBJECT-TYPE
    SYNTAX      IpAddress
    MAX-ACCESS  read-write
    STATUS      current
    DESCRIPTION
        "The specified destination IPv4 address. The packet's sender address is
         AND-ed with the value of Ipv4DestIpMask and then compared with the
         value of this object. If Ipv4DestIp and Ipv4DestIpMask are 0.0.0.0,
         this entry matches any destination IP address. This object is only
         available if FrameType is ipv4(5)."
    ::= { vtssAclConfigAceEntry 705 }

vtssAclConfigAceIpv4DestIpMask OBJECT-TYPE
    SYNTAX      IpAddress
    MAX-ACCESS  read-write
    STATUS      current
    DESCRIPTION
        "The specified destination IPv4 address mask. This object is only
         available if FrameType is ipv4(5)."
    ::= { vtssAclConfigAceEntry 706 }

vtssAclConfigAceIpv4IcmpTypeOp OBJECT-TYPE
    SYNTAX      VTSSASType
    MAX-ACCESS  read-write
    STATUS      current
    DESCRIPTION
        "Indicates how a IPv4 packet's ICMP type field is to be compared. This
         object is only available if FrameType is ipv4(5) and Ipv4Protocol is
         icmp(1)."
    ::= { vtssAclConfigAceEntry 707 }

vtssAclConfigAceIpv4IcmpType OBJECT-TYPE
    SYNTAX      VTSSUnsigned8
    MAX-ACCESS  read-write
    STATUS      current
    DESCRIPTION
        "The ICMP type field in the IPv4 header. Possible values are 0-255. This
         object is only available if FrameType is ipv4(5), Ipv4Protocol is
         icmp(1) and Ipv4IcmpTypeOp is specific(1)."
    ::= { vtssAclConfigAceEntry 708 }

vtssAclConfigAceIpv4IcmpCodeOp OBJECT-TYPE
    SYNTAX      VTSSASType
    MAX-ACCESS  read-write
    STATUS      current
    DESCRIPTION
        "Indicates how a IPv4 packet's ICMP code field is to be compared. This
         object is only available if FrameType is ipv4(5) and Ipv4Protocol is
         icmp(1)."
    ::= { vtssAclConfigAceEntry 709 }

vtssAclConfigAceIpv4IcmpCode OBJECT-TYPE
    SYNTAX      VTSSUnsigned8
    MAX-ACCESS  read-write
    STATUS      current
    DESCRIPTION
        "The ICMP code field in the IPv4 header. Possible values are 0-255. This
         object is only available if FrameType is ipv4(5), Ipv4Protocol is
         icmp(1) and Ipv4IcmpCodeOp is specific(1)."
    ::= { vtssAclConfigAceEntry 710 }

vtssAclConfigAceIpv4SrcPortOp OBJECT-TYPE
    SYNTAX      VTSSASRType
    MAX-ACCESS  read-write
    STATUS      current
    DESCRIPTION
        "Indicates how a packet's source TCP/UDP port number is to be compared.
         This object is only available if FrameType is ipv4(5)."
    ::= { vtssAclConfigAceEntry 711 }

vtssAclConfigAceIpv4SrcPort OBJECT-TYPE
    SYNTAX      VTSSUnsigned16
    MAX-ACCESS  read-write
    STATUS      current
    DESCRIPTION
        "The source port number of the TCP or UDP protocol. If the Ipv4SrcPortOp
         object is range(2), this object will be the starting port number of the
         port range. Valid range is 0-65535. This object is only available if
         FrameType is ipv4(5) and Ipv4SrcPortOp is not any(0)."
    ::= { vtssAclConfigAceEntry 712 }

vtssAclConfigAceIpv4SrcPortRange OBJECT-TYPE
    SYNTAX      VTSSUnsigned16
    MAX-ACCESS  read-write
    STATUS      current
    DESCRIPTION
        "The source port number of the TCP or UDP protocol. If the Ipv4SrcPortOp
         object is range(2), this object will be the ending port number of the
         port range. Valid range is 0-65535. This object is only available if
         FrameType is ipv4(5) and Ipv4SrcPortOp is range(2)."
    ::= { vtssAclConfigAceEntry 713 }

vtssAclConfigAceIpv4DestPortOp OBJECT-TYPE
    SYNTAX      VTSSASRType
    MAX-ACCESS  read-write
    STATUS      current
    DESCRIPTION
        "Indicates how a packet's destination TCP/UDP port number is to be
         compared. This object is only available if FrameType is ipv4(5)."
    ::= { vtssAclConfigAceEntry 714 }

vtssAclConfigAceIpv4DestPort OBJECT-TYPE
    SYNTAX      VTSSUnsigned16
    MAX-ACCESS  read-write
    STATUS      current
    DESCRIPTION
        "The destination port number of the TCP or UDP protocol. If the
         Ipv4DestPortOp object in the same row is range(2), this object will be
         the starting port number of the port range. Valid range is 0-65535.
         This object is only available if FrameType is ipv4(5) and
         Ipv4DestPortOp is not any(0)."
    ::= { vtssAclConfigAceEntry 715 }

vtssAclConfigAceIpv4DestPortRange OBJECT-TYPE
    SYNTAX      VTSSUnsigned16
    MAX-ACCESS  read-write
    STATUS      current
    DESCRIPTION
        "The destination port number of the TCP or UDP protocol. If the
         Ipv4DestPortOp object in the same row is range(2), this object will be
         the ending port number of the port range. Valid range is 0-65535. This
         object is only available if FrameType is ipv4(5) and Ipv4DestPortOp is
         range(2)."
    ::= { vtssAclConfigAceEntry 716 }

vtssAclConfigAceIpv4FlagTtl OBJECT-TYPE
    SYNTAX      VTSSBitType
    MAX-ACCESS  read-write
    STATUS      current
    DESCRIPTION
        "Indicates how a IPv4 packet's Time-to-Live field (TTL) is to be
         compared. The value 0 means any TTL value is allowed (don't-care
         field), value 1 means TTL is not equal zero and value 2 means TTL is
         equal to zero. This object is only available if FrameType is ipv4(5)."
    ::= { vtssAclConfigAceEntry 717 }

vtssAclConfigAceIpv4FlagFragment OBJECT-TYPE
    SYNTAX      VTSSBitType
    MAX-ACCESS  read-write
    STATUS      current
    DESCRIPTION
        "Indicates how a IPv4 packet's More-Fragments field (MF) is to be
         compared. The value 0 means any MF value is allowed (don't-care field),
         value 1 means MF is not equal one (MF field isn't set) and value 2
         means MF is equal to one (MF field is set). This object is only
         available if FrameType is ipv4(5)."
    ::= { vtssAclConfigAceEntry 718 }

vtssAclConfigAceIpv4FlagIpOption OBJECT-TYPE
    SYNTAX      VTSSBitType
    MAX-ACCESS  read-write
    STATUS      current
    DESCRIPTION
        "Indicates how a IPv4 packet's options field is to be compared. This
         object is only available if FrameType is ipv4(5)."
    ::= { vtssAclConfigAceEntry 719 }

vtssAclConfigAceIpv4TcpFlagFin OBJECT-TYPE
    SYNTAX      VTSSBitType
    MAX-ACCESS  read-write
    STATUS      current
    DESCRIPTION
        "Indicates how the IPv4 TCP FIN flag is matched. This object is only
         available if FrameType is ipv4(5) and Ipv4Protocol is tcp(6)."
    ::= { vtssAclConfigAceEntry 720 }

vtssAclConfigAceIpv4TcpFlagSyn OBJECT-TYPE
    SYNTAX      VTSSBitType
    MAX-ACCESS  read-write
    STATUS      current
    DESCRIPTION
        "Indicates how the IPv4 TCP SYN flag is matched. This object is only
         available if FrameType is ipv4(5) and Ipv4Protocol is tcp(6)."
    ::= { vtssAclConfigAceEntry 721 }

vtssAclConfigAceIpv4TcpFlagRst OBJECT-TYPE
    SYNTAX      VTSSBitType
    MAX-ACCESS  read-write
    STATUS      current
    DESCRIPTION
        "Indicates how the IPv4 TCP RST flag is matched. This object is only
         available if FrameType is ipv4(5) and Ipv4Protocol is tcp(6)."
    ::= { vtssAclConfigAceEntry 722 }

vtssAclConfigAceIpv4TcpFlagPsh OBJECT-TYPE
    SYNTAX      VTSSBitType
    MAX-ACCESS  read-write
    STATUS      current
    DESCRIPTION
        "Indicates how the IPv4 TCP PSH flag is matched. This object is only
         available if FrameType is ipv4(5) and Ipv4Protocol is tcp(6)."
    ::= { vtssAclConfigAceEntry 723 }

vtssAclConfigAceIpv4TcpFlagAck OBJECT-TYPE
    SYNTAX      VTSSBitType
    MAX-ACCESS  read-write
    STATUS      current
    DESCRIPTION
        "Indicates how the IPv4 TCP ACK flag is matched. This object is only
         available if FrameType is ipv4(5) and Ipv4Protocol is tcp(6)."
    ::= { vtssAclConfigAceEntry 724 }

vtssAclConfigAceIpv4TcpFlagUrg OBJECT-TYPE
    SYNTAX      VTSSBitType
    MAX-ACCESS  read-write
    STATUS      current
    DESCRIPTION
        "Indicates how the IPv4 TCP URG flag is matched. This object is only
         available if FrameType is ipv4(5) and Ipv4Protocol is tcp(6)."
    ::= { vtssAclConfigAceEntry 725 }

vtssAclConfigAceIpv6NextHeaderOp OBJECT-TYPE
    SYNTAX      VTSSASType
    MAX-ACCESS  read-write
    STATUS      current
    DESCRIPTION
        "Specify the IPv6 next header filter for this ACE. This object is only
         available if FrameType is ipv6(6)."
    ::= { vtssAclConfigAceEntry 801 }

vtssAclConfigAceIpv6NextHeader OBJECT-TYPE
    SYNTAX      VTSSUnsigned8
    MAX-ACCESS  read-write
    STATUS      current
    DESCRIPTION
        "When 'Specific' is selected for the IPv6 next header value, you can
         enter a specific value. The allowed range is 0 to 255. A frame that
         hits this ACE matches this IPv6 protocol value. This object is only
         available if FrameType is ipv6(6) and Ipv6NextHeaderOp is specific(1)."
    ::= { vtssAclConfigAceEntry 802 }

vtssAclConfigAceIpv6Icmpv6TypeOp OBJECT-TYPE
    SYNTAX      VTSSASType
    MAX-ACCESS  read-write
    STATUS      current
    DESCRIPTION
        "Indicates how a IPv6 packet's ICMPv6 type field is to be compared. This
         object is only available if FrameType is ipv6(6) and Ipv6NextHeader is
         icmpv6(58)."
    ::= { vtssAclConfigAceEntry 803 }

vtssAclConfigAceIpv6Icmpv6Type OBJECT-TYPE
    SYNTAX      VTSSUnsigned8
    MAX-ACCESS  read-write
    STATUS      current
    DESCRIPTION
        "The ICMPv6 type field in the IPv6 header. Possible values are 0-255.
         This object is only available if FrameType is ipv6(6), Ipv6NextHeader
         is icmpv6(58) and Ipv6Icmpv6TypeOp is specific(1)."
    ::= { vtssAclConfigAceEntry 804 }

vtssAclConfigAceIpv6Icmpv6CodeOp OBJECT-TYPE
    SYNTAX      VTSSASType
    MAX-ACCESS  read-write
    STATUS      current
    DESCRIPTION
        "Indicates how a IPv6 packet's ICMPv6 code field is to be compared. This
         object is only available if FrameType is ipv6(6) and Ipv6NextHeader is
         icmpv6(58)."
    ::= { vtssAclConfigAceEntry 805 }

vtssAclConfigAceIpv6Icmpv6Code OBJECT-TYPE
    SYNTAX      VTSSUnsigned8
    MAX-ACCESS  read-write
    STATUS      current
    DESCRIPTION
        "The ICMP code field in the IPv6 header. Possible values are 0-255. This
         object is only available if FrameType is ipv6(6), Ipv6NextHeader is
         icmpv6(58) and Ipv6Icmpv6CodeOp is specific(1)."
    ::= { vtssAclConfigAceEntry 806 }

vtssAclConfigAceIpv6SrcIp OBJECT-TYPE
    SYNTAX      InetAddressIPv6
    MAX-ACCESS  read-write
    STATUS      current
    DESCRIPTION
        "The specified source IPv6 address. The packet's sender address is
         AND-ed with the value of Ipv6SrcIpMask and then compared with the value
         of this object. If Ipv6SrcIp and Ipv4SrcIpMask are 0::, this entry
         matches any source IP address. This object is only available if
         FrameType is ipv6(6)."
    ::= { vtssAclConfigAceEntry 807 }

vtssAclConfigAceIpv6SrcIpMask OBJECT-TYPE
    SYNTAX      InetAddressIPv6
    MAX-ACCESS  read-write
    STATUS      current
    DESCRIPTION
        "The specified source IPv6 address mask. This object is only available
         if FrameType is ipv6(6)."
    ::= { vtssAclConfigAceEntry 808 }

vtssAclConfigAceIpv6SrcPortOp OBJECT-TYPE
    SYNTAX      VTSSASRType
    MAX-ACCESS  read-write
    STATUS      current
    DESCRIPTION
        "Indicates how a packet's source TCP/UDP port number is to be compared.
         This object is only available if FrameType is ipv6(6)."
    ::= { vtssAclConfigAceEntry 809 }

vtssAclConfigAceIpv6SrcPort OBJECT-TYPE
    SYNTAX      VTSSUnsigned16
    MAX-ACCESS  read-write
    STATUS      current
    DESCRIPTION
        "The source port number of the TCP or UDP protocol. If the Ipv6SrcPortOp
         object in the same row is range(2), this object will be the starting
         port number of the port range. Valid range is 0-65535. This object is
         only available if FrameType is ipv6(6) and Ipv6SrcPortOp is not any(0)."
    ::= { vtssAclConfigAceEntry 810 }

vtssAclConfigAceIpv6SrcPortRange OBJECT-TYPE
    SYNTAX      VTSSUnsigned16
    MAX-ACCESS  read-write
    STATUS      current
    DESCRIPTION
        "The source port number of the TCP or UDP protocol. If the Ipv6SrcPortOp
         object in the same row is range(2), this object will be the ending port
         number of the port range. Valid range is 0-65535. This object is only
         available if FrameType is ipv6(6) and Ipv6SrcPortOp is range(2)."
    ::= { vtssAclConfigAceEntry 811 }

vtssAclConfigAceIpv6DestPortOp OBJECT-TYPE
    SYNTAX      VTSSASRType
    MAX-ACCESS  read-write
    STATUS      current
    DESCRIPTION
        "Indicates how a packet's destination TCP/UDP port number is to be
         compared. This object is only available if FrameType is ipv6(6)."
    ::= { vtssAclConfigAceEntry 812 }

vtssAclConfigAceIpv6DestPort OBJECT-TYPE
    SYNTAX      VTSSUnsigned16
    MAX-ACCESS  read-write
    STATUS      current
    DESCRIPTION
        "The destination port number of the TCP or UDP protocol. If the
         Ipv6DestPortOp object in the same row is range(2), this object will be
         the starting port number of the port range. Valid range is 0-65535.
         This object is only available if FrameType is ipv6(6) and
         Ipv6DestPortOp is not any(0)."
    ::= { vtssAclConfigAceEntry 813 }

vtssAclConfigAceIpv6DestPortRange OBJECT-TYPE
    SYNTAX      VTSSUnsigned16
    MAX-ACCESS  read-write
    STATUS      current
    DESCRIPTION
        "The destination port number of the TCP or UDP protocol. If the
         Ipv6DestPortOp object in the same row is range(2), this object will be
         the ending port number of the port range. Valid range is 0-65535. This
         object is only available if FrameType is ipv6(6) and Ipv6DestPortOp is
         range(2)."
    ::= { vtssAclConfigAceEntry 814 }

vtssAclConfigAceIpv6FlagTtl OBJECT-TYPE
    SYNTAX      VTSSBitType
    MAX-ACCESS  read-write
    STATUS      current
    DESCRIPTION
        "Indicates how a IPv6 packet's Time-to-Live field (TTL) is to be
         compared. The value 0 means any TTL value is allowed (don't-care
         field), value 1 means TTL is not equal zero and value 2 means TTL is
         equal to zero. This object is only available if FrameType is ipv6(6)."
    ::= { vtssAclConfigAceEntry 815 }

vtssAclConfigAceIpv6TcpFlagFin OBJECT-TYPE
    SYNTAX      VTSSBitType
    MAX-ACCESS  read-write
    STATUS      current
    DESCRIPTION
        "Indicates how a IPv6 TCP packet's 'No more data from sender' field
         (FIN) is to be compared. The value 0 means any FIN value is allowed
         (don't-care field), value 1 means FIN is not equal one (FIN field isn't
         set) and value 2 means FIN is equal to one (FIN field is set). This
         object is only available if FrameType is ipv6(6) and Ipv6NextHeader is
         tcp(6)."
    ::= { vtssAclConfigAceEntry 816 }

vtssAclConfigAceIpv6TcpFlagSyn OBJECT-TYPE
    SYNTAX      VTSSBitType
    MAX-ACCESS  read-write
    STATUS      current
    DESCRIPTION
        "Indicates how a IPv6 TCP packet's 'Synchronize sequence numbers' field
         (SYN) is to be compared. The value 0 means any SYN value is allowed
         (don't-care field), value 1 means SYN is not equal one (FIN field isn't
         set) and value 2 means SYN is equal to one (FIN field is set). This
         object is only available if FrameType is ipv6(6) and Ipv6NextHeader is
         tcp(6)."
    ::= { vtssAclConfigAceEntry 817 }

vtssAclConfigAceIpv6TcpFlagRst OBJECT-TYPE
    SYNTAX      VTSSBitType
    MAX-ACCESS  read-write
    STATUS      current
    DESCRIPTION
        "Indicates how a IPv6 TCP packet's 'Reset the connection' field (RST) is
         to be compared. The value 0 means any RST value is allowed (don't-care
         field), value 1 means RST is not equal one (FIN field isn't set) and
         value 2 means RST is equal to one (FIN field is set). This object is
         only available if FrameType is ipv6(6) and Ipv6NextHeader is tcp(6)."
    ::= { vtssAclConfigAceEntry 818 }

vtssAclConfigAceIpv6TcpFlagPsh OBJECT-TYPE
    SYNTAX      VTSSBitType
    MAX-ACCESS  read-write
    STATUS      current
    DESCRIPTION
        "Indicates how a IPv6 TCP packet's 'Push Function' field (PSH) is to be
         compared. The value 0 means any PSH value is allowed (don't-care
         field), value 1 means PSH is not equal one (FIN field isn't set) and
         value 2 means PSH is equal to one (FIN field is set). This object is
         only available if FrameType is ipv6(6) and Ipv6NextHeader is tcp(6)."
    ::= { vtssAclConfigAceEntry 819 }

vtssAclConfigAceIpv6TcpFlagAck OBJECT-TYPE
    SYNTAX      VTSSBitType
    MAX-ACCESS  read-write
    STATUS      current
    DESCRIPTION
        "Indicates how a IPv6 TCP packet's 'Acknowledgment field significant'
         field (ACK) is to be compared. The value 0 means any FIN value is
         allowed (don't-care field), value 1 means ACK is not equal one (FIN
         field isn't set) and value 2 means ACK is equal to one (FIN field is
         set). This object is only available if FrameType is ipv6(6) and
         Ipv6NextHeader is tcp(6)."
    ::= { vtssAclConfigAceEntry 820 }

vtssAclConfigAceIpv6TcpFlagUrg OBJECT-TYPE
    SYNTAX      VTSSBitType
    MAX-ACCESS  read-write
    STATUS      current
    DESCRIPTION
        "Indicates how a IPv6 TCP packet's 'Urgent Pointer field significant'
         field (URG) is to be compared. The value 0 means any URG value is
         allowed (don't-care field), value 1 means URG is not equal one (FIN
         field isn't set) and value 2 means URG is equal to one (FIN field is
         set). This object is only available if FrameType is ipv6(6) and
         Ipv6NextHeader is tcp(6)."
    ::= { vtssAclConfigAceEntry 821 }

vtssAclConfigAceAction OBJECT-TYPE
    SYNTAX      VTSSRowEditorState
    MAX-ACCESS  read-write
    STATUS      current
    DESCRIPTION
        "Action"
    ::= { vtssAclConfigAceEntry 10000 }

vtssAclConfigAceRowEditor OBJECT IDENTIFIER
    ::= { vtssAclConfigAce 2 }

vtssAclConfigAceRowEditorAceId OBJECT-TYPE
    SYNTAX      Integer32 (0..2147483647)
    MAX-ACCESS  read-write
    STATUS      current
    DESCRIPTION
        "The ACE ID."
    ::= { vtssAclConfigAceRowEditor 1 }

vtssAclConfigAceRowEditorNextAceId OBJECT-TYPE
    SYNTAX      Unsigned32
    MAX-ACCESS  read-write
    STATUS      current
    DESCRIPTION
        "The ID of ACE next to this ACE."
    ::= { vtssAclConfigAceRowEditor 2 }

vtssAclConfigAceRowEditorHitAction OBJECT-TYPE
    SYNTAX      VTSSAclHitAction
    MAX-ACCESS  read-write
    STATUS      current
    DESCRIPTION
        "The hit action operation for this ACE."
    ::= { vtssAclConfigAceRowEditor 101 }

vtssAclConfigAceRowEditorRedirectPortList OBJECT-TYPE
    SYNTAX      VTSSPortList
    MAX-ACCESS  read-write
    STATUS      current
    DESCRIPTION
        "The redirect port list for this ACE."
    ::= { vtssAclConfigAceRowEditor 102 }

vtssAclConfigAceRowEditorRedirectPortListSwitchPort OBJECT-TYPE
    SYNTAX      Unsigned32
    MAX-ACCESS  read-write
    STATUS      current
    DESCRIPTION
        "The redirect switch port for this ACE. The object is only abaliable if
         AclAceIngressPortListMode is switchport. And it is used when this ACE
         is applied on specific switch port of all switches in stackable
         devices.
         
         This object is only available if the capability object
         'vtssAclCapabilitiesStackableAceSupported' is True."
    ::= { vtssAclConfigAceRowEditor 103 }

vtssAclConfigAceRowEditorEgressPortList OBJECT-TYPE
    SYNTAX      VTSSPortList
    MAX-ACCESS  read-write
    STATUS      current
    DESCRIPTION
        "The egress port list. The port list is to define what ports are allowed
         to be egress ports. If the egress port of an incoming frame is in the
         port list then the frame will be forwared to that port. Otherwise, if
         the egress port is not in the port list then the egress port is not
         allowed and the incoming frame will be dropped.
         
         This object is only available if the capability object
         'vtssAclCapabilitiesEgressPortSupported' is True."
    ::= { vtssAclConfigAceRowEditor 104 }

vtssAclConfigAceRowEditorRateLimiterId OBJECT-TYPE
    SYNTAX      Unsigned32
    MAX-ACCESS  read-write
    STATUS      current
    DESCRIPTION
        "The rate limiter ID. 0 means to be disabled."
    ::= { vtssAclConfigAceRowEditor 105 }

vtssAclConfigAceRowEditorEvcPolicerId OBJECT-TYPE
    SYNTAX      VTSSUnsigned16
    MAX-ACCESS  read-write
    STATUS      obsolete
    DESCRIPTION
        "The EVC policer ID. 0 means to be disabled. Obsolete.
         
         This object is only available if the capability object
         'vtssAclCapabilitiesEvcPolicerSupported' is True."
    ::= { vtssAclConfigAceRowEditor 106 }

vtssAclConfigAceRowEditorMirror OBJECT-TYPE
    SYNTAX      TruthValue
    MAX-ACCESS  read-write
    STATUS      current
    DESCRIPTION
        "The mirror operation. Frames matching this ACE are mirrored to the
         destination mirror port that is configured in the mirror module.
         
         This object is only available if the capability object
         'vtssAclCapabilitiesMirrorSupported' is True."
    ::= { vtssAclConfigAceRowEditor 107 }

vtssAclConfigAceRowEditorLogging OBJECT-TYPE
    SYNTAX      TruthValue
    MAX-ACCESS  read-write
    STATUS      current
    DESCRIPTION
        "Specify the logging operation of the ACE. Notice that the logging
         message doesn't include the 4 bytes CRC information. The allowed values
         are: True - Frames matching the ACE are stored in the System Log. False
         - Frames matching the ACE are not logged. Note: The logging feature
         only works when the packet length is less than 1518(without VLAN tags)
         and the system log memory size and logging rate is limited."
    ::= { vtssAclConfigAceRowEditor 108 }

vtssAclConfigAceRowEditorShutdown OBJECT-TYPE
    SYNTAX      TruthValue
    MAX-ACCESS  read-write
    STATUS      current
    DESCRIPTION
        "Specify the port shut down operation of the ACE. The allowed values
         are: True: If a frame matches the ACE, the ingress port will be shuted
         down. False: Port shut down is disabled for the ACE. Note: The shutdown
         feature only works when the packet length is less than 1518(without
         VLAN tags)."
    ::= { vtssAclConfigAceRowEditor 109 }

vtssAclConfigAceRowEditorIngressPortListMode OBJECT-TYPE
    SYNTAX      VTSSAclAceIngressPortListMode
    MAX-ACCESS  read-write
    STATUS      current
    DESCRIPTION
        "The ingress port list mode for this ACE. The possible mode are: 'any':
         Indicates this ACE is applied on all switches and all ports.
         'specific': Indicates this ACE is applied on specific switch and
         specific ports. 'switch': Indicates this ACE is applied on all ports of
         specific switch in stackable devices. 'switchport': Indicates this ACE
         is applied on specific switch port of all switches in stackable
         devices."
    ::= { vtssAclConfigAceRowEditor 201 }

vtssAclConfigAceRowEditorIngressPortList OBJECT-TYPE
    SYNTAX      VTSSPortList
    MAX-ACCESS  read-write
    STATUS      current
    DESCRIPTION
        "The ingress port list for this ACE. The object is only abaliable if
         AclAceIngressPortListMode is specific. And it is used when this ACE is
         applied on specific switch and specific ports."
    ::= { vtssAclConfigAceRowEditor 202 }

vtssAclConfigAceRowEditorIngressPortListSwitch OBJECT-TYPE
    SYNTAX      Unsigned32
    MAX-ACCESS  read-write
    STATUS      current
    DESCRIPTION
        "The ingress switch ID for this ACE. The object is only abaliable if
         AclAceIngressPortListMode is switch. And it is used when this ACE is
         applied on specific switch port of all switches in stackable devices.
         
         This object is only available if the capability object
         'vtssAclCapabilitiesStackableAceSupported' is True."
    ::= { vtssAclConfigAceRowEditor 203 }

vtssAclConfigAceRowEditorIngressPortListSwitchPort OBJECT-TYPE
    SYNTAX      Unsigned32
    MAX-ACCESS  read-write
    STATUS      current
    DESCRIPTION
        "The ingress switch port for this ACE. The object is only abaliable if
         AclAceIngressPortListMode is switchport. And it is used when this ACE
         is applied on specific switch port of all switches in stackable
         devices.
         
         This object is only available if the capability object
         'vtssAclCapabilitiesStackableAceSupported' is True."
    ::= { vtssAclConfigAceRowEditor 204 }

vtssAclConfigAceRowEditorPolicyValue OBJECT-TYPE
    SYNTAX      VTSSUnsigned8
    MAX-ACCESS  read-write
    STATUS      current
    DESCRIPTION
        "The policy number for this ACE."
    ::= { vtssAclConfigAceRowEditor 205 }

vtssAclConfigAceRowEditorPolicyMask OBJECT-TYPE
    SYNTAX      VTSSUnsigned8
    MAX-ACCESS  read-write
    STATUS      current
    DESCRIPTION
        "The policy mask for this ACE. The allowed range is 0x0 to 0xff. If the
         binary bit value is '0', it means this bit is don't-care. The real
         matched pattern is [policy_value & policy_bitmask]. For example, if the
         policy value is 3 and the policy bitmask is 0x10(bit 0 is don't-care
         bit), then policy 2 and 3 are applied to this rule."
    ::= { vtssAclConfigAceRowEditor 206 }

vtssAclConfigAceRowEditorSecondLookup OBJECT-TYPE
    SYNTAX      TruthValue
    MAX-ACCESS  read-write
    STATUS      current
    DESCRIPTION
        "The second lookup operation for this ACE.
         
         This object is only available if the capability object
         'vtssAclCapabilitiesSecondLookupSupported' is True."
    ::= { vtssAclConfigAceRowEditor 207 }

vtssAclConfigAceRowEditorVlanId OBJECT-TYPE
    SYNTAX      VTSSUnsigned16
    MAX-ACCESS  read-write
    STATUS      current
    DESCRIPTION
        "The VLAN ID for this ACE. Possible values are: 0(disabled), 1-4095."
    ::= { vtssAclConfigAceRowEditor 301 }

vtssAclConfigAceRowEditorVlanTagPriority OBJECT-TYPE
    SYNTAX      VTSSVlanTagPriority
    MAX-ACCESS  read-write
    STATUS      current
    DESCRIPTION
        "The VLAN tag priority for this ACE."
    ::= { vtssAclConfigAceRowEditor 302 }

vtssAclConfigAceRowEditorVlanTagged OBJECT-TYPE
    SYNTAX      VTSSAclAceVlanTagged
    MAX-ACCESS  read-write
    STATUS      current
    DESCRIPTION
        "The 802.1Q VLAN tagged for this ACE.
         
         This object is only available if the capability object
         'vtssAclCapabilitiesVlanTaggedSupported' is True."
    ::= { vtssAclConfigAceRowEditor 303 }

vtssAclConfigAceRowEditorFrameType OBJECT-TYPE
    SYNTAX      VTSSAclAceFrameType
    MAX-ACCESS  read-write
    STATUS      current
    DESCRIPTION
        "The frame type for this ACE."
    ::= { vtssAclConfigAceRowEditor 401 }

vtssAclConfigAceRowEditorDestMacOp OBJECT-TYPE
    SYNTAX      VTSSAdvDestMacType
    MAX-ACCESS  read-write
    STATUS      current
    DESCRIPTION
        "Indicates how a packet's destination MAC address to be matched."
    ::= { vtssAclConfigAceRowEditor 402 }

vtssAclConfigAceRowEditorEtherSrcMacOp OBJECT-TYPE
    SYNTAX      VTSSASType
    MAX-ACCESS  read-write
    STATUS      current
    DESCRIPTION
        "Indicates how a Ethernet type packet's source MAC address to be
         matched. This object is only available if FrameType is ether(1)."
    ::= { vtssAclConfigAceRowEditor 501 }

vtssAclConfigAceRowEditorEtherSrcMac OBJECT-TYPE
    SYNTAX      MacAddress
    MAX-ACCESS  read-write
    STATUS      current
    DESCRIPTION
        "Indicates the 48 bits source MAC address. This object is only available
         if FrameType is ether(1) and EtherSrcMacOp is specific(1)."
    ::= { vtssAclConfigAceRowEditor 502 }

vtssAclConfigAceRowEditorEtherDestMac OBJECT-TYPE
    SYNTAX      MacAddress
    MAX-ACCESS  read-write
    STATUS      current
    DESCRIPTION
        "Indicates the 48 bits destination MAC address. This object is only
         available if FrameType is ether(1) and EtherDestMacOp is specific(1)."
    ::= { vtssAclConfigAceRowEditor 503 }

vtssAclConfigAceRowEditorEtherType OBJECT-TYPE
    SYNTAX      VTSSUnsigned16
    MAX-ACCESS  read-write
    STATUS      current
    DESCRIPTION
        "Indicates the packet's 16 bit Ethernet type field. Possible values are:
         0(disabled), 0x600-0xFFFF but excluding 0x800(IPv4), 0x806(ARP) and
         0x86DD(IPv6). This object is only available if FrameType is ether(1)
         and EtherDestMacOp is specific(1)."
    ::= { vtssAclConfigAceRowEditor 504 }

vtssAclConfigAceRowEditorArpSrcMacOp OBJECT-TYPE
    SYNTAX      VTSSASType
    MAX-ACCESS  read-write
    STATUS      current
    DESCRIPTION
        "Indicates how a ARP packet's source MAC address to be matched. This
         object is only available if FrameType is arp(4)."
    ::= { vtssAclConfigAceRowEditor 601 }

vtssAclConfigAceRowEditorArpSrcMac OBJECT-TYPE
    SYNTAX      MacAddress
    MAX-ACCESS  read-write
    STATUS      current
    DESCRIPTION
        "Indicates the 48 bits source MAC address. This object is only available
         if FrameType is arp(4) and ArpSrcMacOp is specific(1)."
    ::= { vtssAclConfigAceRowEditor 602 }

vtssAclConfigAceRowEditorArpSenderIp OBJECT-TYPE
    SYNTAX      IpAddress
    MAX-ACCESS  read-write
    STATUS      current
    DESCRIPTION
        "The specified ARP sender IP address. The packet's sender address is
         AND-ed with the value of ArpSenderIpMask and then compared with the
         value of this object. If ArpSenderIp and ArpSrcIpMask are 0.0.0.0, this
         entry matches any sender IP address. This object is only available if
         FrameType is arp(4)."
    ::= { vtssAclConfigAceRowEditor 603 }

vtssAclConfigAceRowEditorArpSenderIpMask OBJECT-TYPE
    SYNTAX      IpAddress
    MAX-ACCESS  read-write
    STATUS      current
    DESCRIPTION
        "The specified ARP sender IP address mask. This object is only available
         if FrameType is arp(4)."
    ::= { vtssAclConfigAceRowEditor 604 }

vtssAclConfigAceRowEditorArpTargetIp OBJECT-TYPE
    SYNTAX      IpAddress
    MAX-ACCESS  read-write
    STATUS      current
    DESCRIPTION
        "The specified ARP target IP address. The packet's target address is
         AND-ed with the value of ArpTragetIpMask and then compared with the
         value of this object. If ArpTragetIp and ArpSrcIpMask are 0.0.0.0, this
         entry matches any target IP address. This object is only available if
         FrameType is arp(4)."
    ::= { vtssAclConfigAceRowEditor 605 }

vtssAclConfigAceRowEditorArpTargetIpMask OBJECT-TYPE
    SYNTAX      IpAddress
    MAX-ACCESS  read-write
    STATUS      current
    DESCRIPTION
        "The specified ARP target IP address mask. This object is only available
         if FrameType is arp(4)."
    ::= { vtssAclConfigAceRowEditor 606 }

vtssAclConfigAceRowEditorArpOpcode OBJECT-TYPE
    SYNTAX      VTSSAclAceArpOp
    MAX-ACCESS  read-write
    STATUS      current
    DESCRIPTION
        "Indicates how a ARP packet's opcode to be matched. This object is only
         available if FrameType is arp(4)."
    ::= { vtssAclConfigAceRowEditor 607 }

vtssAclConfigAceRowEditorArpFlagReq OBJECT-TYPE
    SYNTAX      VTSSBitType
    MAX-ACCESS  read-write
    STATUS      current
    DESCRIPTION
        "Indicates how a ARP packet's request/reply opcode is to be compared.
         This object is only available if FrameType is arp(4)."
    ::= { vtssAclConfigAceRowEditor 608 }

vtssAclConfigAceRowEditorArpFlagSha OBJECT-TYPE
    SYNTAX      VTSSBitType
    MAX-ACCESS  read-write
    STATUS      current
    DESCRIPTION
        "Indicates how a ARP packet's sender hardware address field (SHA) to be
         compared. This object is only available if FrameType is arp(4)."
    ::= { vtssAclConfigAceRowEditor 609 }

vtssAclConfigAceRowEditorArpFlagTha OBJECT-TYPE
    SYNTAX      VTSSBitType
    MAX-ACCESS  read-write
    STATUS      current
    DESCRIPTION
        "Indicates how a ARP packet's target hardware address field (THA) is to
         be compared. This object is only available if FrameType is arp(4)."
    ::= { vtssAclConfigAceRowEditor 610 }

vtssAclConfigAceRowEditorArpFlagHln OBJECT-TYPE
    SYNTAX      VTSSBitType
    MAX-ACCESS  read-write
    STATUS      current
    DESCRIPTION
        "Indicates how a ARP packet's s hardware address length field (HLN) is
         to be compared. The value 0 means any HLN value is allowed (don't-care
         field), value 1 means HLN is not equal to Ethernet (0x06) or the (PLN)
         is not equal to IPv4 (0x04) and value 2 means HLN is equal to Ethernet
         (0x06) or the (PLN) is not equal to IPv4 (0x04). This object is only
         available if FrameType is arp(4)."
    ::= { vtssAclConfigAceRowEditor 611 }

vtssAclConfigAceRowEditorArpFlagHrd OBJECT-TYPE
    SYNTAX      VTSSBitType
    MAX-ACCESS  read-write
    STATUS      current
    DESCRIPTION
        "Indicates how a ARP packet's hardware address space field (HRD) is to
         be compared. The value 0 means any HRD value is allowed (don't-care
         field), value 1 means HRD is not equal to Ethernet (1) and value 2
         means HRD is equal to Ethernet (1). This object is only available if
         FrameType is arp(4)."
    ::= { vtssAclConfigAceRowEditor 612 }

vtssAclConfigAceRowEditorArpFlagPro OBJECT-TYPE
    SYNTAX      VTSSBitType
    MAX-ACCESS  read-write
    STATUS      current
    DESCRIPTION
        "Indicates how a ARP packet's protocol address space field (PRO) is to
         be compared. The value 0 means any PRO value is allowed (don't-care
         field), value 1 means PRO is not equal to IP (0x800) and value 2 means
         PRO is equal to IP (0x800). This object is only available if FrameType
         is arp(4)."
    ::= { vtssAclConfigAceRowEditor 613 }

vtssAclConfigAceRowEditorIpv4ProtocolOp OBJECT-TYPE
    SYNTAX      VTSSASType
    MAX-ACCESS  read-write
    STATUS      current
    DESCRIPTION
        "Indicates how a IPv4 packet's protocol field is to be compared. This
         object is only available if FrameType is ipv4(5)."
    ::= { vtssAclConfigAceRowEditor 701 }

vtssAclConfigAceRowEditorIpv4Protocol OBJECT-TYPE
    SYNTAX      VTSSUnsigned8
    MAX-ACCESS  read-write
    STATUS      current
    DESCRIPTION
        "The protocol number field in the IPv4 header used to indicate a higher
         layer protocol. Possible values are 0-255. This object is only
         available if FrameType is ipv4(5) and Ipv4ProtocolOp is specific(1)."
    ::= { vtssAclConfigAceRowEditor 702 }

vtssAclConfigAceRowEditorIpv4SrcIp OBJECT-TYPE
    SYNTAX      IpAddress
    MAX-ACCESS  read-write
    STATUS      current
    DESCRIPTION
        "The specified source IPv4 address. The packet's sender address is
         AND-ed with the value of Ipv4SrcIpMask and then compared with the value
         of this object. If Ipv4SrcIp and Ipv4SrcIpMask are 0.0.0.0, this entry
         matches any source IP address. This object is only available if
         FrameType is ipv4(5)."
    ::= { vtssAclConfigAceRowEditor 703 }

vtssAclConfigAceRowEditorIpv4SrcIpMask OBJECT-TYPE
    SYNTAX      IpAddress
    MAX-ACCESS  read-write
    STATUS      current
    DESCRIPTION
        "The specified source IPv4 address mask. This object is only available
         if FrameType is ipv4(5)."
    ::= { vtssAclConfigAceRowEditor 704 }

vtssAclConfigAceRowEditorIpv4DestIp OBJECT-TYPE
    SYNTAX      IpAddress
    MAX-ACCESS  read-write
    STATUS      current
    DESCRIPTION
        "The specified destination IPv4 address. The packet's sender address is
         AND-ed with the value of Ipv4DestIpMask and then compared with the
         value of this object. If Ipv4DestIp and Ipv4DestIpMask are 0.0.0.0,
         this entry matches any destination IP address. This object is only
         available if FrameType is ipv4(5)."
    ::= { vtssAclConfigAceRowEditor 705 }

vtssAclConfigAceRowEditorIpv4DestIpMask OBJECT-TYPE
    SYNTAX      IpAddress
    MAX-ACCESS  read-write
    STATUS      current
    DESCRIPTION
        "The specified destination IPv4 address mask. This object is only
         available if FrameType is ipv4(5)."
    ::= { vtssAclConfigAceRowEditor 706 }

vtssAclConfigAceRowEditorIpv4IcmpTypeOp OBJECT-TYPE
    SYNTAX      VTSSASType
    MAX-ACCESS  read-write
    STATUS      current
    DESCRIPTION
        "Indicates how a IPv4 packet's ICMP type field is to be compared. This
         object is only available if FrameType is ipv4(5) and Ipv4Protocol is
         icmp(1)."
    ::= { vtssAclConfigAceRowEditor 707 }

vtssAclConfigAceRowEditorIpv4IcmpType OBJECT-TYPE
    SYNTAX      VTSSUnsigned8
    MAX-ACCESS  read-write
    STATUS      current
    DESCRIPTION
        "The ICMP type field in the IPv4 header. Possible values are 0-255. This
         object is only available if FrameType is ipv4(5), Ipv4Protocol is
         icmp(1) and Ipv4IcmpTypeOp is specific(1)."
    ::= { vtssAclConfigAceRowEditor 708 }

vtssAclConfigAceRowEditorIpv4IcmpCodeOp OBJECT-TYPE
    SYNTAX      VTSSASType
    MAX-ACCESS  read-write
    STATUS      current
    DESCRIPTION
        "Indicates how a IPv4 packet's ICMP code field is to be compared. This
         object is only available if FrameType is ipv4(5) and Ipv4Protocol is
         icmp(1)."
    ::= { vtssAclConfigAceRowEditor 709 }

vtssAclConfigAceRowEditorIpv4IcmpCode OBJECT-TYPE
    SYNTAX      VTSSUnsigned8
    MAX-ACCESS  read-write
    STATUS      current
    DESCRIPTION
        "The ICMP code field in the IPv4 header. Possible values are 0-255. This
         object is only available if FrameType is ipv4(5), Ipv4Protocol is
         icmp(1) and Ipv4IcmpCodeOp is specific(1)."
    ::= { vtssAclConfigAceRowEditor 710 }

vtssAclConfigAceRowEditorIpv4SrcPortOp OBJECT-TYPE
    SYNTAX      VTSSASRType
    MAX-ACCESS  read-write
    STATUS      current
    DESCRIPTION
        "Indicates how a packet's source TCP/UDP port number is to be compared.
         This object is only available if FrameType is ipv4(5)."
    ::= { vtssAclConfigAceRowEditor 711 }

vtssAclConfigAceRowEditorIpv4SrcPort OBJECT-TYPE
    SYNTAX      VTSSUnsigned16
    MAX-ACCESS  read-write
    STATUS      current
    DESCRIPTION
        "The source port number of the TCP or UDP protocol. If the Ipv4SrcPortOp
         object is range(2), this object will be the starting port number of the
         port range. Valid range is 0-65535. This object is only available if
         FrameType is ipv4(5) and Ipv4SrcPortOp is not any(0)."
    ::= { vtssAclConfigAceRowEditor 712 }

vtssAclConfigAceRowEditorIpv4SrcPortRange OBJECT-TYPE
    SYNTAX      VTSSUnsigned16
    MAX-ACCESS  read-write
    STATUS      current
    DESCRIPTION
        "The source port number of the TCP or UDP protocol. If the Ipv4SrcPortOp
         object is range(2), this object will be the ending port number of the
         port range. Valid range is 0-65535. This object is only available if
         FrameType is ipv4(5) and Ipv4SrcPortOp is range(2)."
    ::= { vtssAclConfigAceRowEditor 713 }

vtssAclConfigAceRowEditorIpv4DestPortOp OBJECT-TYPE
    SYNTAX      VTSSASRType
    MAX-ACCESS  read-write
    STATUS      current
    DESCRIPTION
        "Indicates how a packet's destination TCP/UDP port number is to be
         compared. This object is only available if FrameType is ipv4(5)."
    ::= { vtssAclConfigAceRowEditor 714 }

vtssAclConfigAceRowEditorIpv4DestPort OBJECT-TYPE
    SYNTAX      VTSSUnsigned16
    MAX-ACCESS  read-write
    STATUS      current
    DESCRIPTION
        "The destination port number of the TCP or UDP protocol. If the
         Ipv4DestPortOp object in the same row is range(2), this object will be
         the starting port number of the port range. Valid range is 0-65535.
         This object is only available if FrameType is ipv4(5) and
         Ipv4DestPortOp is not any(0)."
    ::= { vtssAclConfigAceRowEditor 715 }

vtssAclConfigAceRowEditorIpv4DestPortRange OBJECT-TYPE
    SYNTAX      VTSSUnsigned16
    MAX-ACCESS  read-write
    STATUS      current
    DESCRIPTION
        "The destination port number of the TCP or UDP protocol. If the
         Ipv4DestPortOp object in the same row is range(2), this object will be
         the ending port number of the port range. Valid range is 0-65535. This
         object is only available if FrameType is ipv4(5) and Ipv4DestPortOp is
         range(2)."
    ::= { vtssAclConfigAceRowEditor 716 }

vtssAclConfigAceRowEditorIpv4FlagTtl OBJECT-TYPE
    SYNTAX      VTSSBitType
    MAX-ACCESS  read-write
    STATUS      current
    DESCRIPTION
        "Indicates how a IPv4 packet's Time-to-Live field (TTL) is to be
         compared. The value 0 means any TTL value is allowed (don't-care
         field), value 1 means TTL is not equal zero and value 2 means TTL is
         equal to zero. This object is only available if FrameType is ipv4(5)."
    ::= { vtssAclConfigAceRowEditor 717 }

vtssAclConfigAceRowEditorIpv4FlagFragment OBJECT-TYPE
    SYNTAX      VTSSBitType
    MAX-ACCESS  read-write
    STATUS      current
    DESCRIPTION
        "Indicates how a IPv4 packet's More-Fragments field (MF) is to be
         compared. The value 0 means any MF value is allowed (don't-care field),
         value 1 means MF is not equal one (MF field isn't set) and value 2
         means MF is equal to one (MF field is set). This object is only
         available if FrameType is ipv4(5)."
    ::= { vtssAclConfigAceRowEditor 718 }

vtssAclConfigAceRowEditorIpv4FlagIpOption OBJECT-TYPE
    SYNTAX      VTSSBitType
    MAX-ACCESS  read-write
    STATUS      current
    DESCRIPTION
        "Indicates how a IPv4 packet's options field is to be compared. This
         object is only available if FrameType is ipv4(5)."
    ::= { vtssAclConfigAceRowEditor 719 }

vtssAclConfigAceRowEditorIpv4TcpFlagFin OBJECT-TYPE
    SYNTAX      VTSSBitType
    MAX-ACCESS  read-write
    STATUS      current
    DESCRIPTION
        "Indicates how the IPv4 TCP FIN flag is matched. This object is only
         available if FrameType is ipv4(5) and Ipv4Protocol is tcp(6)."
    ::= { vtssAclConfigAceRowEditor 720 }

vtssAclConfigAceRowEditorIpv4TcpFlagSyn OBJECT-TYPE
    SYNTAX      VTSSBitType
    MAX-ACCESS  read-write
    STATUS      current
    DESCRIPTION
        "Indicates how the IPv4 TCP SYN flag is matched. This object is only
         available if FrameType is ipv4(5) and Ipv4Protocol is tcp(6)."
    ::= { vtssAclConfigAceRowEditor 721 }

vtssAclConfigAceRowEditorIpv4TcpFlagRst OBJECT-TYPE
    SYNTAX      VTSSBitType
    MAX-ACCESS  read-write
    STATUS      current
    DESCRIPTION
        "Indicates how the IPv4 TCP RST flag is matched. This object is only
         available if FrameType is ipv4(5) and Ipv4Protocol is tcp(6)."
    ::= { vtssAclConfigAceRowEditor 722 }

vtssAclConfigAceRowEditorIpv4TcpFlagPsh OBJECT-TYPE
    SYNTAX      VTSSBitType
    MAX-ACCESS  read-write
    STATUS      current
    DESCRIPTION
        "Indicates how the IPv4 TCP PSH flag is matched. This object is only
         available if FrameType is ipv4(5) and Ipv4Protocol is tcp(6)."
    ::= { vtssAclConfigAceRowEditor 723 }

vtssAclConfigAceRowEditorIpv4TcpFlagAck OBJECT-TYPE
    SYNTAX      VTSSBitType
    MAX-ACCESS  read-write
    STATUS      current
    DESCRIPTION
        "Indicates how the IPv4 TCP ACK flag is matched. This object is only
         available if FrameType is ipv4(5) and Ipv4Protocol is tcp(6)."
    ::= { vtssAclConfigAceRowEditor 724 }

vtssAclConfigAceRowEditorIpv4TcpFlagUrg OBJECT-TYPE
    SYNTAX      VTSSBitType
    MAX-ACCESS  read-write
    STATUS      current
    DESCRIPTION
        "Indicates how the IPv4 TCP URG flag is matched. This object is only
         available if FrameType is ipv4(5) and Ipv4Protocol is tcp(6)."
    ::= { vtssAclConfigAceRowEditor 725 }

vtssAclConfigAceRowEditorIpv6NextHeaderOp OBJECT-TYPE
    SYNTAX      VTSSASType
    MAX-ACCESS  read-write
    STATUS      current
    DESCRIPTION
        "Specify the IPv6 next header filter for this ACE. This object is only
         available if FrameType is ipv6(6)."
    ::= { vtssAclConfigAceRowEditor 801 }

vtssAclConfigAceRowEditorIpv6NextHeader OBJECT-TYPE
    SYNTAX      VTSSUnsigned8
    MAX-ACCESS  read-write
    STATUS      current
    DESCRIPTION
        "When 'Specific' is selected for the IPv6 next header value, you can
         enter a specific value. The allowed range is 0 to 255. A frame that
         hits this ACE matches this IPv6 protocol value. This object is only
         available if FrameType is ipv6(6) and Ipv6NextHeaderOp is specific(1)."
    ::= { vtssAclConfigAceRowEditor 802 }

vtssAclConfigAceRowEditorIpv6Icmpv6TypeOp OBJECT-TYPE
    SYNTAX      VTSSASType
    MAX-ACCESS  read-write
    STATUS      current
    DESCRIPTION
        "Indicates how a IPv6 packet's ICMPv6 type field is to be compared. This
         object is only available if FrameType is ipv6(6) and Ipv6NextHeader is
         icmpv6(58)."
    ::= { vtssAclConfigAceRowEditor 803 }

vtssAclConfigAceRowEditorIpv6Icmpv6Type OBJECT-TYPE
    SYNTAX      VTSSUnsigned8
    MAX-ACCESS  read-write
    STATUS      current
    DESCRIPTION
        "The ICMPv6 type field in the IPv6 header. Possible values are 0-255.
         This object is only available if FrameType is ipv6(6), Ipv6NextHeader
         is icmpv6(58) and Ipv6Icmpv6TypeOp is specific(1)."
    ::= { vtssAclConfigAceRowEditor 804 }

vtssAclConfigAceRowEditorIpv6Icmpv6CodeOp OBJECT-TYPE
    SYNTAX      VTSSASType
    MAX-ACCESS  read-write
    STATUS      current
    DESCRIPTION
        "Indicates how a IPv6 packet's ICMPv6 code field is to be compared. This
         object is only available if FrameType is ipv6(6) and Ipv6NextHeader is
         icmpv6(58)."
    ::= { vtssAclConfigAceRowEditor 805 }

vtssAclConfigAceRowEditorIpv6Icmpv6Code OBJECT-TYPE
    SYNTAX      VTSSUnsigned8
    MAX-ACCESS  read-write
    STATUS      current
    DESCRIPTION
        "The ICMP code field in the IPv6 header. Possible values are 0-255. This
         object is only available if FrameType is ipv6(6), Ipv6NextHeader is
         icmpv6(58) and Ipv6Icmpv6CodeOp is specific(1)."
    ::= { vtssAclConfigAceRowEditor 806 }

vtssAclConfigAceRowEditorIpv6SrcIp OBJECT-TYPE
    SYNTAX      InetAddressIPv6
    MAX-ACCESS  read-write
    STATUS      current
    DESCRIPTION
        "The specified source IPv6 address. The packet's sender address is
         AND-ed with the value of Ipv6SrcIpMask and then compared with the value
         of this object. If Ipv6SrcIp and Ipv4SrcIpMask are 0::, this entry
         matches any source IP address. This object is only available if
         FrameType is ipv6(6)."
    ::= { vtssAclConfigAceRowEditor 807 }

vtssAclConfigAceRowEditorIpv6SrcIpMask OBJECT-TYPE
    SYNTAX      InetAddressIPv6
    MAX-ACCESS  read-write
    STATUS      current
    DESCRIPTION
        "The specified source IPv6 address mask. This object is only available
         if FrameType is ipv6(6)."
    ::= { vtssAclConfigAceRowEditor 808 }

vtssAclConfigAceRowEditorIpv6SrcPortOp OBJECT-TYPE
    SYNTAX      VTSSASRType
    MAX-ACCESS  read-write
    STATUS      current
    DESCRIPTION
        "Indicates how a packet's source TCP/UDP port number is to be compared.
         This object is only available if FrameType is ipv6(6)."
    ::= { vtssAclConfigAceRowEditor 809 }

vtssAclConfigAceRowEditorIpv6SrcPort OBJECT-TYPE
    SYNTAX      VTSSUnsigned16
    MAX-ACCESS  read-write
    STATUS      current
    DESCRIPTION
        "The source port number of the TCP or UDP protocol. If the Ipv6SrcPortOp
         object in the same row is range(2), this object will be the starting
         port number of the port range. Valid range is 0-65535. This object is
         only available if FrameType is ipv6(6) and Ipv6SrcPortOp is not any(0)."
    ::= { vtssAclConfigAceRowEditor 810 }

vtssAclConfigAceRowEditorIpv6SrcPortRange OBJECT-TYPE
    SYNTAX      VTSSUnsigned16
    MAX-ACCESS  read-write
    STATUS      current
    DESCRIPTION
        "The source port number of the TCP or UDP protocol. If the Ipv6SrcPortOp
         object in the same row is range(2), this object will be the ending port
         number of the port range. Valid range is 0-65535. This object is only
         available if FrameType is ipv6(6) and Ipv6SrcPortOp is range(2)."
    ::= { vtssAclConfigAceRowEditor 811 }

vtssAclConfigAceRowEditorIpv6DestPortOp OBJECT-TYPE
    SYNTAX      VTSSASRType
    MAX-ACCESS  read-write
    STATUS      current
    DESCRIPTION
        "Indicates how a packet's destination TCP/UDP port number is to be
         compared. This object is only available if FrameType is ipv6(6)."
    ::= { vtssAclConfigAceRowEditor 812 }

vtssAclConfigAceRowEditorIpv6DestPort OBJECT-TYPE
    SYNTAX      VTSSUnsigned16
    MAX-ACCESS  read-write
    STATUS      current
    DESCRIPTION
        "The destination port number of the TCP or UDP protocol. If the
         Ipv6DestPortOp object in the same row is range(2), this object will be
         the starting port number of the port range. Valid range is 0-65535.
         This object is only available if FrameType is ipv6(6) and
         Ipv6DestPortOp is not any(0)."
    ::= { vtssAclConfigAceRowEditor 813 }

vtssAclConfigAceRowEditorIpv6DestPortRange OBJECT-TYPE
    SYNTAX      VTSSUnsigned16
    MAX-ACCESS  read-write
    STATUS      current
    DESCRIPTION
        "The destination port number of the TCP or UDP protocol. If the
         Ipv6DestPortOp object in the same row is range(2), this object will be
         the ending port number of the port range. Valid range is 0-65535. This
         object is only available if FrameType is ipv6(6) and Ipv6DestPortOp is
         range(2)."
    ::= { vtssAclConfigAceRowEditor 814 }

vtssAclConfigAceRowEditorIpv6FlagTtl OBJECT-TYPE
    SYNTAX      VTSSBitType
    MAX-ACCESS  read-write
    STATUS      current
    DESCRIPTION
        "Indicates how a IPv6 packet's Time-to-Live field (TTL) is to be
         compared. The value 0 means any TTL value is allowed (don't-care
         field), value 1 means TTL is not equal zero and value 2 means TTL is
         equal to zero. This object is only available if FrameType is ipv6(6)."
    ::= { vtssAclConfigAceRowEditor 815 }

vtssAclConfigAceRowEditorIpv6TcpFlagFin OBJECT-TYPE
    SYNTAX      VTSSBitType
    MAX-ACCESS  read-write
    STATUS      current
    DESCRIPTION
        "Indicates how a IPv6 TCP packet's 'No more data from sender' field
         (FIN) is to be compared. The value 0 means any FIN value is allowed
         (don't-care field), value 1 means FIN is not equal one (FIN field isn't
         set) and value 2 means FIN is equal to one (FIN field is set). This
         object is only available if FrameType is ipv6(6) and Ipv6NextHeader is
         tcp(6)."
    ::= { vtssAclConfigAceRowEditor 816 }

vtssAclConfigAceRowEditorIpv6TcpFlagSyn OBJECT-TYPE
    SYNTAX      VTSSBitType
    MAX-ACCESS  read-write
    STATUS      current
    DESCRIPTION
        "Indicates how a IPv6 TCP packet's 'Synchronize sequence numbers' field
         (SYN) is to be compared. The value 0 means any SYN value is allowed
         (don't-care field), value 1 means SYN is not equal one (FIN field isn't
         set) and value 2 means SYN is equal to one (FIN field is set). This
         object is only available if FrameType is ipv6(6) and Ipv6NextHeader is
         tcp(6)."
    ::= { vtssAclConfigAceRowEditor 817 }

vtssAclConfigAceRowEditorIpv6TcpFlagRst OBJECT-TYPE
    SYNTAX      VTSSBitType
    MAX-ACCESS  read-write
    STATUS      current
    DESCRIPTION
        "Indicates how a IPv6 TCP packet's 'Reset the connection' field (RST) is
         to be compared. The value 0 means any RST value is allowed (don't-care
         field), value 1 means RST is not equal one (FIN field isn't set) and
         value 2 means RST is equal to one (FIN field is set). This object is
         only available if FrameType is ipv6(6) and Ipv6NextHeader is tcp(6)."
    ::= { vtssAclConfigAceRowEditor 818 }

vtssAclConfigAceRowEditorIpv6TcpFlagPsh OBJECT-TYPE
    SYNTAX      VTSSBitType
    MAX-ACCESS  read-write
    STATUS      current
    DESCRIPTION
        "Indicates how a IPv6 TCP packet's 'Push Function' field (PSH) is to be
         compared. The value 0 means any PSH value is allowed (don't-care
         field), value 1 means PSH is not equal one (FIN field isn't set) and
         value 2 means PSH is equal to one (FIN field is set). This object is
         only available if FrameType is ipv6(6) and Ipv6NextHeader is tcp(6)."
    ::= { vtssAclConfigAceRowEditor 819 }

vtssAclConfigAceRowEditorIpv6TcpFlagAck OBJECT-TYPE
    SYNTAX      VTSSBitType
    MAX-ACCESS  read-write
    STATUS      current
    DESCRIPTION
        "Indicates how a IPv6 TCP packet's 'Acknowledgment field significant'
         field (ACK) is to be compared. The value 0 means any FIN value is
         allowed (don't-care field), value 1 means ACK is not equal one (FIN
         field isn't set) and value 2 means ACK is equal to one (FIN field is
         set). This object is only available if FrameType is ipv6(6) and
         Ipv6NextHeader is tcp(6)."
    ::= { vtssAclConfigAceRowEditor 820 }

vtssAclConfigAceRowEditorIpv6TcpFlagUrg OBJECT-TYPE
    SYNTAX      VTSSBitType
    MAX-ACCESS  read-write
    STATUS      current
    DESCRIPTION
        "Indicates how a IPv6 TCP packet's 'Urgent Pointer field significant'
         field (URG) is to be compared. The value 0 means any URG value is
         allowed (don't-care field), value 1 means URG is not equal one (FIN
         field isn't set) and value 2 means URG is equal to one (FIN field is
         set). This object is only available if FrameType is ipv6(6) and
         Ipv6NextHeader is tcp(6)."
    ::= { vtssAclConfigAceRowEditor 821 }

vtssAclConfigAceRowEditorAction OBJECT-TYPE
    SYNTAX      VTSSRowEditorState
    MAX-ACCESS  read-write
    STATUS      current
    DESCRIPTION
        "Action"
    ::= { vtssAclConfigAceRowEditor 10000 }

vtssAclConfigAcePrecedenceTable OBJECT-TYPE
    SYNTAX      SEQUENCE OF VTSSAclConfigAcePrecedenceEntry
    MAX-ACCESS  not-accessible
    STATUS      current
    DESCRIPTION
        "It displays the sequence of ACEs to be hit."
    ::= { vtssAclConfigAce 3 }

vtssAclConfigAcePrecedenceEntry OBJECT-TYPE
    SYNTAX      VTSSAclConfigAcePrecedenceEntry
    MAX-ACCESS  not-accessible
    STATUS      current
    DESCRIPTION
        "Each row contains the corresponding ACE ID."
    INDEX       { vtssAclConfigAcePrecedencePrecedence }
    ::= { vtssAclConfigAcePrecedenceTable 1 }

VTSSAclConfigAcePrecedenceEntry ::= SEQUENCE {
    vtssAclConfigAcePrecedencePrecedence  Integer32,
    vtssAclConfigAcePrecedenceAceId       Unsigned32
}

vtssAclConfigAcePrecedencePrecedence OBJECT-TYPE
    SYNTAX      Integer32 (0..2147483647)
    MAX-ACCESS  accessible-for-notify
    STATUS      current
    DESCRIPTION
        "The ACL ACE hit precedence."
    ::= { vtssAclConfigAcePrecedenceEntry 1 }

vtssAclConfigAcePrecedenceAceId OBJECT-TYPE
    SYNTAX      Unsigned32
    MAX-ACCESS  read-only
    STATUS      current
    DESCRIPTION
        "Identifier of ACE"
    ::= { vtssAclConfigAcePrecedenceEntry 2 }

vtssAclStatus OBJECT IDENTIFIER
    ::= { vtssAclMibObjects 3 }

vtssAclStatusInterface OBJECT IDENTIFIER
    ::= { vtssAclStatus 2 }

vtssAclStatusInterfaceHitCountTable OBJECT-TYPE
    SYNTAX      SEQUENCE OF VTSSAclStatusInterfaceHitCountEntry
    MAX-ACCESS  not-accessible
    STATUS      current
    DESCRIPTION
        "Table of interface hit count status."
    ::= { vtssAclStatusInterface 1 }

vtssAclStatusInterfaceHitCountEntry OBJECT-TYPE
    SYNTAX      VTSSAclStatusInterfaceHitCountEntry
    MAX-ACCESS  not-accessible
    STATUS      current
    DESCRIPTION
        "Each row contains the hit count status per interface."
    INDEX       { vtssAclStatusInterfaceHitCountIfIndex }
    ::= { vtssAclStatusInterfaceHitCountTable 1 }

VTSSAclStatusInterfaceHitCountEntry ::= SEQUENCE {
    vtssAclStatusInterfaceHitCountIfIndex  VTSSInterfaceIndex,
    vtssAclStatusInterfaceHitCountCounter  Unsigned32
}

vtssAclStatusInterfaceHitCountIfIndex OBJECT-TYPE
    SYNTAX      VTSSInterfaceIndex
    MAX-ACCESS  accessible-for-notify
    STATUS      current
    DESCRIPTION
        "The index of logical interface."
    ::= { vtssAclStatusInterfaceHitCountEntry 1 }

vtssAclStatusInterfaceHitCountCounter OBJECT-TYPE
    SYNTAX      Unsigned32
    MAX-ACCESS  read-only
    STATUS      current
    DESCRIPTION
        "The hit count of this interface."
    ::= { vtssAclStatusInterfaceHitCountEntry 2 }

vtssAclStatusAce OBJECT IDENTIFIER
    ::= { vtssAclStatus 3 }

vtssAclStatusAceTable OBJECT-TYPE
    SYNTAX      SEQUENCE OF VTSSAclStatusAceEntry
    MAX-ACCESS  not-accessible
    STATUS      current
    DESCRIPTION
        "Table of ACE status."
    ::= { vtssAclStatusAce 1 }

vtssAclStatusAceEntry OBJECT-TYPE
    SYNTAX      VTSSAclStatusAceEntry
    MAX-ACCESS  not-accessible
    STATUS      current
    DESCRIPTION
        "Each row contains the status per switch per precedence."
    INDEX       { vtssAclStatusAceSwitchId,
                  vtssAclStatusAcePrecedence }
    ::= { vtssAclStatusAceTable 1 }

VTSSAclStatusAceEntry ::= SEQUENCE {
    vtssAclStatusAceSwitchId    Integer32,
    vtssAclStatusAcePrecedence  Integer32,
    vtssAclStatusAceAclUser     VTSSDisplayString,
    vtssAclStatusAceAceId       Unsigned32,
    vtssAclStatusAceConflict    TruthValue
}

vtssAclStatusAceSwitchId OBJECT-TYPE
    SYNTAX      Integer32 (0..2147483647)
    MAX-ACCESS  accessible-for-notify
    STATUS      current
    DESCRIPTION
        "The switch ID."
    ::= { vtssAclStatusAceEntry 1 }

vtssAclStatusAcePrecedence OBJECT-TYPE
    SYNTAX      Integer32 (0..2147483647)
    MAX-ACCESS  accessible-for-notify
    STATUS      current
    DESCRIPTION
        "The ACL ACE hit precedence."
    ::= { vtssAclStatusAceEntry 2 }

vtssAclStatusAceAclUser OBJECT-TYPE
    SYNTAX      VTSSDisplayString (SIZE(0..31))
    MAX-ACCESS  read-only
    STATUS      current
    DESCRIPTION
        "User of ACE"
    ::= { vtssAclStatusAceEntry 3 }

vtssAclStatusAceAceId OBJECT-TYPE
    SYNTAX      Unsigned32
    MAX-ACCESS  read-only
    STATUS      current
    DESCRIPTION
        "Identifier of ACE"
    ::= { vtssAclStatusAceEntry 4 }

vtssAclStatusAceConflict OBJECT-TYPE
    SYNTAX      TruthValue
    MAX-ACCESS  read-only
    STATUS      current
    DESCRIPTION
        "The conflict status of this ACE. When the status value is true, it
         means the specific ACE is not applied to the hardware due to hardware
         limitations."
    ::= { vtssAclStatusAceEntry 5 }

vtssAclStatusAceHitCountTable OBJECT-TYPE
    SYNTAX      SEQUENCE OF VTSSAclStatusAceHitCountEntry
    MAX-ACCESS  not-accessible
    STATUS      current
    DESCRIPTION
        "Table of ACE hit count status."
    ::= { vtssAclStatusAce 2 }

vtssAclStatusAceHitCountEntry OBJECT-TYPE
    SYNTAX      VTSSAclStatusAceHitCountEntry
    MAX-ACCESS  not-accessible
    STATUS      current
    DESCRIPTION
        "Each row contains the hit count status per ACE."
    INDEX       { vtssAclStatusAceHitCountAceId }
    ::= { vtssAclStatusAceHitCountTable 1 }

VTSSAclStatusAceHitCountEntry ::= SEQUENCE {
    vtssAclStatusAceHitCountAceId    Integer32,
    vtssAclStatusAceHitCountCounter  Unsigned32
}

vtssAclStatusAceHitCountAceId OBJECT-TYPE
    SYNTAX      Integer32 (0..2147483647)
    MAX-ACCESS  accessible-for-notify
    STATUS      current
    DESCRIPTION
        "The ACE ID."
    ::= { vtssAclStatusAceHitCountEntry 1 }

vtssAclStatusAceHitCountCounter OBJECT-TYPE
    SYNTAX      Unsigned32
    MAX-ACCESS  read-only
    STATUS      current
    DESCRIPTION
        "The hit count of this ACE."
    ::= { vtssAclStatusAceHitCountEntry 2 }

vtssAclControl OBJECT IDENTIFIER
    ::= { vtssAclMibObjects 4 }

vtssAclControlGlobals OBJECT IDENTIFIER
    ::= { vtssAclControl 1 }

vtssAclControlGlobalsClearAllHitCount OBJECT-TYPE
    SYNTAX      TruthValue
    MAX-ACCESS  read-write
    STATUS      current
    DESCRIPTION
        "Set true to clear hit counts of all ACEs and interfaces."
    ::= { vtssAclControlGlobals 1 }

vtssAclControlInterface OBJECT IDENTIFIER
    ::= { vtssAclControl 2 }

vtssAclControlInterfaceControlTable OBJECT-TYPE
    SYNTAX      SEQUENCE OF VTSSAclControlInterfaceControlEntry
    MAX-ACCESS  not-accessible
    STATUS      current
    DESCRIPTION
        "This is a table of interface control"
    ::= { vtssAclControlInterface 1 }

vtssAclControlInterfaceControlEntry OBJECT-TYPE
    SYNTAX      VTSSAclControlInterfaceControlEntry
    MAX-ACCESS  not-accessible
    STATUS      current
    DESCRIPTION
        "Each interface has a set of parameters"
    INDEX       { vtssAclControlInterfaceControlIfIndex }
    ::= { vtssAclControlInterfaceControlTable 1 }

VTSSAclControlInterfaceControlEntry ::= SEQUENCE {
    vtssAclControlInterfaceControlIfIndex  VTSSInterfaceIndex,
    vtssAclControlInterfaceControlState    TruthValue
}

vtssAclControlInterfaceControlIfIndex OBJECT-TYPE
    SYNTAX      VTSSInterfaceIndex
    MAX-ACCESS  accessible-for-notify
    STATUS      current
    DESCRIPTION
        "The index of logical interface."
    ::= { vtssAclControlInterfaceControlEntry 1 }

vtssAclControlInterfaceControlState OBJECT-TYPE
    SYNTAX      TruthValue
    MAX-ACCESS  read-write
    STATUS      current
    DESCRIPTION
        "Specify the port status. True is to enable the port and false is to
         shutdown the port"
    ::= { vtssAclControlInterfaceControlEntry 2 }

vtssAclMibConformance OBJECT IDENTIFIER
    ::= { vtssAclMib 2 }

vtssAclMibCompliances OBJECT IDENTIFIER
    ::= { vtssAclMibConformance 1 }

vtssAclMibGroups OBJECT IDENTIFIER
    ::= { vtssAclMibConformance 2 }

vtssAclCapabilitiesInfoGroup OBJECT-GROUP
    OBJECTS     { vtssAclCapabilitiesAceIdMax,
                  vtssAclCapabilitiesPolicyIdMax,
                  vtssAclCapabilitiesRateLimiterIdMax,
                  vtssAclCapabilitiesEvcPolicerIdMax,
                  vtssAclCapabilitiesRateLimiterBitRateSupported,
                  vtssAclCapabilitiesEvcPolicerSupported,
                  vtssAclCapabilitiesMirrorSupported,
                  vtssAclCapabilitiesMultipleRedirectPortsSupported,
                  vtssAclCapabilitiesSecondLookupSupported,
                  vtssAclCapabilitiesMultipleIngressPortsSupported,
                  vtssAclCapabilitiesEgressPortSupported,
                  vtssAclCapabilitiesVlanTaggedSupported,
                  vtssAclCapabilitiesStackableAceSupported }
    STATUS      current
    DESCRIPTION
        "A collection of objects."
    ::= { vtssAclMibGroups 1 }

vtssAclConfigInterfaceConfigInfoGroup OBJECT-GROUP
    OBJECTS     { vtssAclConfigInterfaceConfigIfIndex,
                  vtssAclConfigInterfaceConfigPolicyId,
                  vtssAclConfigInterfaceConfigHitAction,
                  vtssAclConfigInterfaceConfigRedirectPortList,
                  vtssAclConfigInterfaceConfigRateLimiterId,
                  vtssAclConfigInterfaceConfigMirror,
                  vtssAclConfigInterfaceConfigLogging,
                  vtssAclConfigInterfaceConfigShutdown }
    STATUS      current
    DESCRIPTION
        "A collection of objects."
    ::= { vtssAclMibGroups 2 }

vtssAclConfigRateLimiterInfoGroup OBJECT-GROUP
    OBJECTS     { vtssAclConfigRateLimiterRateLimiterId,
                  vtssAclConfigRateLimiterBitRateEnable,
                  vtssAclConfigRateLimiterBitRate,
                  vtssAclConfigRateLimiterPacketRate }
    STATUS      current
    DESCRIPTION
        "A collection of objects."
    ::= { vtssAclMibGroups 3 }

vtssAclConfigAceInfoGroup OBJECT-GROUP
    OBJECTS     { vtssAclConfigAceAceId, vtssAclConfigAceNextAceId,
                  vtssAclConfigAceHitAction,
                  vtssAclConfigAceRedirectPortList,
                  vtssAclConfigAceRedirectPortListSwitchPort,
                  vtssAclConfigAceEgressPortList,
                  vtssAclConfigAceRateLimiterId,
                  vtssAclConfigAceMirror, vtssAclConfigAceLogging,
                  vtssAclConfigAceShutdown,
                  vtssAclConfigAceIngressPortListMode,
                  vtssAclConfigAceIngressPortList,
                  vtssAclConfigAceIngressPortListSwitch,
                  vtssAclConfigAceIngressPortListSwitchPort,
                  vtssAclConfigAcePolicyValue,
                  vtssAclConfigAcePolicyMask,
                  vtssAclConfigAceSecondLookup,
                  vtssAclConfigAceVlanId,
                  vtssAclConfigAceVlanTagPriority,
                  vtssAclConfigAceVlanTagged,
                  vtssAclConfigAceFrameType,
                  vtssAclConfigAceDestMacOp,
                  vtssAclConfigAceEtherSrcMacOp,
                  vtssAclConfigAceEtherSrcMac,
                  vtssAclConfigAceEtherDestMac,
                  vtssAclConfigAceEtherType,
                  vtssAclConfigAceArpSrcMacOp,
                  vtssAclConfigAceArpSrcMac,
                  vtssAclConfigAceArpSenderIp,
                  vtssAclConfigAceArpSenderIpMask,
                  vtssAclConfigAceArpTargetIp,
                  vtssAclConfigAceArpTargetIpMask,
                  vtssAclConfigAceArpOpcode,
                  vtssAclConfigAceArpFlagReq,
                  vtssAclConfigAceArpFlagSha,
                  vtssAclConfigAceArpFlagTha,
                  vtssAclConfigAceArpFlagHln,
                  vtssAclConfigAceArpFlagHrd,
                  vtssAclConfigAceArpFlagPro,
                  vtssAclConfigAceIpv4ProtocolOp,
                  vtssAclConfigAceIpv4Protocol,
                  vtssAclConfigAceIpv4SrcIp,
                  vtssAclConfigAceIpv4SrcIpMask,
                  vtssAclConfigAceIpv4DestIp,
                  vtssAclConfigAceIpv4DestIpMask,
                  vtssAclConfigAceIpv4IcmpTypeOp,
                  vtssAclConfigAceIpv4IcmpType,
                  vtssAclConfigAceIpv4IcmpCodeOp,
                  vtssAclConfigAceIpv4IcmpCode,
                  vtssAclConfigAceIpv4SrcPortOp,
                  vtssAclConfigAceIpv4SrcPort,
                  vtssAclConfigAceIpv4SrcPortRange,
                  vtssAclConfigAceIpv4DestPortOp,
                  vtssAclConfigAceIpv4DestPort,
                  vtssAclConfigAceIpv4DestPortRange,
                  vtssAclConfigAceIpv4FlagTtl,
                  vtssAclConfigAceIpv4FlagFragment,
                  vtssAclConfigAceIpv4FlagIpOption,
                  vtssAclConfigAceIpv4TcpFlagFin,
                  vtssAclConfigAceIpv4TcpFlagSyn,
                  vtssAclConfigAceIpv4TcpFlagRst,
                  vtssAclConfigAceIpv4TcpFlagPsh,
                  vtssAclConfigAceIpv4TcpFlagAck,
                  vtssAclConfigAceIpv4TcpFlagUrg,
                  vtssAclConfigAceIpv6NextHeaderOp,
                  vtssAclConfigAceIpv6NextHeader,
                  vtssAclConfigAceIpv6Icmpv6TypeOp,
                  vtssAclConfigAceIpv6Icmpv6Type,
                  vtssAclConfigAceIpv6Icmpv6CodeOp,
                  vtssAclConfigAceIpv6Icmpv6Code,
                  vtssAclConfigAceIpv6SrcIp,
                  vtssAclConfigAceIpv6SrcIpMask,
                  vtssAclConfigAceIpv6SrcPortOp,
                  vtssAclConfigAceIpv6SrcPort,
                  vtssAclConfigAceIpv6SrcPortRange,
                  vtssAclConfigAceIpv6DestPortOp,
                  vtssAclConfigAceIpv6DestPort,
                  vtssAclConfigAceIpv6DestPortRange,
                  vtssAclConfigAceIpv6FlagTtl,
                  vtssAclConfigAceIpv6TcpFlagFin,
                  vtssAclConfigAceIpv6TcpFlagSyn,
                  vtssAclConfigAceIpv6TcpFlagRst,
                  vtssAclConfigAceIpv6TcpFlagPsh,
                  vtssAclConfigAceIpv6TcpFlagAck,
                  vtssAclConfigAceIpv6TcpFlagUrg,
                  vtssAclConfigAceAction }
    STATUS      current
    DESCRIPTION
        "A collection of objects."
    ::= { vtssAclMibGroups 4 }

vtssAclConfigAceRowEditorInfoGroup OBJECT-GROUP
    OBJECTS     { vtssAclConfigAceRowEditorAceId,
                  vtssAclConfigAceRowEditorNextAceId,
                  vtssAclConfigAceRowEditorHitAction,
                  vtssAclConfigAceRowEditorRedirectPortList,
                  vtssAclConfigAceRowEditorRedirectPortListSwitchPort,
                  vtssAclConfigAceRowEditorEgressPortList,
                  vtssAclConfigAceRowEditorRateLimiterId,
                  vtssAclConfigAceRowEditorMirror,
                  vtssAclConfigAceRowEditorLogging,
                  vtssAclConfigAceRowEditorShutdown,
                  vtssAclConfigAceRowEditorIngressPortListMode,
                  vtssAclConfigAceRowEditorIngressPortList,
                  vtssAclConfigAceRowEditorIngressPortListSwitch,
                  vtssAclConfigAceRowEditorIngressPortListSwitchPort,
                  vtssAclConfigAceRowEditorPolicyValue,
                  vtssAclConfigAceRowEditorPolicyMask,
                  vtssAclConfigAceRowEditorSecondLookup,
                  vtssAclConfigAceRowEditorVlanId,
                  vtssAclConfigAceRowEditorVlanTagPriority,
                  vtssAclConfigAceRowEditorVlanTagged,
                  vtssAclConfigAceRowEditorFrameType,
                  vtssAclConfigAceRowEditorDestMacOp,
                  vtssAclConfigAceRowEditorEtherSrcMacOp,
                  vtssAclConfigAceRowEditorEtherSrcMac,
                  vtssAclConfigAceRowEditorEtherDestMac,
                  vtssAclConfigAceRowEditorEtherType,
                  vtssAclConfigAceRowEditorArpSrcMacOp,
                  vtssAclConfigAceRowEditorArpSrcMac,
                  vtssAclConfigAceRowEditorArpSenderIp,
                  vtssAclConfigAceRowEditorArpSenderIpMask,
                  vtssAclConfigAceRowEditorArpTargetIp,
                  vtssAclConfigAceRowEditorArpTargetIpMask,
                  vtssAclConfigAceRowEditorArpOpcode,
                  vtssAclConfigAceRowEditorArpFlagReq,
                  vtssAclConfigAceRowEditorArpFlagSha,
                  vtssAclConfigAceRowEditorArpFlagTha,
                  vtssAclConfigAceRowEditorArpFlagHln,
                  vtssAclConfigAceRowEditorArpFlagHrd,
                  vtssAclConfigAceRowEditorArpFlagPro,
                  vtssAclConfigAceRowEditorIpv4ProtocolOp,
                  vtssAclConfigAceRowEditorIpv4Protocol,
                  vtssAclConfigAceRowEditorIpv4SrcIp,
                  vtssAclConfigAceRowEditorIpv4SrcIpMask,
                  vtssAclConfigAceRowEditorIpv4DestIp,
                  vtssAclConfigAceRowEditorIpv4DestIpMask,
                  vtssAclConfigAceRowEditorIpv4IcmpTypeOp,
                  vtssAclConfigAceRowEditorIpv4IcmpType,
                  vtssAclConfigAceRowEditorIpv4IcmpCodeOp,
                  vtssAclConfigAceRowEditorIpv4IcmpCode,
                  vtssAclConfigAceRowEditorIpv4SrcPortOp,
                  vtssAclConfigAceRowEditorIpv4SrcPort,
                  vtssAclConfigAceRowEditorIpv4SrcPortRange,
                  vtssAclConfigAceRowEditorIpv4DestPortOp,
                  vtssAclConfigAceRowEditorIpv4DestPort,
                  vtssAclConfigAceRowEditorIpv4DestPortRange,
                  vtssAclConfigAceRowEditorIpv4FlagTtl,
                  vtssAclConfigAceRowEditorIpv4FlagFragment,
                  vtssAclConfigAceRowEditorIpv4FlagIpOption,
                  vtssAclConfigAceRowEditorIpv4TcpFlagFin,
                  vtssAclConfigAceRowEditorIpv4TcpFlagSyn,
                  vtssAclConfigAceRowEditorIpv4TcpFlagRst,
                  vtssAclConfigAceRowEditorIpv4TcpFlagPsh,
                  vtssAclConfigAceRowEditorIpv4TcpFlagAck,
                  vtssAclConfigAceRowEditorIpv4TcpFlagUrg,
                  vtssAclConfigAceRowEditorIpv6NextHeaderOp,
                  vtssAclConfigAceRowEditorIpv6NextHeader,
                  vtssAclConfigAceRowEditorIpv6Icmpv6TypeOp,
                  vtssAclConfigAceRowEditorIpv6Icmpv6Type,
                  vtssAclConfigAceRowEditorIpv6Icmpv6CodeOp,
                  vtssAclConfigAceRowEditorIpv6Icmpv6Code,
                  vtssAclConfigAceRowEditorIpv6SrcIp,
                  vtssAclConfigAceRowEditorIpv6SrcIpMask,
                  vtssAclConfigAceRowEditorIpv6SrcPortOp,
                  vtssAclConfigAceRowEditorIpv6SrcPort,
                  vtssAclConfigAceRowEditorIpv6SrcPortRange,
                  vtssAclConfigAceRowEditorIpv6DestPortOp,
                  vtssAclConfigAceRowEditorIpv6DestPort,
                  vtssAclConfigAceRowEditorIpv6DestPortRange,
                  vtssAclConfigAceRowEditorIpv6FlagTtl,
                  vtssAclConfigAceRowEditorIpv6TcpFlagFin,
                  vtssAclConfigAceRowEditorIpv6TcpFlagSyn,
                  vtssAclConfigAceRowEditorIpv6TcpFlagRst,
                  vtssAclConfigAceRowEditorIpv6TcpFlagPsh,
                  vtssAclConfigAceRowEditorIpv6TcpFlagAck,
                  vtssAclConfigAceRowEditorIpv6TcpFlagUrg,
                  vtssAclConfigAceRowEditorAction }
    STATUS      current
    DESCRIPTION
        "A collection of objects."
    ::= { vtssAclMibGroups 5 }

vtssAclConfigAcePrecedenceInfoGroup OBJECT-GROUP
    OBJECTS     { vtssAclConfigAcePrecedencePrecedence,
                  vtssAclConfigAcePrecedenceAceId }
    STATUS      current
    DESCRIPTION
        "A collection of objects."
    ::= { vtssAclMibGroups 6 }

vtssAclStatusInterfaceHitCountInfoGroup OBJECT-GROUP
    OBJECTS     { vtssAclStatusInterfaceHitCountIfIndex,
                  vtssAclStatusInterfaceHitCountCounter }
    STATUS      current
    DESCRIPTION
        "A collection of objects."
    ::= { vtssAclMibGroups 7 }

vtssAclStatusAceInfoGroup OBJECT-GROUP
    OBJECTS     { vtssAclStatusAceSwitchId,
                  vtssAclStatusAcePrecedence, vtssAclStatusAceAclUser,
                  vtssAclStatusAceAceId, vtssAclStatusAceConflict }
    STATUS      current
    DESCRIPTION
        "A collection of objects."
    ::= { vtssAclMibGroups 8 }

vtssAclStatusAceHitCountInfoGroup OBJECT-GROUP
    OBJECTS     { vtssAclStatusAceHitCountAceId,
                  vtssAclStatusAceHitCountCounter }
    STATUS      current
    DESCRIPTION
        "A collection of objects."
    ::= { vtssAclMibGroups 9 }

vtssAclControlGlobalsInfoGroup OBJECT-GROUP
    OBJECTS     { vtssAclControlGlobalsClearAllHitCount }
    STATUS      current
    DESCRIPTION
        "A collection of objects."
    ::= { vtssAclMibGroups 10 }

vtssAclControlInterfaceControlInfoGroup OBJECT-GROUP
    OBJECTS     { vtssAclControlInterfaceControlIfIndex,
                  vtssAclControlInterfaceControlState }
    STATUS      current
    DESCRIPTION
        "A collection of objects."
    ::= { vtssAclMibGroups 11 }

vtssAclMibCompliance MODULE-COMPLIANCE
    STATUS      current
    DESCRIPTION
        "The compliance statement for the implementation."

    MODULE      -- this module

    MANDATORY-GROUPS { vtssAclCapabilitiesInfoGroup,
                       vtssAclConfigInterfaceConfigInfoGroup,
                       vtssAclConfigRateLimiterInfoGroup,
                       vtssAclConfigAceInfoGroup,
                       vtssAclConfigAceRowEditorInfoGroup,
                       vtssAclConfigAcePrecedenceInfoGroup,
                       vtssAclStatusInterfaceHitCountInfoGroup,
                       vtssAclStatusAceInfoGroup,
                       vtssAclStatusAceHitCountInfoGroup,
                       vtssAclControlGlobalsInfoGroup,
                       vtssAclControlInterfaceControlInfoGroup }

    ::= { vtssAclMibCompliances 1 }

END
