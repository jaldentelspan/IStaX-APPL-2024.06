-- *****************************************************************
-- HTTPS-MIB:  Microsemi ENT private MIB
-- ****************************************************************

VTSS-HTTPS-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    TruthValue FROM SNMPv2-TC
    ;

vtssHttpsMib MODULE-IDENTITY
    LAST-UPDATED "201410100000Z"
    ORGANIZATION
        "Microsemi Corporation"
    CONTACT-INFO
        "Application support: http://www.microchip.com/support"
    DESCRIPTION
        "This is a private version of HTTPS"
    REVISION    "201410100000Z"
    DESCRIPTION
        "Editorial changes"
    REVISION    "201407010000Z"
    DESCRIPTION
        "Initial version"
    ::= { vtssSwitchMgmt 47 }


vtssHttpsMibObjects OBJECT IDENTIFIER
    ::= { vtssHttpsMib 1 }

vtssHttpsConfig OBJECT IDENTIFIER
    ::= { vtssHttpsMibObjects 2 }

vtssHttpsConfigGlobals OBJECT IDENTIFIER
    ::= { vtssHttpsConfig 1 }

vtssHttpsConfigGlobalsMode OBJECT-TYPE
    SYNTAX      TruthValue
    MAX-ACCESS  read-write
    STATUS      current
    DESCRIPTION
        "Global mode of HTTPS. true is to enable the functions of HTTPS and
         false is to disable it."
    ::= { vtssHttpsConfigGlobals 1 }

vtssHttpsConfigGlobalsRedirectToHttps OBJECT-TYPE
    SYNTAX      TruthValue
    MAX-ACCESS  read-write
    STATUS      current
    DESCRIPTION
        "The flag is to enable/disable the automatic redirection from HTTP to
         HTTPS. true is to enable the redirection and false is to disable the
         redirection."
    ::= { vtssHttpsConfigGlobals 2 }

vtssHttpsMibConformance OBJECT IDENTIFIER
    ::= { vtssHttpsMib 2 }

vtssHttpsMibCompliances OBJECT IDENTIFIER
    ::= { vtssHttpsMibConformance 1 }

vtssHttpsMibGroups OBJECT IDENTIFIER
    ::= { vtssHttpsMibConformance 2 }

vtssHttpsConfigGlobalsInfoGroup OBJECT-GROUP
    OBJECTS     { vtssHttpsConfigGlobalsMode,
                  vtssHttpsConfigGlobalsRedirectToHttps }
    STATUS      current
    DESCRIPTION
        "A collection of objects."
    ::= { vtssHttpsMibGroups 1 }

vtssHttpsMibCompliance MODULE-COMPLIANCE
    STATUS      current
    DESCRIPTION
        "The compliance statement for the implementation."

    MODULE      -- this module

    MANDATORY-GROUPS { vtssHttpsConfigGlobalsInfoGroup }

    ::= { vtssHttpsMibCompliances 1 }

END
