-- *****************************************************************
-- GVRP-MIB:  Microsemi ENT private MIB
-- ****************************************************************

VTSS-GVRP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    TruthValue FROM SNMPv2-TC
    VTSSInterfaceIndex FROM VTSS-TC
    ;

vtssGvrpMib MODULE-IDENTITY
    LAST-UPDATED "201703130000Z"
    ORGANIZATION
        "Microsemi Corporation"
    CONTACT-INFO
        "Application support: http://www.microchip.com/support"
    DESCRIPTION
        "Private GVRP MIB."
    REVISION    "201703130000Z"
    DESCRIPTION
        "Updated the description of GVRP Max VLANs parameter."
    REVISION    "201510220000Z"
    DESCRIPTION
        "Fixed a typo and updated the description of GVRP Max VLANs value."
    REVISION    "201411110000Z"
    DESCRIPTION
        "Initial version"
    ::= { vtssSwitchMgmt 89 }


vtssGvrpMibObjects OBJECT IDENTIFIER
    ::= { vtssGvrpMib 1 }

vtssGvrpConfig OBJECT IDENTIFIER
    ::= { vtssGvrpMibObjects 2 }

vtssGvrpConfigGlobals OBJECT IDENTIFIER
    ::= { vtssGvrpConfig 1 }

vtssGvrpConfigGlobalsMode OBJECT-TYPE
    SYNTAX      TruthValue
    MAX-ACCESS  read-write
    STATUS      current
    DESCRIPTION
        "Global enabling of GVRP protocol. TRUE - enable GVRP, FALSE - disable
         GVRP."
    ::= { vtssGvrpConfigGlobals 1 }

vtssGvrpConfigGlobalsJoinTime OBJECT-TYPE
    SYNTAX      Integer32 (1..20)
    MAX-ACCESS  read-write
    STATUS      current
    DESCRIPTION
        "Join-time protocol parameter. Range [1,20] centi seconds."
    ::= { vtssGvrpConfigGlobals 2 }

vtssGvrpConfigGlobalsLeaveTime OBJECT-TYPE
    SYNTAX      Integer32 (60..300)
    MAX-ACCESS  read-write
    STATUS      current
    DESCRIPTION
        "Leave-time protocol parameter. Range [60,300] centi seconds."
    ::= { vtssGvrpConfigGlobals 3 }

vtssGvrpConfigGlobalsLeaveAllTime OBJECT-TYPE
    SYNTAX      Integer32 (1000..5000)
    MAX-ACCESS  read-write
    STATUS      current
    DESCRIPTION
        "Leave-all-time protocol parameter. Range [1000,5000] centi seconds."
    ::= { vtssGvrpConfigGlobals 4 }

vtssGvrpConfigGlobalsMaxVlans OBJECT-TYPE
    SYNTAX      Integer32 (1..4094)
    MAX-ACCESS  read-write
    STATUS      current
    DESCRIPTION
        "Maximum number of VLANs simultaneously supported by GVRP. Range is
         [1,4094]. GVRP must be disabled in order to change this parameter."
    ::= { vtssGvrpConfigGlobals 5 }

vtssGvrpConfigInterface OBJECT IDENTIFIER
    ::= { vtssGvrpConfig 2 }

vtssGvrpConfigInterfaceTable OBJECT-TYPE
    SYNTAX      SEQUENCE OF VTSSGvrpConfigInterfaceEntry
    MAX-ACCESS  not-accessible
    STATUS      current
    DESCRIPTION
        "This is a table of interface configuration"
    ::= { vtssGvrpConfigInterface 1 }

vtssGvrpConfigInterfaceEntry OBJECT-TYPE
    SYNTAX      VTSSGvrpConfigInterfaceEntry
    MAX-ACCESS  not-accessible
    STATUS      current
    DESCRIPTION
        "Each interface has a set of parameters"
    INDEX       { vtssGvrpConfigInterfaceIfIndex }
    ::= { vtssGvrpConfigInterfaceTable 1 }

VTSSGvrpConfigInterfaceEntry ::= SEQUENCE {
    vtssGvrpConfigInterfaceIfIndex  VTSSInterfaceIndex,
    vtssGvrpConfigInterfaceMode     TruthValue
}

vtssGvrpConfigInterfaceIfIndex OBJECT-TYPE
    SYNTAX      VTSSInterfaceIndex
    MAX-ACCESS  accessible-for-notify
    STATUS      current
    DESCRIPTION
        "The index of logical interface."
    ::= { vtssGvrpConfigInterfaceEntry 1 }

vtssGvrpConfigInterfaceMode OBJECT-TYPE
    SYNTAX      TruthValue
    MAX-ACCESS  read-write
    STATUS      current
    DESCRIPTION
        "Per-port mode of GVRP. TRUE - enable GVRP on the port, FALSE - disable
         GVRP on the port."
    ::= { vtssGvrpConfigInterfaceEntry 2 }

vtssGvrpMibConformance OBJECT IDENTIFIER
    ::= { vtssGvrpMib 2 }

vtssGvrpMibCompliances OBJECT IDENTIFIER
    ::= { vtssGvrpMibConformance 1 }

vtssGvrpMibGroups OBJECT IDENTIFIER
    ::= { vtssGvrpMibConformance 2 }

vtssGvrpConfigGlobalsInfoGroup OBJECT-GROUP
    OBJECTS     { vtssGvrpConfigGlobalsMode,
                  vtssGvrpConfigGlobalsJoinTime,
                  vtssGvrpConfigGlobalsLeaveTime,
                  vtssGvrpConfigGlobalsLeaveAllTime,
                  vtssGvrpConfigGlobalsMaxVlans }
    STATUS      current
    DESCRIPTION
        "A collection of objects."
    ::= { vtssGvrpMibGroups 1 }

vtssGvrpConfigInterfaceTableInfoGroup OBJECT-GROUP
    OBJECTS     { vtssGvrpConfigInterfaceIfIndex,
                  vtssGvrpConfigInterfaceMode }
    STATUS      current
    DESCRIPTION
        "A collection of objects."
    ::= { vtssGvrpMibGroups 2 }

vtssGvrpMibCompliance MODULE-COMPLIANCE
    STATUS      current
    DESCRIPTION
        "The compliance statement for the implementation."

    MODULE      -- this module

    MANDATORY-GROUPS { vtssGvrpConfigGlobalsInfoGroup,
                       vtssGvrpConfigInterfaceTableInfoGroup }

    ::= { vtssGvrpMibCompliances 1 }

END
