-- *****************************************************************
-- PVLAN-MIB:  Microsemi ENT private MIB
-- ****************************************************************

VTSS-PVLAN-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Unsigned32 FROM SNMPv2-SMI
    TruthValue FROM SNMPv2-TC
    VTSSInterfaceIndex FROM VTSS-TC
    VTSSPortList FROM VTSS-TC
    VTSSRowEditorState FROM VTSS-TC
    ;

vtssPvlanMib MODULE-IDENTITY
    LAST-UPDATED "201407160000Z"
    ORGANIZATION
        "Microsemi Corporation"
    CONTACT-INFO
        "Application support: http://www.microchip.com/support"
    DESCRIPTION
        "This is a private version of the Private VLAN MIB"
    REVISION    "201407160000Z"
    DESCRIPTION
        "Initial version"
    ::= { vtssSwitchMgmt 23 }


vtssPvlanMibObjects OBJECT IDENTIFIER
    ::= { vtssPvlanMib 1 }

vtssPvlanCapabilities OBJECT IDENTIFIER
    ::= { vtssPvlanMibObjects 1 }

vtssPvlanCapabilitiesHasVlanMembershipMgmt OBJECT-TYPE
    SYNTAX      TruthValue
    MAX-ACCESS  read-only
    STATUS      current
    DESCRIPTION
        "The capability to support PVLAN membership configuration by the device."
    ::= { vtssPvlanCapabilities 1 }

vtssPvlanCapabilitiesVlanIdMax OBJECT-TYPE
    SYNTAX      Unsigned32
    MAX-ACCESS  read-only
    STATUS      current
    DESCRIPTION
        "The maximum VLAN ID of PVLAN membership configuration supported by the
         device."
    ::= { vtssPvlanCapabilities 2 }

vtssPvlanCapabilitiesVlanIdMin OBJECT-TYPE
    SYNTAX      Unsigned32
    MAX-ACCESS  read-only
    STATUS      current
    DESCRIPTION
        "The minimum VLAN ID of PVLAN membership configuration supported by the
         device."
    ::= { vtssPvlanCapabilities 3 }

vtssPvlanConfig OBJECT IDENTIFIER
    ::= { vtssPvlanMibObjects 2 }

vtssPvlanConfigInterface OBJECT IDENTIFIER
    ::= { vtssPvlanConfig 1 }

vtssPvlanConfigInterfaceVlanMembershipTable OBJECT-TYPE
    SYNTAX      SEQUENCE OF VTSSPvlanConfigInterfaceVlanMembershipEntry
    MAX-ACCESS  not-accessible
    STATUS      current
    DESCRIPTION
        "This is a table for managing Private VLAN VLAN membership entries."
    ::= { vtssPvlanConfigInterface 1 }

vtssPvlanConfigInterfaceVlanMembershipEntry OBJECT-TYPE
    SYNTAX      VTSSPvlanConfigInterfaceVlanMembershipEntry
    MAX-ACCESS  not-accessible
    STATUS      current
    DESCRIPTION
        "Each entry has a set of parameters."
    INDEX       { vtssPvlanConfigInterfaceVlanMembershipPvlanIndex }
    ::= { vtssPvlanConfigInterfaceVlanMembershipTable 1 }

VTSSPvlanConfigInterfaceVlanMembershipEntry ::= SEQUENCE {
    vtssPvlanConfigInterfaceVlanMembershipPvlanIndex  Unsigned32,
    vtssPvlanConfigInterfaceVlanMembershipPortList    VTSSPortList,
    vtssPvlanConfigInterfaceVlanMembershipAction      VTSSRowEditorState
}

vtssPvlanConfigInterfaceVlanMembershipPvlanIndex OBJECT-TYPE
    SYNTAX      Unsigned32
    MAX-ACCESS  accessible-for-notify
    STATUS      current
    DESCRIPTION
        "Configuration index of the Private VLAN membership table."
    ::= { vtssPvlanConfigInterfaceVlanMembershipEntry 1 }

vtssPvlanConfigInterfaceVlanMembershipPortList OBJECT-TYPE
    SYNTAX      VTSSPortList
    MAX-ACCESS  read-write
    STATUS      current
    DESCRIPTION
        "It is used to denote the memberships of the specific Private VLAN
         configuration."
    ::= { vtssPvlanConfigInterfaceVlanMembershipEntry 2 }

vtssPvlanConfigInterfaceVlanMembershipAction OBJECT-TYPE
    SYNTAX      VTSSRowEditorState
    MAX-ACCESS  read-write
    STATUS      current
    DESCRIPTION
        "Action"
    ::= { vtssPvlanConfigInterfaceVlanMembershipEntry 100 }

vtssPvlanConfigInterfaceVlanMembershipTableRowEditor OBJECT IDENTIFIER
    ::= { vtssPvlanConfigInterface 2 }

vtssPvlanConfigInterfaceVlanMembershipTableRowEditorPvlanIndex OBJECT-TYPE
    SYNTAX      Unsigned32
    MAX-ACCESS  read-write
    STATUS      current
    DESCRIPTION
        "Configuration index of the Private VLAN membership table."
    ::= { vtssPvlanConfigInterfaceVlanMembershipTableRowEditor 1 }

vtssPvlanConfigInterfaceVlanMembershipTableRowEditorPortList OBJECT-TYPE
    SYNTAX      VTSSPortList
    MAX-ACCESS  read-write
    STATUS      current
    DESCRIPTION
        "It is used to denote the memberships of the specific Private VLAN
         configuration."
    ::= { vtssPvlanConfigInterfaceVlanMembershipTableRowEditor 2 }

vtssPvlanConfigInterfaceVlanMembershipTableRowEditorAction OBJECT-TYPE
    SYNTAX      VTSSRowEditorState
    MAX-ACCESS  read-write
    STATUS      current
    DESCRIPTION
        "Action"
    ::= { vtssPvlanConfigInterfaceVlanMembershipTableRowEditor 100 }

vtssPvlanConfigInterfacePortIsolatationTable OBJECT-TYPE
    SYNTAX      SEQUENCE OF VTSSPvlanConfigInterfacePortIsolatationEntry
    MAX-ACCESS  not-accessible
    STATUS      current
    DESCRIPTION
        "This is a table for managing Private VLAN port isolation entries."
    ::= { vtssPvlanConfigInterface 3 }

vtssPvlanConfigInterfacePortIsolatationEntry OBJECT-TYPE
    SYNTAX      VTSSPvlanConfigInterfacePortIsolatationEntry
    MAX-ACCESS  not-accessible
    STATUS      current
    DESCRIPTION
        "Each entry has a set of parameters."
    INDEX       { vtssPvlanConfigInterfacePortIsolatationPortIndex }
    ::= { vtssPvlanConfigInterfacePortIsolatationTable 1 }

VTSSPvlanConfigInterfacePortIsolatationEntry ::= SEQUENCE {
    vtssPvlanConfigInterfacePortIsolatationPortIndex  VTSSInterfaceIndex,
    vtssPvlanConfigInterfacePortIsolatationEnabled    TruthValue
}

vtssPvlanConfigInterfacePortIsolatationPortIndex OBJECT-TYPE
    SYNTAX      VTSSInterfaceIndex
    MAX-ACCESS  accessible-for-notify
    STATUS      current
    DESCRIPTION
        "Logical interface number of the Private VLAN port isolation."
    ::= { vtssPvlanConfigInterfacePortIsolatationEntry 1 }

vtssPvlanConfigInterfacePortIsolatationEnabled OBJECT-TYPE
    SYNTAX      TruthValue
    MAX-ACCESS  read-write
    STATUS      current
    DESCRIPTION
        "Enable/Disable the Private VLAN isolation functionality."
    ::= { vtssPvlanConfigInterfacePortIsolatationEntry 2 }

vtssPvlanMibConformance OBJECT IDENTIFIER
    ::= { vtssPvlanMib 2 }

vtssPvlanMibCompliances OBJECT IDENTIFIER
    ::= { vtssPvlanMibConformance 1 }

vtssPvlanMibGroups OBJECT IDENTIFIER
    ::= { vtssPvlanMibConformance 2 }

vtssPvlanCapabilitiesInfoGroup OBJECT-GROUP
    OBJECTS     { vtssPvlanCapabilitiesHasVlanMembershipMgmt,
                  vtssPvlanCapabilitiesVlanIdMax,
                  vtssPvlanCapabilitiesVlanIdMin }
    STATUS      current
    DESCRIPTION
        "A collection of objects."
    ::= { vtssPvlanMibGroups 1 }

vtssPvlanConfigInterfaceVlanMembershipTableInfoGroup OBJECT-GROUP
    OBJECTS     { vtssPvlanConfigInterfaceVlanMembershipPvlanIndex,
                  vtssPvlanConfigInterfaceVlanMembershipPortList,
                  vtssPvlanConfigInterfaceVlanMembershipAction }
    STATUS      current
    DESCRIPTION
        "A collection of objects."
    ::= { vtssPvlanMibGroups 2 }

vtssPvlanConfigInterfaceVlanMembershipTableRowEditorInfoGroup OBJECT-GROUP
    OBJECTS     {                   vtssPvlanConfigInterfaceVlanMembershipTableRowEditorPvlanIndex,
                  vtssPvlanConfigInterfaceVlanMembershipTableRowEditorPortList,
                  vtssPvlanConfigInterfaceVlanMembershipTableRowEditorAction }
    STATUS      current
    DESCRIPTION
        "A collection of objects."
    ::= { vtssPvlanMibGroups 3 }

vtssPvlanConfigInterfacePortIsolatationTableInfoGroup OBJECT-GROUP
    OBJECTS     { vtssPvlanConfigInterfacePortIsolatationPortIndex,
                  vtssPvlanConfigInterfacePortIsolatationEnabled }
    STATUS      current
    DESCRIPTION
        "A collection of objects."
    ::= { vtssPvlanMibGroups 4 }

vtssPvlanMibCompliance MODULE-COMPLIANCE
    STATUS      current
    DESCRIPTION
        "The compliance statement for the implementation."

    MODULE      -- this module

    MANDATORY-GROUPS { vtssPvlanCapabilitiesInfoGroup,
                       vtssPvlanConfigInterfaceVlanMembershipTableInfoGroup,
                       vtssPvlanConfigInterfaceVlanMembershipTableRowEditorInfoGroup,
                       vtssPvlanConfigInterfacePortIsolatationTableInfoGroup }

    ::= { vtssPvlanMibCompliances 1 }

END
