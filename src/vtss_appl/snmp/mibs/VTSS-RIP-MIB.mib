-- *****************************************************************
-- RIP-MIB:  Microsemi ENT private MIB
-- ****************************************************************

VTSS-RIP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    IpAddress FROM SNMPv2-SMI
    Unsigned32 FROM SNMPv2-SMI
    TruthValue FROM SNMPv2-TC
    VTSSDisplayString FROM VTSS-TC
    VTSSInterfaceIndex FROM VTSS-TC
    VTSSRowEditorState FROM VTSS-TC
    VTSSUnsigned8 FROM VTSS-TC
    ;

vtssRipMib MODULE-IDENTITY
    LAST-UPDATED "201806110000Z"
    ORGANIZATION
        "Microsemi Corporation"
    CONTACT-INFO
        "Application support: http://www.microchip.com/support"
    DESCRIPTION
        "This is a private version of the RIP MIB."
    REVISION    "201806110000Z"
    DESCRIPTION
        "Initial version."
    ::= { vtssSwitchMgmt 152 }


VTSSRipAuthType ::= TEXTUAL-CONVENTION
    STATUS      current
    DESCRIPTION
        "This enumeration indicates RIP authentication type."
    SYNTAX      INTEGER { nullAuth(0), simplePasswordAuth(1),
                          md5Auth(2) }

VTSSRipDbProtoSubType ::= TEXTUAL-CONVENTION
    STATUS      current
    DESCRIPTION
        "This enumeration indicates the protocol sub-type of the RIP database
         entry."
    SYNTAX      INTEGER { static(0), normal(1), default(2),
                          redistribute(3), interface(4), unknown(5) }

VTSSRipDbProtoType ::= TEXTUAL-CONVENTION
    STATUS      current
    DESCRIPTION
        "This enumeration indicates the protocol type of the RIP database entry."
    SYNTAX      INTEGER { rip(0), connected(1), static(2), ospf(3),
                          unknown(4) }

VTSSRipGlobalVerType ::= TEXTUAL-CONVENTION
    STATUS      current
    DESCRIPTION
        "The global RIP version."
    SYNTAX      INTEGER { default(0), v1(1), v2(2) }

VTSSRipIntfReceiveVersion ::= TEXTUAL-CONVENTION
    STATUS      current
    DESCRIPTION
        "The RIP version for the advertisement reception on the interface."
    SYNTAX      INTEGER { none(0), v1(1), v2(2), both(3),
                          notSpecified(4) }

VTSSRipIntfSendVersion ::= TEXTUAL-CONVENTION
    STATUS      current
    DESCRIPTION
        "The RIP version for the advertisement transmission on the interface."
    SYNTAX      INTEGER { v1(1), v2(2), both(3), notSpecified(4) }

VTSSRipOffsetListDirection ::= TEXTUAL-CONVENTION
    STATUS      current
    DESCRIPTION
        "The direction to add the offset to routing metric update."
    SYNTAX      INTEGER { in(0), out(1) }

VTSSRipSplitHorizonMode ::= TEXTUAL-CONVENTION
    STATUS      current
    DESCRIPTION
        "The split horizon mode."
    SYNTAX      INTEGER { splitHorizon(0), poisonedReverse(1),
                          disabled(2) }

vtssRipMibObjects OBJECT IDENTIFIER
    ::= { vtssRipMib 1 }

vtssRipCapabilities OBJECT IDENTIFIER
    ::= { vtssRipMibObjects 1 }

vtssRipCapabilitiesMinRedistDefMetric OBJECT-TYPE
    SYNTAX      VTSSUnsigned8
    MAX-ACCESS  read-only
    STATUS      current
    DESCRIPTION
        "The minimum value of RIP redistributed default metric"
    ::= { vtssRipCapabilities 1 }

vtssRipCapabilitiesMaxRedistDefMetric OBJECT-TYPE
    SYNTAX      VTSSUnsigned8
    MAX-ACCESS  read-only
    STATUS      current
    DESCRIPTION
        "The maximum value of RIP redistributed default metric"
    ::= { vtssRipCapabilities 2 }

vtssRipCapabilitiesMinRedistSpecificMetric OBJECT-TYPE
    SYNTAX      VTSSUnsigned8
    MAX-ACCESS  read-only
    STATUS      current
    DESCRIPTION
        "The minimum value of RIP redistributed specific metric value."
    ::= { vtssRipCapabilities 3 }

vtssRipCapabilitiesMaxRedistSpecificMetric OBJECT-TYPE
    SYNTAX      VTSSUnsigned8
    MAX-ACCESS  read-only
    STATUS      current
    DESCRIPTION
        "The maximum value of RIP redistributed specific metric value."
    ::= { vtssRipCapabilities 4 }

vtssRipCapabilitiesIsOspfRedistributedSupported OBJECT-TYPE
    SYNTAX      TruthValue
    MAX-ACCESS  read-only
    STATUS      current
    DESCRIPTION
        "Indicate if OSPF redistributed is supported or not"
    ::= { vtssRipCapabilities 5 }

vtssRipCapabilitiesMinTimer OBJECT-TYPE
    SYNTAX      Unsigned32
    MAX-ACCESS  read-only
    STATUS      current
    DESCRIPTION
        "The minimum value of RIP timers value"
    ::= { vtssRipCapabilities 6 }

vtssRipCapabilitiesMaxTimer OBJECT-TYPE
    SYNTAX      Unsigned32
    MAX-ACCESS  read-only
    STATUS      current
    DESCRIPTION
        "The maximum value of RIP timers value"
    ::= { vtssRipCapabilities 7 }

vtssRipCapabilitiesMinAdminDistance OBJECT-TYPE
    SYNTAX      VTSSUnsigned8
    MAX-ACCESS  read-only
    STATUS      current
    DESCRIPTION
        "The minimum value of RIP administrative distance value"
    ::= { vtssRipCapabilities 8 }

vtssRipCapabilitiesMaxAdminDistance OBJECT-TYPE
    SYNTAX      VTSSUnsigned8
    MAX-ACCESS  read-only
    STATUS      current
    DESCRIPTION
        "The maximum value of RIP administrative distance value"
    ::= { vtssRipCapabilities 9 }

vtssRipCapabilitiesSimplePwdLenMax OBJECT-TYPE
    SYNTAX      Unsigned32
    MAX-ACCESS  read-only
    STATUS      current
    DESCRIPTION
        "Maximum value of simple password string length"
    ::= { vtssRipCapabilities 10 }

vtssRipCapabilitiesKeyChainNameLenMax OBJECT-TYPE
    SYNTAX      Unsigned32
    MAX-ACCESS  read-only
    STATUS      current
    DESCRIPTION
        "Maximum value of key chain name length"
    ::= { vtssRipCapabilities 11 }

vtssRipCapabilitiesOffsetListMaxCount OBJECT-TYPE
    SYNTAX      Unsigned32
    MAX-ACCESS  read-only
    STATUS      current
    DESCRIPTION
        "The maximum count of the RIP offset-list"
    ::= { vtssRipCapabilities 12 }

vtssRipCapabilitiesMinOffsetListMetric OBJECT-TYPE
    SYNTAX      VTSSUnsigned8
    MAX-ACCESS  read-only
    STATUS      current
    DESCRIPTION
        "The minimum value of RIP offset-list metric value."
    ::= { vtssRipCapabilities 13 }

vtssRipCapabilitiesMaxOffsetListMetric OBJECT-TYPE
    SYNTAX      VTSSUnsigned8
    MAX-ACCESS  read-only
    STATUS      current
    DESCRIPTION
        "The maximum value of RIP offset-list specific metric value."
    ::= { vtssRipCapabilities 14 }

vtssRipCapabilitiesNetworkSegmentMaxCount OBJECT-TYPE
    SYNTAX      Unsigned32
    MAX-ACCESS  read-only
    STATUS      current
    DESCRIPTION
        "The maximum count of the RIP count of the RIP network segments"
    ::= { vtssRipCapabilities 15 }

vtssRipCapabilitiesNeighborMaxCount OBJECT-TYPE
    SYNTAX      Unsigned32
    MAX-ACCESS  read-only
    STATUS      current
    DESCRIPTION
        "The maximum count of the RIP neighbors"
    ::= { vtssRipCapabilities 16 }

vtssRipConfig OBJECT IDENTIFIER
    ::= { vtssRipMibObjects 2 }

vtssRipConfigRouter OBJECT IDENTIFIER
    ::= { vtssRipConfig 1 }

vtssRipConfigRouterRouterMode OBJECT-TYPE
    SYNTAX      TruthValue
    MAX-ACCESS  read-write
    STATUS      current
    DESCRIPTION
        "RIP router mode."
    ::= { vtssRipConfigRouter 1 }

vtssRipConfigRouterVersion OBJECT-TYPE
    SYNTAX      VTSSRipGlobalVerType
    MAX-ACCESS  read-write
    STATUS      current
    DESCRIPTION
        "RIP version support."
    ::= { vtssRipConfigRouter 2 }

vtssRipConfigRouterUpdateTimer OBJECT-TYPE
    SYNTAX      Unsigned32 (5..2147483)
    MAX-ACCESS  read-write
    STATUS      current
    DESCRIPTION
        "The timer interval (in seconds) between the router sends the complete
         routing table to all neighboring RIP routers."
    ::= { vtssRipConfigRouter 3 }

vtssRipConfigRouterInvalidTimer OBJECT-TYPE
    SYNTAX      Unsigned32 (5..2147483)
    MAX-ACCESS  read-write
    STATUS      current
    DESCRIPTION
        "The invalid timer is the number of seconds after which a route will be
         marked invalid."
    ::= { vtssRipConfigRouter 4 }

vtssRipConfigRouterGarbageCollectionTimer OBJECT-TYPE
    SYNTAX      Unsigned32 (5..2147483)
    MAX-ACCESS  read-write
    STATUS      current
    DESCRIPTION
        "The garbage collection timer is the number of seconds after which a
         route will be deleted."
    ::= { vtssRipConfigRouter 5 }

vtssRipConfigRouterRedistDefaultMetric OBJECT-TYPE
    SYNTAX      VTSSUnsigned8 (1..16)
    MAX-ACCESS  read-write
    STATUS      current
    DESCRIPTION
        "The RIP default redistributed metric.It is used when the metric value
         isn't specificed for the redistributed protocol type."
    ::= { vtssRipConfigRouter 6 }

vtssRipConfigRouterConnectedRedistEnabled OBJECT-TYPE
    SYNTAX      TruthValue
    MAX-ACCESS  read-write
    STATUS      current
    DESCRIPTION
        "Indicate if the router redistribute the directly connected routes with
         RIP not enabled into the RIP domain or not."
    ::= { vtssRipConfigRouter 7 }

vtssRipConfigRouterConnectedRedistIsSpecificMetric OBJECT-TYPE
    SYNTAX      TruthValue
    MAX-ACCESS  read-write
    STATUS      current
    DESCRIPTION
        "Indicate the metric value of connected interfaces redistribution is a
         specific configured value or not."
    ::= { vtssRipConfigRouter 8 }

vtssRipConfigRouterConnectedRedistMetricVal OBJECT-TYPE
    SYNTAX      VTSSUnsigned8 (1..16)
    MAX-ACCESS  read-write
    STATUS      current
    DESCRIPTION
        "User specified metric value for the connected interfaces. The field is
         significant only when the argument 'ConnectedRedistIsSpecificMetric' is
         TRUE. If the specific metric setting is removed while the connected
         redistributed mode is enabled, the router will updates the original
         connected redistributed routes with metric value 16 before updates to
         the new metric value."
    ::= { vtssRipConfigRouter 9 }

vtssRipConfigRouterStaticRedistEnabled OBJECT-TYPE
    SYNTAX      TruthValue
    MAX-ACCESS  read-write
    STATUS      current
    DESCRIPTION
        "Indicate if the router redistribute the static routes intothe RIP
         domain or not."
    ::= { vtssRipConfigRouter 10 }

vtssRipConfigRouterStaticRedistIsSpecificMetric OBJECT-TYPE
    SYNTAX      TruthValue
    MAX-ACCESS  read-write
    STATUS      current
    DESCRIPTION
        "Indicate the metric value if static route redistribution is a specific
         configured value or not."
    ::= { vtssRipConfigRouter 11 }

vtssRipConfigRouterStaticRedistMetricVal OBJECT-TYPE
    SYNTAX      VTSSUnsigned8 (1..16)
    MAX-ACCESS  read-write
    STATUS      current
    DESCRIPTION
        "User specified metric value for the static routes. The field is
         significant only when the argument 'StaticRedistIsSpecificMetric' is
         TRUE. If the specific metric setting is removed while the static
         redistributed mode is enabled, the router will updates the original
         static redistributed routes with metric value 16 before updates to the
         new metric value"
    ::= { vtssRipConfigRouter 12 }

vtssRipConfigRouterOspfRedistEnabled OBJECT-TYPE
    SYNTAX      TruthValue
    MAX-ACCESS  read-write
    STATUS      current
    DESCRIPTION
        "Indicate if the router redistribute the OSPF routes into the RIP domain
         or not. The field is significant only when the OSPF protocol is
         supported on the device."
    ::= { vtssRipConfigRouter 13 }

vtssRipConfigRouterOspfRedistIsSpecificMetric OBJECT-TYPE
    SYNTAX      TruthValue
    MAX-ACCESS  read-write
    STATUS      current
    DESCRIPTION
        "Indicate the metric value if RIP route redistribution is a specific
         configured value or not.The field is significant only when the OSPF
         protocol is supported on the device."
    ::= { vtssRipConfigRouter 14 }

vtssRipConfigRouterOspfRedistMetricVal OBJECT-TYPE
    SYNTAX      VTSSUnsigned8 (1..16)
    MAX-ACCESS  read-write
    STATUS      current
    DESCRIPTION
        "User specified metric value for the RIP routes. The field is
         significant only when the OSPF protocol is supported on the device and
         argument 'OspfRedistIsSpecificMetric' is TRUE. If the specific metric
         setting is removed while the OSPF redistributed mode is enabled, the
         router will updates the original OSPF redistributed routes with metric
         value 16 before updates to the new metric value"
    ::= { vtssRipConfigRouter 15 }

vtssRipConfigRouterDefaultRouteRedist OBJECT-TYPE
    SYNTAX      TruthValue
    MAX-ACCESS  read-write
    STATUS      current
    DESCRIPTION
        "The RIP default route redistribution."
    ::= { vtssRipConfigRouter 16 }

vtssRipConfigRouterDefPassiveIntf OBJECT-TYPE
    SYNTAX      TruthValue
    MAX-ACCESS  read-write
    STATUS      current
    DESCRIPTION
        "Configure all interfaces as passive-interface by default."
    ::= { vtssRipConfigRouter 17 }

vtssRipConfigRouterAdminDistance OBJECT-TYPE
    SYNTAX      VTSSUnsigned8 (1..255)
    MAX-ACCESS  read-write
    STATUS      current
    DESCRIPTION
        "The RIP administrative distance."
    ::= { vtssRipConfigRouter 18 }

vtssRipConfigNetworkTable OBJECT-TYPE
    SYNTAX      SEQUENCE OF VTSSRipConfigNetworkEntry
    MAX-ACCESS  not-accessible
    STATUS      current
    DESCRIPTION
        "This is RIP network configuration table. It is used to specify the RIP
         enabled interface(s). When RIP is enabled on the specific interface(s),
         the router can provide the network information to the other RIP routers
         via those interfaces."
    ::= { vtssRipConfig 2 }

vtssRipConfigNetworkEntry OBJECT-TYPE
    SYNTAX      VTSSRipConfigNetworkEntry
    MAX-ACCESS  not-accessible
    STATUS      current
    DESCRIPTION
        "Each entry in this table represents the RIP enabled interface(s)."
    INDEX       { vtssRipConfigNetworkNetwork,
                  vtssRipConfigNetworkIpSubnetMaskLength }
    ::= { vtssRipConfigNetworkTable 1 }

VTSSRipConfigNetworkEntry ::= SEQUENCE {
    vtssRipConfigNetworkNetwork             IpAddress,
    vtssRipConfigNetworkIpSubnetMaskLength  Integer32,
    vtssRipConfigNetworkAction              VTSSRowEditorState
}

vtssRipConfigNetworkNetwork OBJECT-TYPE
    SYNTAX      IpAddress
    MAX-ACCESS  accessible-for-notify
    STATUS      current
    DESCRIPTION
        "IPv4 network address."
    ::= { vtssRipConfigNetworkEntry 1 }

vtssRipConfigNetworkIpSubnetMaskLength OBJECT-TYPE
    SYNTAX      Integer32 (0..32)
    MAX-ACCESS  accessible-for-notify
    STATUS      current
    DESCRIPTION
        "IPv4 network mask length."
    ::= { vtssRipConfigNetworkEntry 2 }

vtssRipConfigNetworkAction OBJECT-TYPE
    SYNTAX      VTSSRowEditorState
    MAX-ACCESS  read-write
    STATUS      current
    DESCRIPTION
        "Action"
    ::= { vtssRipConfigNetworkEntry 100 }

vtssRipConfigNetworkTableRowEditor OBJECT IDENTIFIER
    ::= { vtssRipConfig 3 }

vtssRipConfigNetworkTableRowEditorNetwork OBJECT-TYPE
    SYNTAX      IpAddress
    MAX-ACCESS  read-write
    STATUS      current
    DESCRIPTION
        "IPv4 network address."
    ::= { vtssRipConfigNetworkTableRowEditor 1 }

vtssRipConfigNetworkTableRowEditorIpSubnetMaskLength OBJECT-TYPE
    SYNTAX      Integer32 (0..32)
    MAX-ACCESS  read-write
    STATUS      current
    DESCRIPTION
        "IPv4 network mask length."
    ::= { vtssRipConfigNetworkTableRowEditor 2 }

vtssRipConfigNetworkTableRowEditorAction OBJECT-TYPE
    SYNTAX      VTSSRowEditorState
    MAX-ACCESS  read-write
    STATUS      current
    DESCRIPTION
        "Action"
    ::= { vtssRipConfigNetworkTableRowEditor 100 }

vtssRipConfigRouterInterfaceTable OBJECT-TYPE
    SYNTAX      SEQUENCE OF VTSSRipConfigRouterInterfaceEntry
    MAX-ACCESS  not-accessible
    STATUS      current
    DESCRIPTION
        "This is RIP router interface configuration table."
    ::= { vtssRipConfig 4 }

vtssRipConfigRouterInterfaceEntry OBJECT-TYPE
    SYNTAX      VTSSRipConfigRouterInterfaceEntry
    MAX-ACCESS  not-accessible
    STATUS      current
    DESCRIPTION
        "Each router interface has a set of parameters."
    INDEX       { vtssRipConfigRouterInterfaceIfIndex }
    ::= { vtssRipConfigRouterInterfaceTable 1 }

VTSSRipConfigRouterInterfaceEntry ::= SEQUENCE {
    vtssRipConfigRouterInterfaceIfIndex           VTSSInterfaceIndex,
    vtssRipConfigRouterInterfacePassiveInterface  TruthValue
}

vtssRipConfigRouterInterfaceIfIndex OBJECT-TYPE
    SYNTAX      VTSSInterfaceIndex
    MAX-ACCESS  accessible-for-notify
    STATUS      current
    DESCRIPTION
        "Logical interface number."
    ::= { vtssRipConfigRouterInterfaceEntry 1 }

vtssRipConfigRouterInterfacePassiveInterface OBJECT-TYPE
    SYNTAX      TruthValue
    MAX-ACCESS  read-write
    STATUS      current
    DESCRIPTION
        "Enable the interface as RIP passive-interface."
    ::= { vtssRipConfigRouterInterfaceEntry 2 }

vtssRipConfigNeighborTable OBJECT-TYPE
    SYNTAX      SEQUENCE OF VTSSRipConfigNeighborEntry
    MAX-ACCESS  not-accessible
    STATUS      current
    DESCRIPTION
        "This is RIP neighbor connection table. It is used to configure the RIP
         router to send RIP updates to specific neighbors using the unicast,
         broadcast, or network IP address after update timer expiration."
    ::= { vtssRipConfig 5 }

vtssRipConfigNeighborEntry OBJECT-TYPE
    SYNTAX      VTSSRipConfigNeighborEntry
    MAX-ACCESS  not-accessible
    STATUS      current
    DESCRIPTION
        "Each entry in this table represents the neighbor address."
    INDEX       { vtssRipConfigNeighborIpv4Addr }
    ::= { vtssRipConfigNeighborTable 1 }

VTSSRipConfigNeighborEntry ::= SEQUENCE {
    vtssRipConfigNeighborIpv4Addr  IpAddress,
    vtssRipConfigNeighborAction    VTSSRowEditorState
}

vtssRipConfigNeighborIpv4Addr OBJECT-TYPE
    SYNTAX      IpAddress
    MAX-ACCESS  accessible-for-notify
    STATUS      current
    DESCRIPTION
        "The IPv4 address."
    ::= { vtssRipConfigNeighborEntry 1 }

vtssRipConfigNeighborAction OBJECT-TYPE
    SYNTAX      VTSSRowEditorState
    MAX-ACCESS  read-write
    STATUS      current
    DESCRIPTION
        "Action"
    ::= { vtssRipConfigNeighborEntry 100 }

vtssRipConfigNeighborTableRowEditor OBJECT IDENTIFIER
    ::= { vtssRipConfig 6 }

vtssRipConfigNeighborTableRowEditorIpv4Addr OBJECT-TYPE
    SYNTAX      IpAddress
    MAX-ACCESS  read-write
    STATUS      current
    DESCRIPTION
        "The IPv4 address."
    ::= { vtssRipConfigNeighborTableRowEditor 1 }

vtssRipConfigNeighborTableRowEditorAction OBJECT-TYPE
    SYNTAX      VTSSRowEditorState
    MAX-ACCESS  read-write
    STATUS      current
    DESCRIPTION
        "Action"
    ::= { vtssRipConfigNeighborTableRowEditor 100 }

vtssRipConfigInterfaceTable OBJECT-TYPE
    SYNTAX      SEQUENCE OF VTSSRipConfigInterfaceEntry
    MAX-ACCESS  not-accessible
    STATUS      current
    DESCRIPTION
        "This is RIP interface configuration table."
    ::= { vtssRipConfig 7 }

vtssRipConfigInterfaceEntry OBJECT-TYPE
    SYNTAX      VTSSRipConfigInterfaceEntry
    MAX-ACCESS  not-accessible
    STATUS      current
    DESCRIPTION
        "Each interface has a set of parameters."
    INDEX       { vtssRipConfigInterfaceIfIndex }
    ::= { vtssRipConfigInterfaceTable 1 }

VTSSRipConfigInterfaceEntry ::= SEQUENCE {
    vtssRipConfigInterfaceIfIndex           VTSSInterfaceIndex,
    vtssRipConfigInterfaceSendVersion       VTSSRipIntfSendVersion,
    vtssRipConfigInterfaceRecvVersion       VTSSRipIntfReceiveVersion,
    vtssRipConfigInterfaceSplitHorizonMode  VTSSRipSplitHorizonMode,
    vtssRipConfigInterfaceAuthType          VTSSRipAuthType,
    vtssRipConfigInterfaceKeyChainName      VTSSDisplayString,
    vtssRipConfigInterfaceIsEncrypted       TruthValue,
    vtssRipConfigInterfaceSimplePwd         VTSSDisplayString
}

vtssRipConfigInterfaceIfIndex OBJECT-TYPE
    SYNTAX      VTSSInterfaceIndex
    MAX-ACCESS  accessible-for-notify
    STATUS      current
    DESCRIPTION
        "Logical interface number."
    ::= { vtssRipConfigInterfaceEntry 1 }

vtssRipConfigInterfaceSendVersion OBJECT-TYPE
    SYNTAX      VTSSRipIntfSendVersion
    MAX-ACCESS  read-write
    STATUS      current
    DESCRIPTION
        "The RIP version for the advertisement transmission on the interface."
    ::= { vtssRipConfigInterfaceEntry 2 }

vtssRipConfigInterfaceRecvVersion OBJECT-TYPE
    SYNTAX      VTSSRipIntfReceiveVersion
    MAX-ACCESS  read-write
    STATUS      current
    DESCRIPTION
        "The RIP version for the advertisement reception on the interface."
    ::= { vtssRipConfigInterfaceEntry 3 }

vtssRipConfigInterfaceSplitHorizonMode OBJECT-TYPE
    SYNTAX      VTSSRipSplitHorizonMode
    MAX-ACCESS  read-write
    STATUS      current
    DESCRIPTION
        "The split horizon mode."
    ::= { vtssRipConfigInterfaceEntry 4 }

vtssRipConfigInterfaceAuthType OBJECT-TYPE
    SYNTAX      VTSSRipAuthType
    MAX-ACCESS  read-write
    STATUS      current
    DESCRIPTION
        "The authentication type."
    ::= { vtssRipConfigInterfaceEntry 5 }

vtssRipConfigInterfaceKeyChainName OBJECT-TYPE
    SYNTAX      VTSSDisplayString (SIZE(0..31))
    MAX-ACCESS  read-write
    STATUS      current
    DESCRIPTION
        "The key chain used by MD5 authentication."
    ::= { vtssRipConfigInterfaceEntry 6 }

vtssRipConfigInterfaceIsEncrypted OBJECT-TYPE
    SYNTAX      TruthValue
    MAX-ACCESS  read-write
    STATUS      current
    DESCRIPTION
        "The flag indicates the simple password is encrypted or not. TRUE means
         the simple password is encrypted. FALSE means the simple password is
         plain text."
    ::= { vtssRipConfigInterfaceEntry 7 }

vtssRipConfigInterfaceSimplePwd OBJECT-TYPE
    SYNTAX      VTSSDisplayString (SIZE(0..128))
    MAX-ACCESS  read-write
    STATUS      current
    DESCRIPTION
        "The simple password."
    ::= { vtssRipConfigInterfaceEntry 8 }

vtssRipConfigOffsetListTable OBJECT-TYPE
    SYNTAX      SEQUENCE OF VTSSRipConfigOffsetListEntry
    MAX-ACCESS  not-accessible
    STATUS      current
    DESCRIPTION
        "This is RIP offset-list configuration table."
    ::= { vtssRipConfig 8 }

vtssRipConfigOffsetListEntry OBJECT-TYPE
    SYNTAX      VTSSRipConfigOffsetListEntry
    MAX-ACCESS  not-accessible
    STATUS      current
    DESCRIPTION
        "Each offset-list entry has a set of parameters."
    INDEX       { vtssRipConfigOffsetListIfIndex,
                  vtssRipConfigOffsetListRipOffsetListDirection }
    ::= { vtssRipConfigOffsetListTable 1 }

VTSSRipConfigOffsetListEntry ::= SEQUENCE {
    vtssRipConfigOffsetListIfIndex                 VTSSInterfaceIndex,
    vtssRipConfigOffsetListRipOffsetListDirection  VTSSRipOffsetListDirection,
    vtssRipConfigOffsetListAccessListName          VTSSDisplayString,
    vtssRipConfigOffsetListOffsetMetric            VTSSUnsigned8,
    vtssRipConfigOffsetListAction                  VTSSRowEditorState
}

vtssRipConfigOffsetListIfIndex OBJECT-TYPE
    SYNTAX      VTSSInterfaceIndex
    MAX-ACCESS  accessible-for-notify
    STATUS      current
    DESCRIPTION
        "Logical interface number."
    ::= { vtssRipConfigOffsetListEntry 1 }

vtssRipConfigOffsetListRipOffsetListDirection OBJECT-TYPE
    SYNTAX      VTSSRipOffsetListDirection
    MAX-ACCESS  accessible-for-notify
    STATUS      current
    DESCRIPTION
        "The direction to add the offset to routing metric update."
    ::= { vtssRipConfigOffsetListEntry 2 }

vtssRipConfigOffsetListAccessListName OBJECT-TYPE
    SYNTAX      VTSSDisplayString (SIZE(0..31))
    MAX-ACCESS  read-write
    STATUS      current
    DESCRIPTION
        "Access-list name."
    ::= { vtssRipConfigOffsetListEntry 3 }

vtssRipConfigOffsetListOffsetMetric OBJECT-TYPE
    SYNTAX      VTSSUnsigned8 (0..16)
    MAX-ACCESS  read-write
    STATUS      current
    DESCRIPTION
        "The offset to incoming or outgoing routing metric."
    ::= { vtssRipConfigOffsetListEntry 4 }

vtssRipConfigOffsetListAction OBJECT-TYPE
    SYNTAX      VTSSRowEditorState
    MAX-ACCESS  read-write
    STATUS      current
    DESCRIPTION
        "Action"
    ::= { vtssRipConfigOffsetListEntry 100 }

vtssRipConfigOffsetListTableRowEditor OBJECT IDENTIFIER
    ::= { vtssRipConfig 9 }

vtssRipConfigOffsetListTableRowEditorIfIndex OBJECT-TYPE
    SYNTAX      VTSSInterfaceIndex
    MAX-ACCESS  read-write
    STATUS      current
    DESCRIPTION
        "Logical interface number."
    ::= { vtssRipConfigOffsetListTableRowEditor 1 }

vtssRipConfigOffsetListTableRowEditorRipOffsetListDirection OBJECT-TYPE
    SYNTAX      VTSSRipOffsetListDirection
    MAX-ACCESS  read-write
    STATUS      current
    DESCRIPTION
        "The direction to add the offset to routing metric update."
    ::= { vtssRipConfigOffsetListTableRowEditor 2 }

vtssRipConfigOffsetListTableRowEditorAccessListName OBJECT-TYPE
    SYNTAX      VTSSDisplayString (SIZE(0..31))
    MAX-ACCESS  read-write
    STATUS      current
    DESCRIPTION
        "Access-list name."
    ::= { vtssRipConfigOffsetListTableRowEditor 3 }

vtssRipConfigOffsetListTableRowEditorOffsetMetric OBJECT-TYPE
    SYNTAX      VTSSUnsigned8 (0..16)
    MAX-ACCESS  read-write
    STATUS      current
    DESCRIPTION
        "The offset to incoming or outgoing routing metric."
    ::= { vtssRipConfigOffsetListTableRowEditor 4 }

vtssRipConfigOffsetListTableRowEditorAction OBJECT-TYPE
    SYNTAX      VTSSRowEditorState
    MAX-ACCESS  read-write
    STATUS      current
    DESCRIPTION
        "Action"
    ::= { vtssRipConfigOffsetListTableRowEditor 100 }

vtssRipStatus OBJECT IDENTIFIER
    ::= { vtssRipMibObjects 3 }

vtssRipStatusGeneral OBJECT IDENTIFIER
    ::= { vtssRipStatus 1 }

vtssRipStatusGeneralRouterModeIsEnabled OBJECT-TYPE
    SYNTAX      TruthValue
    MAX-ACCESS  read-only
    STATUS      current
    DESCRIPTION
        "RIP router mode."
    ::= { vtssRipStatusGeneral 1 }

vtssRipStatusGeneralVersion OBJECT-TYPE
    SYNTAX      VTSSRipGlobalVerType
    MAX-ACCESS  read-only
    STATUS      current
    DESCRIPTION
        "This indicates the global rip version. By default, the router sends
         RIPv2 and accepts both RIPv1 and RIPv2. When the router receive either
         version of REQUESTS or triggered updates packets, it replies with the
         appropriate version. Be aware that the RIP network class configuration
         when RIPv1 is involved in the topology. RIPv1 uses classful routing,
         the subnet information is not included in the routing updates. The
         limitation makes it impossible to have different-sized subnets inside
         of the same network class. In other words, all subnets in a network
         class must have the same size."
    ::= { vtssRipStatusGeneral 2 }

vtssRipStatusGeneralUpdateTimer OBJECT-TYPE
    SYNTAX      Unsigned32
    MAX-ACCESS  read-only
    STATUS      current
    DESCRIPTION
        "The timer interval (in seconds) between the router sends the complete
         routing table to all neighboring RIP routers"
    ::= { vtssRipStatusGeneral 3 }

vtssRipStatusGeneralInvalidTimer OBJECT-TYPE
    SYNTAX      Unsigned32
    MAX-ACCESS  read-only
    STATUS      current
    DESCRIPTION
        "The invalid timer is the number of seconds after which a route will be
         marked invalid."
    ::= { vtssRipStatusGeneral 4 }

vtssRipStatusGeneralGarbageCollectionTimer OBJECT-TYPE
    SYNTAX      Unsigned32
    MAX-ACCESS  read-only
    STATUS      current
    DESCRIPTION
        "The garbage collection timer is the number of seconds after which a
         route will be deleted."
    ::= { vtssRipStatusGeneral 5 }

vtssRipStatusGeneralNextUpdateTime OBJECT-TYPE
    SYNTAX      Unsigned32
    MAX-ACCESS  read-only
    STATUS      current
    DESCRIPTION
        "Specifies when the next round of updates will be sent out from this
         router in seconds."
    ::= { vtssRipStatusGeneral 6 }

vtssRipStatusGeneralRedistDefMetric OBJECT-TYPE
    SYNTAX      VTSSUnsigned8
    MAX-ACCESS  read-only
    STATUS      current
    DESCRIPTION
        "This indicates the default metric value of redistributed routes."
    ::= { vtssRipStatusGeneral 7 }

vtssRipStatusGeneralIsRedistributeConnected OBJECT-TYPE
    SYNTAX      TruthValue
    MAX-ACCESS  read-only
    STATUS      current
    DESCRIPTION
        "This indicates the connected route is redistributed or not."
    ::= { vtssRipStatusGeneral 8 }

vtssRipStatusGeneralIsRedistributeStatic OBJECT-TYPE
    SYNTAX      TruthValue
    MAX-ACCESS  read-only
    STATUS      current
    DESCRIPTION
        "This indicates the static route is redistributed or not."
    ::= { vtssRipStatusGeneral 9 }

vtssRipStatusGeneralIsRedistributeOSPF OBJECT-TYPE
    SYNTAX      TruthValue
    MAX-ACCESS  read-only
    STATUS      current
    DESCRIPTION
        "This indicates the OSPF route is redistributed or not."
    ::= { vtssRipStatusGeneral 10 }

vtssRipStatusGeneralAdminDistance OBJECT-TYPE
    SYNTAX      VTSSUnsigned8
    MAX-ACCESS  read-only
    STATUS      current
    DESCRIPTION
        "This indicates administrative distance value"
    ::= { vtssRipStatusGeneral 11 }

vtssRipStatusInterfaceTable OBJECT-TYPE
    SYNTAX      SEQUENCE OF VTSSRipStatusInterfaceEntry
    MAX-ACCESS  not-accessible
    STATUS      current
    DESCRIPTION
        "The RIP interface status information table."
    ::= { vtssRipStatus 2 }

vtssRipStatusInterfaceEntry OBJECT-TYPE
    SYNTAX      VTSSRipStatusInterfaceEntry
    MAX-ACCESS  not-accessible
    STATUS      current
    DESCRIPTION
        "Each entry in this table represents RIP the active interface status
         information."
    INDEX       { vtssRipStatusInterfaceIfIndex }
    ::= { vtssRipStatusInterfaceTable 1 }

VTSSRipStatusInterfaceEntry ::= SEQUENCE {
    vtssRipStatusInterfaceIfIndex             VTSSInterfaceIndex,
    vtssRipStatusInterfaceSendVersion         VTSSRipIntfSendVersion,
    vtssRipStatusInterfaceRecvVersion         VTSSRipIntfReceiveVersion,
    vtssRipStatusInterfaceTriggeredUpdate     TruthValue,
    vtssRipStatusInterfaceIsPassiveInterface  TruthValue,
    vtssRipStatusInterfaceAuthType            VTSSRipAuthType,
    vtssRipStatusInterfaceKeyChainName        VTSSDisplayString
}

vtssRipStatusInterfaceIfIndex OBJECT-TYPE
    SYNTAX      VTSSInterfaceIndex
    MAX-ACCESS  accessible-for-notify
    STATUS      current
    DESCRIPTION
        "Logical interface number."
    ::= { vtssRipStatusInterfaceEntry 1 }

vtssRipStatusInterfaceSendVersion OBJECT-TYPE
    SYNTAX      VTSSRipIntfSendVersion
    MAX-ACCESS  read-only
    STATUS      current
    DESCRIPTION
        "The RIP version for the advertisement transmission on the interface."
    ::= { vtssRipStatusInterfaceEntry 2 }

vtssRipStatusInterfaceRecvVersion OBJECT-TYPE
    SYNTAX      VTSSRipIntfReceiveVersion
    MAX-ACCESS  read-only
    STATUS      current
    DESCRIPTION
        "The RIP version for the advertisement reception on the interface."
    ::= { vtssRipStatusInterfaceEntry 3 }

vtssRipStatusInterfaceTriggeredUpdate OBJECT-TYPE
    SYNTAX      TruthValue
    MAX-ACCESS  read-only
    STATUS      current
    DESCRIPTION
        "This indicates the interface enable triggered update or not."
    ::= { vtssRipStatusInterfaceEntry 4 }

vtssRipStatusInterfaceIsPassiveInterface OBJECT-TYPE
    SYNTAX      TruthValue
    MAX-ACCESS  read-only
    STATUS      current
    DESCRIPTION
        "This indicates if the passive-interface is active on the interface or
         not."
    ::= { vtssRipStatusInterfaceEntry 5 }

vtssRipStatusInterfaceAuthType OBJECT-TYPE
    SYNTAX      VTSSRipAuthType
    MAX-ACCESS  read-only
    STATUS      current
    DESCRIPTION
        "The authentication type."
    ::= { vtssRipStatusInterfaceEntry 6 }

vtssRipStatusInterfaceKeyChainName OBJECT-TYPE
    SYNTAX      VTSSDisplayString (SIZE(0..31))
    MAX-ACCESS  read-only
    STATUS      current
    DESCRIPTION
        "This indicates the interface is associate with a specific key-chain
         name."
    ::= { vtssRipStatusInterfaceEntry 7 }

vtssRipStatusDbTable OBJECT-TYPE
    SYNTAX      SEQUENCE OF VTSSRipStatusDbEntry
    MAX-ACCESS  not-accessible
    STATUS      current
    DESCRIPTION
        "The RIP database information table."
    ::= { vtssRipStatus 3 }

vtssRipStatusDbEntry OBJECT-TYPE
    SYNTAX      VTSSRipStatusDbEntry
    MAX-ACCESS  not-accessible
    STATUS      current
    DESCRIPTION
        "Each row contains the corresponding information of a routing entry in
         the RIP database."
    INDEX       { vtssRipStatusDbNetworkAddress,
                  vtssRipStatusDbNetworkPrefixSize,
                  vtssRipStatusDbNextHop }
    ::= { vtssRipStatusDbTable 1 }

VTSSRipStatusDbEntry ::= SEQUENCE {
    vtssRipStatusDbNetworkAddress     IpAddress,
    vtssRipStatusDbNetworkPrefixSize  Integer32,
    vtssRipStatusDbNextHop            IpAddress,
    vtssRipStatusDbType               VTSSRipDbProtoType,
    vtssRipStatusDbSubType            VTSSRipDbProtoSubType,
    vtssRipStatusDbMetric             VTSSUnsigned8,
    vtssRipStatusDbExternalMetric     Unsigned32,
    vtssRipStatusDbIsSelfInterface    TruthValue,
    vtssRipStatusDbSourceAddress      IpAddress,
    vtssRipStatusDbTag                Unsigned32,
    vtssRipStatusDbUptime             Unsigned32
}

vtssRipStatusDbNetworkAddress OBJECT-TYPE
    SYNTAX      IpAddress
    MAX-ACCESS  accessible-for-notify
    STATUS      current
    DESCRIPTION
        "The destination IP address of the route."
    ::= { vtssRipStatusDbEntry 1 }

vtssRipStatusDbNetworkPrefixSize OBJECT-TYPE
    SYNTAX      Integer32 (0..32)
    MAX-ACCESS  accessible-for-notify
    STATUS      current
    DESCRIPTION
        "The destination network prefix size of the route."
    ::= { vtssRipStatusDbEntry 2 }

vtssRipStatusDbNextHop OBJECT-TYPE
    SYNTAX      IpAddress
    MAX-ACCESS  accessible-for-notify
    STATUS      current
    DESCRIPTION
        "The first gateway along the route to the destination."
    ::= { vtssRipStatusDbEntry 3 }

vtssRipStatusDbType OBJECT-TYPE
    SYNTAX      VTSSRipDbProtoType
    MAX-ACCESS  read-only
    STATUS      current
    DESCRIPTION
        "The protocol type of the route."
    ::= { vtssRipStatusDbEntry 4 }

vtssRipStatusDbSubType OBJECT-TYPE
    SYNTAX      VTSSRipDbProtoSubType
    MAX-ACCESS  read-only
    STATUS      current
    DESCRIPTION
        "The protocol sub-type of the route."
    ::= { vtssRipStatusDbEntry 5 }

vtssRipStatusDbMetric OBJECT-TYPE
    SYNTAX      VTSSUnsigned8
    MAX-ACCESS  read-only
    STATUS      current
    DESCRIPTION
        "The metric of the route."
    ::= { vtssRipStatusDbEntry 6 }

vtssRipStatusDbExternalMetric OBJECT-TYPE
    SYNTAX      Unsigned32
    MAX-ACCESS  read-only
    STATUS      current
    DESCRIPTION
        "The field is significant only when the route is redistributed from
         other protocol type, for example, OSPF. This indicates the metric value
         from the original redistributed source."
    ::= { vtssRipStatusDbEntry 7 }

vtssRipStatusDbIsSelfInterface OBJECT-TYPE
    SYNTAX      TruthValue
    MAX-ACCESS  read-only
    STATUS      current
    DESCRIPTION
        "This indicates the route is generated from one of the local interfaces
         or not."
    ::= { vtssRipStatusDbEntry 8 }

vtssRipStatusDbSourceAddress OBJECT-TYPE
    SYNTAX      IpAddress
    MAX-ACCESS  read-only
    STATUS      current
    DESCRIPTION
        "The learning source IP address of the route. This indicates the route
         is learned an IP address. The field is significant only when the route
         isn't generated from the local interfaces."
    ::= { vtssRipStatusDbEntry 9 }

vtssRipStatusDbTag OBJECT-TYPE
    SYNTAX      Unsigned32
    MAX-ACCESS  read-only
    STATUS      current
    DESCRIPTION
        "The tag of the route. It is used to provide a method of separating
         'internal' RIP routes, which may have been imported from an EGP
         (Exterior gateway protocol) or another IGP (Interior gateway protocol).
         For example, routes imported from OSPF can have a route tag value which
         the other routing protocols can use to prevent advertising the same
         route back to the original protocol routing domain."
    ::= { vtssRipStatusDbEntry 10 }

vtssRipStatusDbUptime OBJECT-TYPE
    SYNTAX      Unsigned32
    MAX-ACCESS  read-only
    STATUS      current
    DESCRIPTION
        "The time field is significant only when the route is learned from the
         neighbors. When the route destination is reachable (its metric value
         less than 16), the time field means the invalid time of the route. When
         the route destination is unreachable (its metric value great than 16),
         the time field means the garbage-collection time of the route."
    ::= { vtssRipStatusDbEntry 11 }

vtssRipStatusPeerTable OBJECT-TYPE
    SYNTAX      SEQUENCE OF VTSSRipStatusPeerEntry
    MAX-ACCESS  not-accessible
    STATUS      current
    DESCRIPTION
        "This is RIP peer table. It is used to provide the RIP peer information."
    ::= { vtssRipStatus 4 }

vtssRipStatusPeerEntry OBJECT-TYPE
    SYNTAX      VTSSRipStatusPeerEntry
    MAX-ACCESS  not-accessible
    STATUS      current
    DESCRIPTION
        "Each entry in this table represents the information for a RIP peer."
    INDEX       { vtssRipStatusPeerIpv4Addr }
    ::= { vtssRipStatusPeerTable 1 }

VTSSRipStatusPeerEntry ::= SEQUENCE {
    vtssRipStatusPeerIpv4Addr        IpAddress,
    vtssRipStatusPeerVersion         Integer32,
    vtssRipStatusPeerLastUpdateTime  Unsigned32,
    vtssRipStatusPeerRecvBadPackets  Unsigned32,
    vtssRipStatusPeerRecvBadRoutes   Unsigned32
}

vtssRipStatusPeerIpv4Addr OBJECT-TYPE
    SYNTAX      IpAddress
    MAX-ACCESS  accessible-for-notify
    STATUS      current
    DESCRIPTION
        "The IPv4 address."
    ::= { vtssRipStatusPeerEntry 1 }

vtssRipStatusPeerVersion OBJECT-TYPE
    SYNTAX      Integer32
    MAX-ACCESS  read-only
    STATUS      current
    DESCRIPTION
        "The RIP version number in the header of the last RIP packet received
         from the neighbor."
    ::= { vtssRipStatusPeerEntry 2 }

vtssRipStatusPeerLastUpdateTime OBJECT-TYPE
    SYNTAX      Unsigned32
    MAX-ACCESS  read-only
    STATUS      current
    DESCRIPTION
        "The time duration in seconds from the time the last RIP packet received
         from the neighbor to now."
    ::= { vtssRipStatusPeerEntry 3 }

vtssRipStatusPeerRecvBadPackets OBJECT-TYPE
    SYNTAX      Unsigned32
    MAX-ACCESS  read-only
    STATUS      current
    DESCRIPTION
        "The number of RIP response packets from the neighbor discarded as
         invalid."
    ::= { vtssRipStatusPeerEntry 4 }

vtssRipStatusPeerRecvBadRoutes OBJECT-TYPE
    SYNTAX      Unsigned32
    MAX-ACCESS  read-only
    STATUS      current
    DESCRIPTION
        "The number of routes from the neighbor that were ignored because they
         were invalid."
    ::= { vtssRipStatusPeerEntry 5 }

vtssRipControl OBJECT IDENTIFIER
    ::= { vtssRipMibObjects 4 }

vtssRipControlGlobals OBJECT IDENTIFIER
    ::= { vtssRipControl 1 }

vtssRipControlGlobalsReloadProcess OBJECT-TYPE
    SYNTAX      TruthValue
    MAX-ACCESS  read-write
    STATUS      current
    DESCRIPTION
        "Set true to reload RIP process."
    ::= { vtssRipControlGlobals 1 }

vtssRipMibConformance OBJECT IDENTIFIER
    ::= { vtssRipMib 2 }

vtssRipMibCompliances OBJECT IDENTIFIER
    ::= { vtssRipMibConformance 1 }

vtssRipMibGroups OBJECT IDENTIFIER
    ::= { vtssRipMibConformance 2 }

vtssRipCapabilitiesInfoGroup OBJECT-GROUP
    OBJECTS     { vtssRipCapabilitiesMinRedistDefMetric,
                  vtssRipCapabilitiesMaxRedistDefMetric,
                  vtssRipCapabilitiesMinRedistSpecificMetric,
                  vtssRipCapabilitiesMaxRedistSpecificMetric,
                  vtssRipCapabilitiesIsOspfRedistributedSupported,
                  vtssRipCapabilitiesMinTimer,
                  vtssRipCapabilitiesMaxTimer,
                  vtssRipCapabilitiesMinAdminDistance,
                  vtssRipCapabilitiesMaxAdminDistance,
                  vtssRipCapabilitiesSimplePwdLenMax,
                  vtssRipCapabilitiesKeyChainNameLenMax,
                  vtssRipCapabilitiesOffsetListMaxCount,
                  vtssRipCapabilitiesMinOffsetListMetric,
                  vtssRipCapabilitiesMaxOffsetListMetric,
                  vtssRipCapabilitiesNetworkSegmentMaxCount,
                  vtssRipCapabilitiesNeighborMaxCount }
    STATUS      current
    DESCRIPTION
        "A collection of objects."
    ::= { vtssRipMibGroups 1 }

vtssRipConfigRouterTableInfoGroup OBJECT-GROUP
    OBJECTS     { vtssRipConfigRouterRouterMode,
                  vtssRipConfigRouterVersion,
                  vtssRipConfigRouterUpdateTimer,
                  vtssRipConfigRouterInvalidTimer,
                  vtssRipConfigRouterGarbageCollectionTimer,
                  vtssRipConfigRouterRedistDefaultMetric,
                  vtssRipConfigRouterConnectedRedistEnabled,
                  vtssRipConfigRouterConnectedRedistIsSpecificMetric,
                  vtssRipConfigRouterConnectedRedistMetricVal,
                  vtssRipConfigRouterStaticRedistEnabled,
                  vtssRipConfigRouterStaticRedistIsSpecificMetric,
                  vtssRipConfigRouterStaticRedistMetricVal,
                  vtssRipConfigRouterOspfRedistEnabled,
                  vtssRipConfigRouterOspfRedistIsSpecificMetric,
                  vtssRipConfigRouterOspfRedistMetricVal,
                  vtssRipConfigRouterDefaultRouteRedist,
                  vtssRipConfigRouterDefPassiveIntf,
                  vtssRipConfigRouterAdminDistance }
    STATUS      current
    DESCRIPTION
        "A collection of objects."
    ::= { vtssRipMibGroups 2 }

vtssRipConfigNetworkTableInfoGroup OBJECT-GROUP
    OBJECTS     { vtssRipConfigNetworkNetwork,
                  vtssRipConfigNetworkIpSubnetMaskLength,
                  vtssRipConfigNetworkAction }
    STATUS      current
    DESCRIPTION
        "A collection of objects."
    ::= { vtssRipMibGroups 3 }

vtssRipConfigNetworkTableRowEditorInfoGroup OBJECT-GROUP
    OBJECTS     { vtssRipConfigNetworkTableRowEditorNetwork,
                  vtssRipConfigNetworkTableRowEditorIpSubnetMaskLength,
                  vtssRipConfigNetworkTableRowEditorAction }
    STATUS      current
    DESCRIPTION
        "A collection of objects."
    ::= { vtssRipMibGroups 4 }

vtssRipConfigRouterInterfaceTableInfoGroup OBJECT-GROUP
    OBJECTS     { vtssRipConfigRouterInterfaceIfIndex,
                  vtssRipConfigRouterInterfacePassiveInterface }
    STATUS      current
    DESCRIPTION
        "A collection of objects."
    ::= { vtssRipMibGroups 5 }

vtssRipConfigNeighborTableInfoGroup OBJECT-GROUP
    OBJECTS     { vtssRipConfigNeighborIpv4Addr,
                  vtssRipConfigNeighborAction }
    STATUS      current
    DESCRIPTION
        "A collection of objects."
    ::= { vtssRipMibGroups 6 }

vtssRipConfigNeighborTableRowEditorInfoGroup OBJECT-GROUP
    OBJECTS     { vtssRipConfigNeighborTableRowEditorIpv4Addr,
                  vtssRipConfigNeighborTableRowEditorAction }
    STATUS      current
    DESCRIPTION
        "A collection of objects."
    ::= { vtssRipMibGroups 7 }

vtssRipConfigInterfaceTableInfoGroup OBJECT-GROUP
    OBJECTS     { vtssRipConfigInterfaceIfIndex,
                  vtssRipConfigInterfaceSendVersion,
                  vtssRipConfigInterfaceRecvVersion,
                  vtssRipConfigInterfaceSplitHorizonMode,
                  vtssRipConfigInterfaceAuthType,
                  vtssRipConfigInterfaceKeyChainName,
                  vtssRipConfigInterfaceIsEncrypted,
                  vtssRipConfigInterfaceSimplePwd }
    STATUS      current
    DESCRIPTION
        "A collection of objects."
    ::= { vtssRipMibGroups 8 }

vtssRipConfigOffsetListTableInfoGroup OBJECT-GROUP
    OBJECTS     { vtssRipConfigOffsetListIfIndex,
                  vtssRipConfigOffsetListRipOffsetListDirection,
                  vtssRipConfigOffsetListAccessListName,
                  vtssRipConfigOffsetListOffsetMetric,
                  vtssRipConfigOffsetListAction }
    STATUS      current
    DESCRIPTION
        "A collection of objects."
    ::= { vtssRipMibGroups 9 }

vtssRipConfigOffsetListTableRowEditorInfoGroup OBJECT-GROUP
    OBJECTS     { vtssRipConfigOffsetListTableRowEditorIfIndex,
                  vtssRipConfigOffsetListTableRowEditorRipOffsetListDirection,
                  vtssRipConfigOffsetListTableRowEditorAccessListName,
                  vtssRipConfigOffsetListTableRowEditorOffsetMetric,
                  vtssRipConfigOffsetListTableRowEditorAction }
    STATUS      current
    DESCRIPTION
        "A collection of objects."
    ::= { vtssRipMibGroups 10 }

vtssRipStatusGeneralTableInfoGroup OBJECT-GROUP
    OBJECTS     { vtssRipStatusGeneralRouterModeIsEnabled,
                  vtssRipStatusGeneralVersion,
                  vtssRipStatusGeneralUpdateTimer,
                  vtssRipStatusGeneralInvalidTimer,
                  vtssRipStatusGeneralGarbageCollectionTimer,
                  vtssRipStatusGeneralNextUpdateTime,
                  vtssRipStatusGeneralRedistDefMetric,
                  vtssRipStatusGeneralIsRedistributeConnected,
                  vtssRipStatusGeneralIsRedistributeStatic,
                  vtssRipStatusGeneralIsRedistributeOSPF,
                  vtssRipStatusGeneralAdminDistance }
    STATUS      current
    DESCRIPTION
        "A collection of objects."
    ::= { vtssRipMibGroups 11 }

vtssRipStatusInterfaceTableInfoGroup OBJECT-GROUP
    OBJECTS     { vtssRipStatusInterfaceIfIndex,
                  vtssRipStatusInterfaceSendVersion,
                  vtssRipStatusInterfaceRecvVersion,
                  vtssRipStatusInterfaceTriggeredUpdate,
                  vtssRipStatusInterfaceIsPassiveInterface,
                  vtssRipStatusInterfaceAuthType,
                  vtssRipStatusInterfaceKeyChainName }
    STATUS      current
    DESCRIPTION
        "A collection of objects."
    ::= { vtssRipMibGroups 12 }

vtssRipStatusDbTableInfoGroup OBJECT-GROUP
    OBJECTS     { vtssRipStatusDbNetworkAddress,
                  vtssRipStatusDbNetworkPrefixSize,
                  vtssRipStatusDbNextHop, vtssRipStatusDbType,
                  vtssRipStatusDbSubType, vtssRipStatusDbMetric,
                  vtssRipStatusDbExternalMetric,
                  vtssRipStatusDbIsSelfInterface,
                  vtssRipStatusDbSourceAddress, vtssRipStatusDbTag,
                  vtssRipStatusDbUptime }
    STATUS      current
    DESCRIPTION
        "A collection of objects."
    ::= { vtssRipMibGroups 13 }

vtssRipStatusPeerTableInfoGroup OBJECT-GROUP
    OBJECTS     { vtssRipStatusPeerIpv4Addr, vtssRipStatusPeerVersion,
                  vtssRipStatusPeerLastUpdateTime,
                  vtssRipStatusPeerRecvBadPackets,
                  vtssRipStatusPeerRecvBadRoutes }
    STATUS      current
    DESCRIPTION
        "A collection of objects."
    ::= { vtssRipMibGroups 14 }

vtssRipControlGlobalsInfoGroup OBJECT-GROUP
    OBJECTS     { vtssRipControlGlobalsReloadProcess }
    STATUS      current
    DESCRIPTION
        "A collection of objects."
    ::= { vtssRipMibGroups 15 }

vtssRipMibCompliance MODULE-COMPLIANCE
    STATUS      current
    DESCRIPTION
        "The compliance statement for the implementation."

    MODULE      -- this module

    MANDATORY-GROUPS { vtssRipCapabilitiesInfoGroup,
                       vtssRipConfigRouterTableInfoGroup,
                       vtssRipConfigNetworkTableInfoGroup,
                       vtssRipConfigNetworkTableRowEditorInfoGroup,
                       vtssRipConfigRouterInterfaceTableInfoGroup,
                       vtssRipConfigNeighborTableInfoGroup,
                       vtssRipConfigNeighborTableRowEditorInfoGroup,
                       vtssRipConfigInterfaceTableInfoGroup,
                       vtssRipConfigOffsetListTableInfoGroup,
                       vtssRipConfigOffsetListTableRowEditorInfoGroup,
                       vtssRipStatusGeneralTableInfoGroup,
                       vtssRipStatusInterfaceTableInfoGroup,
                       vtssRipStatusDbTableInfoGroup,
                       vtssRipStatusPeerTableInfoGroup,
                       vtssRipControlGlobalsInfoGroup }

    ::= { vtssRipMibCompliances 1 }

END
