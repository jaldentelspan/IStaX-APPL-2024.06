-- *****************************************************************
-- MVRP-MIB:  Microsemi ENT private MIB
-- ****************************************************************

VTSS-MVRP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Counter64 FROM SNMPv2-SMI
    MacAddress FROM SNMPv2-TC
    TruthValue FROM SNMPv2-TC
    VTSSInterfaceIndex FROM VTSS-TC
    VTSSVlanListQuarter FROM VTSS-TC
    ;

vtssMvrpMib MODULE-IDENTITY
    LAST-UPDATED "201510190000Z"
    ORGANIZATION
        "Microsemi Corporation"
    CONTACT-INFO
        "Application support: http://www.microchip.com/support"
    DESCRIPTION
        "Private MVRP MIB."
    REVISION    "201510190000Z"
    DESCRIPTION
        "Initial version"
    ::= { vtssSwitchMgmt 87 }


vtssMvrpMibObjects OBJECT IDENTIFIER
    ::= { vtssMvrpMib 1 }

vtssMvrpConfig OBJECT IDENTIFIER
    ::= { vtssMvrpMibObjects 2 }

vtssMvrpConfigGlobals OBJECT IDENTIFIER
    ::= { vtssMvrpConfig 1 }

vtssMvrpConfigGlobalsGlobalState OBJECT-TYPE
    SYNTAX      TruthValue
    MAX-ACCESS  read-write
    STATUS      current
    DESCRIPTION
        "Global state of MVRP. TRUE - enable MVRP, FALSE - disable MVRP."
    ::= { vtssMvrpConfigGlobals 1 }

vtssMvrpConfigGlobalsManagedVlans0KTo1K OBJECT-TYPE
    SYNTAX      VTSSVlanListQuarter
    MAX-ACCESS  read-write
    STATUS      current
    DESCRIPTION
        "First quarter of bit-array indicating the MVRP-managed VLANs."
    ::= { vtssMvrpConfigGlobals 2 }

vtssMvrpConfigGlobalsManagedVlans1KTo2K OBJECT-TYPE
    SYNTAX      VTSSVlanListQuarter
    MAX-ACCESS  read-write
    STATUS      current
    DESCRIPTION
        "Second quarter of bit-array indicating the MVRP-managed VLANs."
    ::= { vtssMvrpConfigGlobals 3 }

vtssMvrpConfigGlobalsManagedVlans2KTo3K OBJECT-TYPE
    SYNTAX      VTSSVlanListQuarter
    MAX-ACCESS  read-write
    STATUS      current
    DESCRIPTION
        "Third quarter of bit-array indicating the MVRP-managed VLANs."
    ::= { vtssMvrpConfigGlobals 4 }

vtssMvrpConfigGlobalsManagedVlans3KTo4K OBJECT-TYPE
    SYNTAX      VTSSVlanListQuarter
    MAX-ACCESS  read-write
    STATUS      current
    DESCRIPTION
        "Last quarter of bit-array indicating the MVRP-managed VLANs."
    ::= { vtssMvrpConfigGlobals 5 }

vtssMvrpConfigInterface OBJECT IDENTIFIER
    ::= { vtssMvrpConfig 2 }

vtssMvrpConfigInterfaceTable OBJECT-TYPE
    SYNTAX      SEQUENCE OF VTSSMvrpConfigInterfaceEntry
    MAX-ACCESS  not-accessible
    STATUS      current
    DESCRIPTION
        "This is the MVRP interface configuration table. The number of
         interfaces is the total number of ports available on the switch/stack.
         Each one of these interfaces can be set to either MVRP enabled or MVRP
         disabled."
    ::= { vtssMvrpConfigInterface 1 }

vtssMvrpConfigInterfaceEntry OBJECT-TYPE
    SYNTAX      VTSSMvrpConfigInterfaceEntry
    MAX-ACCESS  not-accessible
    STATUS      current
    DESCRIPTION
        "Entries in this table represent switch interfaces and their
         corresponding MVRP state"
    INDEX       { vtssMvrpConfigInterfaceIfIndex }
    ::= { vtssMvrpConfigInterfaceTable 1 }

VTSSMvrpConfigInterfaceEntry ::= SEQUENCE {
    vtssMvrpConfigInterfaceIfIndex    VTSSInterfaceIndex,
    vtssMvrpConfigInterfacePortState  TruthValue
}

vtssMvrpConfigInterfaceIfIndex OBJECT-TYPE
    SYNTAX      VTSSInterfaceIndex
    MAX-ACCESS  accessible-for-notify
    STATUS      current
    DESCRIPTION
        "Interface index number."
    ::= { vtssMvrpConfigInterfaceEntry 1 }

vtssMvrpConfigInterfacePortState OBJECT-TYPE
    SYNTAX      TruthValue
    MAX-ACCESS  read-write
    STATUS      current
    DESCRIPTION
        "Per-interface state of MVRP. TRUE - enable MVRP on the interface, FALSE
         - disable MVRP on the interface."
    ::= { vtssMvrpConfigInterfaceEntry 2 }

vtssMvrpStatus OBJECT IDENTIFIER
    ::= { vtssMvrpMibObjects 3 }

vtssMvrpStatusInterfaceTable OBJECT-TYPE
    SYNTAX      SEQUENCE OF VTSSMvrpStatusInterfaceEntry
    MAX-ACCESS  not-accessible
    STATUS      current
    DESCRIPTION
        "This is the MVRP interface statistics table. The number of interfaces
         is the total number of ports available on the switch/stack. "
    ::= { vtssMvrpStatus 1 }

vtssMvrpStatusInterfaceEntry OBJECT-TYPE
    SYNTAX      VTSSMvrpStatusInterfaceEntry
    MAX-ACCESS  not-accessible
    STATUS      current
    DESCRIPTION
        "Each entry has a counter and a MAC address."
    INDEX       { vtssMvrpStatusInterfaceIfIndex }
    ::= { vtssMvrpStatusInterfaceTable 1 }

VTSSMvrpStatusInterfaceEntry ::= SEQUENCE {
    vtssMvrpStatusInterfaceIfIndex              VTSSInterfaceIndex,
    vtssMvrpStatusInterfaceFailedRegistrations  Counter64,
    vtssMvrpStatusInterfaceLastPduOrigin        MacAddress
}

vtssMvrpStatusInterfaceIfIndex OBJECT-TYPE
    SYNTAX      VTSSInterfaceIndex
    MAX-ACCESS  accessible-for-notify
    STATUS      current
    DESCRIPTION
        "Interface index number."
    ::= { vtssMvrpStatusInterfaceEntry 1 }

vtssMvrpStatusInterfaceFailedRegistrations OBJECT-TYPE
    SYNTAX      Counter64
    MAX-ACCESS  read-only
    STATUS      current
    DESCRIPTION
        "Number of failed VLAN registrations."
    ::= { vtssMvrpStatusInterfaceEntry 2 }

vtssMvrpStatusInterfaceLastPduOrigin OBJECT-TYPE
    SYNTAX      MacAddress
    MAX-ACCESS  read-only
    STATUS      current
    DESCRIPTION
        "Source MAC Address of the last MVRPDU received."
    ::= { vtssMvrpStatusInterfaceEntry 3 }

vtssMvrpMibConformance OBJECT IDENTIFIER
    ::= { vtssMvrpMib 2 }

vtssMvrpMibCompliances OBJECT IDENTIFIER
    ::= { vtssMvrpMibConformance 1 }

vtssMvrpMibGroups OBJECT IDENTIFIER
    ::= { vtssMvrpMibConformance 2 }

vtssMvrpConfigGlobalsInfoGroup OBJECT-GROUP
    OBJECTS     { vtssMvrpConfigGlobalsGlobalState,
                  vtssMvrpConfigGlobalsManagedVlans0KTo1K,
                  vtssMvrpConfigGlobalsManagedVlans1KTo2K,
                  vtssMvrpConfigGlobalsManagedVlans2KTo3K,
                  vtssMvrpConfigGlobalsManagedVlans3KTo4K }
    STATUS      current
    DESCRIPTION
        "A collection of objects."
    ::= { vtssMvrpMibGroups 1 }

vtssMvrpConfigInterfaceTableInfoGroup OBJECT-GROUP
    OBJECTS     { vtssMvrpConfigInterfaceIfIndex,
                  vtssMvrpConfigInterfacePortState }
    STATUS      current
    DESCRIPTION
        "A collection of objects."
    ::= { vtssMvrpMibGroups 2 }

vtssMvrpStatusInterfaceTableInfoGroup OBJECT-GROUP
    OBJECTS     { vtssMvrpStatusInterfaceIfIndex,
                  vtssMvrpStatusInterfaceFailedRegistrations,
                  vtssMvrpStatusInterfaceLastPduOrigin }
    STATUS      current
    DESCRIPTION
        "A collection of objects."
    ::= { vtssMvrpMibGroups 3 }

vtssMvrpMibCompliance MODULE-COMPLIANCE
    STATUS      current
    DESCRIPTION
        "The compliance statement for the implementation."

    MODULE      -- this module

    MANDATORY-GROUPS { vtssMvrpConfigGlobalsInfoGroup,
                       vtssMvrpConfigInterfaceTableInfoGroup,
                       vtssMvrpStatusInterfaceTableInfoGroup }

    ::= { vtssMvrpMibCompliances 1 }

END
