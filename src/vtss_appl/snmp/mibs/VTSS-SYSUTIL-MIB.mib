-- *****************************************************************
-- SYSUTIL-MIB:  Microsemi ENT private MIB
-- ****************************************************************

VTSS-SYSUTIL-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    Unsigned32 FROM SNMPv2-SMI
    MacAddress FROM SNMPv2-TC
    TruthValue FROM SNMPv2-TC
    VTSSDisplayString FROM VTSS-TC
    ;

vtssSysutilMib MODULE-IDENTITY
    LAST-UPDATED "201602170000Z"
    ORGANIZATION
        "Microsemi Corporation"
    CONTACT-INFO
        "Application support: http://www.microchip.com/support"
    DESCRIPTION
        "This is a private version of SysUtil"
    REVISION    "201602170000Z"
    DESCRIPTION
        "Add system temperature monitor"
    REVISION    "201602150000Z"
    DESCRIPTION
        "Add board serial and type to board info"
    REVISION    "201511020000Z"
    DESCRIPTION
        "Add system time config"
    REVISION    "201510300000Z"
    DESCRIPTION
        "Add board info"
    REVISION    "201510200000Z"
    DESCRIPTION
        "Add system config info"
    REVISION    "201510150000Z"
    DESCRIPTION
        "Add system uptime status"
    REVISION    "201411110000Z"
    DESCRIPTION
        "Add system LED status"
    REVISION    "201410100000Z"
    DESCRIPTION
        "Editorial changes"
    REVISION    "201407010000Z"
    DESCRIPTION
        "Initial version"
    ::= { vtssSwitchMgmt 24 }


VTSSSysutilPowerSupplyStateType ::= TEXTUAL-CONVENTION
    STATUS      current
    DESCRIPTION
        "This enumeration defines the type of power supply state."
    SYNTAX      INTEGER { active(0), standby(1), notPresent(2) }

VTSSSysutilRebootType ::= TEXTUAL-CONVENTION
    STATUS      current
    DESCRIPTION
        "This enumeration defines the type of reboot."
    SYNTAX      INTEGER { noReboot(0), coldReboot(1), warmReboot(2) }

VTSSSysutilSystemLedClearType ::= TEXTUAL-CONVENTION
    STATUS      current
    DESCRIPTION
        "This enumeration defines the type of system LED status clearing."
    SYNTAX      INTEGER { all(0), fatal(1), software(2), post(3),
                          ztp(4), stackFwChk(5) }

VTSSSysutilTemperatureMonitorSensorType ::= TEXTUAL-CONVENTION
    STATUS      current
    DESCRIPTION
        "This enumeration defines the type of temperature sensors."
    SYNTAX      INTEGER { board(0), junction(1) }

vtssSysutilMibObjects OBJECT IDENTIFIER
    ::= { vtssSysutilMib 1 }

vtssSysutilCapabilities OBJECT IDENTIFIER
    ::= { vtssSysutilMibObjects 1 }

vtssSysutilCapabilitiesWarmRebootSupported OBJECT-TYPE
    SYNTAX      TruthValue
    MAX-ACCESS  read-only
    STATUS      current
    DESCRIPTION
        "Indicate if warm restart is supported or not. true means it is
         supported. false means it is not supported."
    ::= { vtssSysutilCapabilities 1 }

vtssSysutilCapabilitiesPostSupported OBJECT-TYPE
    SYNTAX      TruthValue
    MAX-ACCESS  read-only
    STATUS      current
    DESCRIPTION
        "Indicate if POST(Power On Self Test) is supported or not. true(1) means
         it is supported. false(2) means it is not supported."
    ::= { vtssSysutilCapabilities 2 }

vtssSysutilCapabilitiesZtpSupported OBJECT-TYPE
    SYNTAX      TruthValue
    MAX-ACCESS  read-only
    STATUS      current
    DESCRIPTION
        "Indicate if ZTP(Zero Touch Provisioning) is supported or not. true(1)
         means it is supported. false(2) means it is not supported."
    ::= { vtssSysutilCapabilities 3 }

vtssSysutilCapabilitiesStackFwChkSupported OBJECT-TYPE
    SYNTAX      TruthValue
    MAX-ACCESS  read-only
    STATUS      current
    DESCRIPTION
        "Indicate if stack firmware version check is supported or not. true(1)
         means it is supported. false(2) means it is not supported."
    ::= { vtssSysutilCapabilities 4 }

vtssSysutilConfig OBJECT IDENTIFIER
    ::= { vtssSysutilMibObjects 2 }

vtssSysutilConfigSystemInfo OBJECT IDENTIFIER
    ::= { vtssSysutilConfig 1 }

vtssSysutilConfigSystemInfoHostname OBJECT-TYPE
    SYNTAX      VTSSDisplayString (SIZE(0..255))
    MAX-ACCESS  read-write
    STATUS      current
    DESCRIPTION
        "Hostname"
    ::= { vtssSysutilConfigSystemInfo 1 }

vtssSysutilConfigSystemInfoContact OBJECT-TYPE
    SYNTAX      VTSSDisplayString (SIZE(0..255))
    MAX-ACCESS  read-write
    STATUS      current
    DESCRIPTION
        "Contact name."
    ::= { vtssSysutilConfigSystemInfo 2 }

vtssSysutilConfigSystemInfoLocation OBJECT-TYPE
    SYNTAX      VTSSDisplayString (SIZE(0..255))
    MAX-ACCESS  read-write
    STATUS      current
    DESCRIPTION
        "Location."
    ::= { vtssSysutilConfigSystemInfo 3 }

vtssSysutilConfigSystemTime OBJECT IDENTIFIER
    ::= { vtssSysutilConfig 2 }

vtssSysutilConfigSystemTimeSystemCurTime OBJECT-TYPE
    SYNTAX      VTSSDisplayString (SIZE(0..63))
    MAX-ACCESS  read-write
    STATUS      current
    DESCRIPTION
        "Current system time"
    ::= { vtssSysutilConfigSystemTime 1 }

vtssSysutilConfigSystemTimeSystemCurTimeFormat OBJECT-TYPE
    SYNTAX      VTSSDisplayString (SIZE(0..63))
    MAX-ACCESS  read-write
    STATUS      current
    DESCRIPTION
        "Format for setting up current system time"
    ::= { vtssSysutilConfigSystemTime 2 }

vtssSysutilConfigTemperatureMonitorTable OBJECT-TYPE
    SYNTAX      SEQUENCE OF VTSSSysutilConfigTemperatureMonitorEntry
    MAX-ACCESS  not-accessible
    STATUS      current
    DESCRIPTION
        "Table of temperature monitor config."
    ::= { vtssSysutilConfig 3 }

vtssSysutilConfigTemperatureMonitorEntry OBJECT-TYPE
    SYNTAX      VTSSSysutilConfigTemperatureMonitorEntry
    MAX-ACCESS  not-accessible
    STATUS      current
    DESCRIPTION
        "Each row set the sensor config."
    INDEX       { vtssSysutilConfigTemperatureMonitorSensorId }
    ::= { vtssSysutilConfigTemperatureMonitorTable 1 }

VTSSSysutilConfigTemperatureMonitorEntry ::= SEQUENCE {
    vtssSysutilConfigTemperatureMonitorSensorId           VTSSSysutilTemperatureMonitorSensorType,
    vtssSysutilConfigTemperatureMonitorLowThreshold       Integer32,
    vtssSysutilConfigTemperatureMonitorHighThreshold      Integer32,
    vtssSysutilConfigTemperatureMonitorCriticalThreshold  Integer32,
    vtssSysutilConfigTemperatureMonitorHysteresis         Integer32
}

vtssSysutilConfigTemperatureMonitorSensorId OBJECT-TYPE
    SYNTAX      VTSSSysutilTemperatureMonitorSensorType
    MAX-ACCESS  accessible-for-notify
    STATUS      current
    DESCRIPTION
        "The identification of sensor for tempeature monitor."
    ::= { vtssSysutilConfigTemperatureMonitorEntry 1 }

vtssSysutilConfigTemperatureMonitorLowThreshold OBJECT-TYPE
    SYNTAX      Integer32 (-40..125)
    MAX-ACCESS  read-write
    STATUS      current
    DESCRIPTION
        "The low threshold of temperature monior."
    ::= { vtssSysutilConfigTemperatureMonitorEntry 2 }

vtssSysutilConfigTemperatureMonitorHighThreshold OBJECT-TYPE
    SYNTAX      Integer32 (-40..125)
    MAX-ACCESS  read-write
    STATUS      current
    DESCRIPTION
        "The high threshold of temperature monior."
    ::= { vtssSysutilConfigTemperatureMonitorEntry 3 }

vtssSysutilConfigTemperatureMonitorCriticalThreshold OBJECT-TYPE
    SYNTAX      Integer32 (90..150)
    MAX-ACCESS  read-write
    STATUS      current
    DESCRIPTION
        "The critical threshold of temperature monior."
    ::= { vtssSysutilConfigTemperatureMonitorEntry 4 }

vtssSysutilConfigTemperatureMonitorHysteresis OBJECT-TYPE
    SYNTAX      Integer32 (1..5)
    MAX-ACCESS  read-write
    STATUS      current
    DESCRIPTION
        "The value of hysteresis for temperature check."
    ::= { vtssSysutilConfigTemperatureMonitorEntry 5 }

vtssSysutilStatus OBJECT IDENTIFIER
    ::= { vtssSysutilMibObjects 3 }

vtssSysutilStatusCpuLoad OBJECT IDENTIFIER
    ::= { vtssSysutilStatus 1 }

vtssSysutilStatusCpuLoadAverage100msec OBJECT-TYPE
    SYNTAX      Unsigned32
    MAX-ACCESS  read-only
    STATUS      current
    DESCRIPTION
        "Average CPU load (%) in 100 milli-seconds."
    ::= { vtssSysutilStatusCpuLoad 1 }

vtssSysutilStatusCpuLoadAverage1sec OBJECT-TYPE
    SYNTAX      Unsigned32
    MAX-ACCESS  read-only
    STATUS      current
    DESCRIPTION
        "Average CPU load (%) in 1 second."
    ::= { vtssSysutilStatusCpuLoad 2 }

vtssSysutilStatusCpuLoadAverage10sec OBJECT-TYPE
    SYNTAX      Unsigned32
    MAX-ACCESS  read-only
    STATUS      current
    DESCRIPTION
        "Average CPU load (%) in 10 seconds."
    ::= { vtssSysutilStatusCpuLoad 3 }

vtssSysutilStatusPowerSupplyTable OBJECT-TYPE
    SYNTAX      SEQUENCE OF VTSSSysutilStatusPowerSupplyEntry
    MAX-ACCESS  not-accessible
    STATUS      current
    DESCRIPTION
        "Table of power supply status."
    ::= { vtssSysutilStatus 2 }

vtssSysutilStatusPowerSupplyEntry OBJECT-TYPE
    SYNTAX      VTSSSysutilStatusPowerSupplyEntry
    MAX-ACCESS  not-accessible
    STATUS      current
    DESCRIPTION
        "Each row contains the power supply status."
    INDEX       { vtssSysutilStatusPowerSupplySwitchId,
                  vtssSysutilStatusPowerSupplyPsuId }
    ::= { vtssSysutilStatusPowerSupplyTable 1 }

VTSSSysutilStatusPowerSupplyEntry ::= SEQUENCE {
    vtssSysutilStatusPowerSupplySwitchId     Integer32,
    vtssSysutilStatusPowerSupplyPsuId        Integer32,
    vtssSysutilStatusPowerSupplyState        VTSSSysutilPowerSupplyStateType,
    vtssSysutilStatusPowerSupplyDescription  VTSSDisplayString
}

vtssSysutilStatusPowerSupplySwitchId OBJECT-TYPE
    SYNTAX      Integer32 (1..16)
    MAX-ACCESS  accessible-for-notify
    STATUS      current
    DESCRIPTION
        "The identification of switch."
    ::= { vtssSysutilStatusPowerSupplyEntry 1 }

vtssSysutilStatusPowerSupplyPsuId OBJECT-TYPE
    SYNTAX      Integer32 (1..2)
    MAX-ACCESS  accessible-for-notify
    STATUS      current
    DESCRIPTION
        "The identification of power supply."
    ::= { vtssSysutilStatusPowerSupplyEntry 2 }

vtssSysutilStatusPowerSupplyState OBJECT-TYPE
    SYNTAX      VTSSSysutilPowerSupplyStateType
    MAX-ACCESS  read-only
    STATUS      current
    DESCRIPTION
        "The state of power supply."
    ::= { vtssSysutilStatusPowerSupplyEntry 3 }

vtssSysutilStatusPowerSupplyDescription OBJECT-TYPE
    SYNTAX      VTSSDisplayString (SIZE(0..30))
    MAX-ACCESS  read-only
    STATUS      current
    DESCRIPTION
        "The description of power supply."
    ::= { vtssSysutilStatusPowerSupplyEntry 4 }

vtssSysutilStatusSystemLedTable OBJECT-TYPE
    SYNTAX      SEQUENCE OF VTSSSysutilStatusSystemLedEntry
    MAX-ACCESS  not-accessible
    STATUS      current
    DESCRIPTION
        "Table of system LED status."
    ::= { vtssSysutilStatus 3 }

vtssSysutilStatusSystemLedEntry OBJECT-TYPE
    SYNTAX      VTSSSysutilStatusSystemLedEntry
    MAX-ACCESS  not-accessible
    STATUS      current
    DESCRIPTION
        "Each row contains the system LED status."
    INDEX       { vtssSysutilStatusSystemLedSwitchId }
    ::= { vtssSysutilStatusSystemLedTable 1 }

VTSSSysutilStatusSystemLedEntry ::= SEQUENCE {
    vtssSysutilStatusSystemLedSwitchId     Integer32,
    vtssSysutilStatusSystemLedDescription  VTSSDisplayString
}

vtssSysutilStatusSystemLedSwitchId OBJECT-TYPE
    SYNTAX      Integer32 (1..16)
    MAX-ACCESS  accessible-for-notify
    STATUS      current
    DESCRIPTION
        "The identification of switch."
    ::= { vtssSysutilStatusSystemLedEntry 1 }

vtssSysutilStatusSystemLedDescription OBJECT-TYPE
    SYNTAX      VTSSDisplayString (SIZE(0..127))
    MAX-ACCESS  read-only
    STATUS      current
    DESCRIPTION
        "The description of system LED status."
    ::= { vtssSysutilStatusSystemLedEntry 2 }

vtssSysutilStatusSystemUptime OBJECT IDENTIFIER
    ::= { vtssSysutilStatus 4 }

vtssSysutilStatusSystemUptimeSystemUptime OBJECT-TYPE
    SYNTAX      VTSSDisplayString (SIZE(0..10))
    MAX-ACCESS  read-only
    STATUS      current
    DESCRIPTION
        "The time since the DUT is Up."
    ::= { vtssSysutilStatusSystemUptime 1 }

vtssSysutilStatusBoardInfo OBJECT IDENTIFIER
    ::= { vtssSysutilStatus 5 }

vtssSysutilStatusBoardInfoBoardMacAddress OBJECT-TYPE
    SYNTAX      MacAddress
    MAX-ACCESS  read-only
    STATUS      current
    DESCRIPTION
        "Board Mac Address"
    ::= { vtssSysutilStatusBoardInfo 1 }

vtssSysutilStatusBoardInfoBoardID OBJECT-TYPE
    SYNTAX      Unsigned32
    MAX-ACCESS  read-only
    STATUS      current
    DESCRIPTION
        "Board ID"
    ::= { vtssSysutilStatusBoardInfo 2 }

vtssSysutilStatusBoardInfoBoardSerial OBJECT-TYPE
    SYNTAX      VTSSDisplayString (SIZE(0..63))
    MAX-ACCESS  read-only
    STATUS      current
    DESCRIPTION
        "Board ID"
    ::= { vtssSysutilStatusBoardInfo 3 }

vtssSysutilStatusBoardInfoBoardType OBJECT-TYPE
    SYNTAX      VTSSDisplayString (SIZE(0..63))
    MAX-ACCESS  read-only
    STATUS      current
    DESCRIPTION
        "Board ID"
    ::= { vtssSysutilStatusBoardInfo 4 }

vtssSysutilStatusTemperatureMonitorTable OBJECT-TYPE
    SYNTAX      SEQUENCE OF VTSSSysutilStatusTemperatureMonitorEntry
    MAX-ACCESS  not-accessible
    STATUS      current
    DESCRIPTION
        "Table of temperature monitor status."
    ::= { vtssSysutilStatus 6 }

vtssSysutilStatusTemperatureMonitorEntry OBJECT-TYPE
    SYNTAX      VTSSSysutilStatusTemperatureMonitorEntry
    MAX-ACCESS  not-accessible
    STATUS      current
    DESCRIPTION
        "Each row contains the sensor status."
    INDEX       { vtssSysutilStatusTemperatureMonitorSensorId }
    ::= { vtssSysutilStatusTemperatureMonitorTable 1 }

VTSSSysutilStatusTemperatureMonitorEntry ::= SEQUENCE {
    vtssSysutilStatusTemperatureMonitorSensorId       VTSSSysutilTemperatureMonitorSensorType,
    vtssSysutilStatusTemperatureMonitorLowAlarm       TruthValue,
    vtssSysutilStatusTemperatureMonitorHighAlarm      TruthValue,
    vtssSysutilStatusTemperatureMonitorCriticalAlarm  TruthValue,
    vtssSysutilStatusTemperatureMonitorTemperature    Integer32
}

vtssSysutilStatusTemperatureMonitorSensorId OBJECT-TYPE
    SYNTAX      VTSSSysutilTemperatureMonitorSensorType
    MAX-ACCESS  accessible-for-notify
    STATUS      current
    DESCRIPTION
        "The identification of sensor for tempeature monitor."
    ::= { vtssSysutilStatusTemperatureMonitorEntry 1 }

vtssSysutilStatusTemperatureMonitorLowAlarm OBJECT-TYPE
    SYNTAX      TruthValue
    MAX-ACCESS  read-only
    STATUS      current
    DESCRIPTION
        "The alarm flag of temperature low status."
    ::= { vtssSysutilStatusTemperatureMonitorEntry 2 }

vtssSysutilStatusTemperatureMonitorHighAlarm OBJECT-TYPE
    SYNTAX      TruthValue
    MAX-ACCESS  read-only
    STATUS      current
    DESCRIPTION
        "The alarm flag of temperature high status."
    ::= { vtssSysutilStatusTemperatureMonitorEntry 3 }

vtssSysutilStatusTemperatureMonitorCriticalAlarm OBJECT-TYPE
    SYNTAX      TruthValue
    MAX-ACCESS  read-only
    STATUS      current
    DESCRIPTION
        "The alarm flag of temperature critical status."
    ::= { vtssSysutilStatusTemperatureMonitorEntry 4 }

vtssSysutilStatusTemperatureMonitorTemperature OBJECT-TYPE
    SYNTAX      Integer32
    MAX-ACCESS  read-only
    STATUS      current
    DESCRIPTION
        "Current temperature."
    ::= { vtssSysutilStatusTemperatureMonitorEntry 5 }

vtssSysutilControl OBJECT IDENTIFIER
    ::= { vtssSysutilMibObjects 4 }

vtssSysutilControlRebootTable OBJECT-TYPE
    SYNTAX      SEQUENCE OF VTSSSysutilControlRebootEntry
    MAX-ACCESS  not-accessible
    STATUS      current
    DESCRIPTION
        "This is a table to reboot a swicth"
    ::= { vtssSysutilControl 1 }

vtssSysutilControlRebootEntry OBJECT-TYPE
    SYNTAX      VTSSSysutilControlRebootEntry
    MAX-ACCESS  not-accessible
    STATUS      current
    DESCRIPTION
        "Each switch has a set of parameters"
    INDEX       { vtssSysutilControlRebootSwitchId }
    ::= { vtssSysutilControlRebootTable 1 }

VTSSSysutilControlRebootEntry ::= SEQUENCE {
    vtssSysutilControlRebootSwitchId  Integer32,
    vtssSysutilControlRebootType      VTSSSysutilRebootType
}

vtssSysutilControlRebootSwitchId OBJECT-TYPE
    SYNTAX      Integer32 (1..16)
    MAX-ACCESS  accessible-for-notify
    STATUS      current
    DESCRIPTION
        "The identification of switch."
    ::= { vtssSysutilControlRebootEntry 1 }

vtssSysutilControlRebootType OBJECT-TYPE
    SYNTAX      VTSSSysutilRebootType
    MAX-ACCESS  read-write
    STATUS      current
    DESCRIPTION
        "Type of reboot. noReboot(0) does not reboot. coldReboot(1) is to do
         cold reboot. warmReboot(2) is to do warm reboot, but this is optional.
         The OID of vtssSysutilCapabilitiesWarmRebootSupported tells if warm
         reboot is supported or not."
    ::= { vtssSysutilControlRebootEntry 2 }

vtssSysutilControlSystemLedTable OBJECT-TYPE
    SYNTAX      SEQUENCE OF VTSSSysutilControlSystemLedEntry
    MAX-ACCESS  not-accessible
    STATUS      current
    DESCRIPTION
        "This is a table to clear the system LED error status"
    ::= { vtssSysutilControl 2 }

vtssSysutilControlSystemLedEntry OBJECT-TYPE
    SYNTAX      VTSSSysutilControlSystemLedEntry
    MAX-ACCESS  not-accessible
    STATUS      current
    DESCRIPTION
        "Each switch has a set of parameters"
    INDEX       { vtssSysutilControlSystemLedSwitchId }
    ::= { vtssSysutilControlSystemLedTable 1 }

VTSSSysutilControlSystemLedEntry ::= SEQUENCE {
    vtssSysutilControlSystemLedSwitchId     Integer32,
    vtssSysutilControlSystemLedClearStatus  VTSSSysutilSystemLedClearType
}

vtssSysutilControlSystemLedSwitchId OBJECT-TYPE
    SYNTAX      Integer32 (1..16)
    MAX-ACCESS  accessible-for-notify
    STATUS      current
    DESCRIPTION
        "The identification of switch."
    ::= { vtssSysutilControlSystemLedEntry 1 }

vtssSysutilControlSystemLedClearStatus OBJECT-TYPE
    SYNTAX      VTSSSysutilSystemLedClearType
    MAX-ACCESS  read-write
    STATUS      current
    DESCRIPTION
        "Type of system LED status clearing.all(0) is used to clear all error
         status of the system LED and back to normal indication. fatal(1) is
         used to clear fatal error status of the system LED. software(2) is used
         to clear generic software error status of the system LED. post(3) is
         used to clear POST(Power On Self Test) error status of the system LED.
         ztp(4) is used to clear ZTP(Zero Touch Provisioning) error status of
         the system LED. stackFwChk(5) is used to clear stack firmware version
         check error status of the system LED."
    ::= { vtssSysutilControlSystemLedEntry 2 }

vtssSysutilMibConformance OBJECT IDENTIFIER
    ::= { vtssSysutilMib 2 }

vtssSysutilMibCompliances OBJECT IDENTIFIER
    ::= { vtssSysutilMibConformance 1 }

vtssSysutilMibGroups OBJECT IDENTIFIER
    ::= { vtssSysutilMibConformance 2 }

vtssSysutilCapabilitiesInfoGroup OBJECT-GROUP
    OBJECTS     { vtssSysutilCapabilitiesWarmRebootSupported,
                  vtssSysutilCapabilitiesPostSupported,
                  vtssSysutilCapabilitiesZtpSupported,
                  vtssSysutilCapabilitiesStackFwChkSupported }
    STATUS      current
    DESCRIPTION
        "A collection of objects."
    ::= { vtssSysutilMibGroups 1 }

vtssSysutilConfigSystemInfoInfoGroup OBJECT-GROUP
    OBJECTS     { vtssSysutilConfigSystemInfoHostname,
                  vtssSysutilConfigSystemInfoContact,
                  vtssSysutilConfigSystemInfoLocation }
    STATUS      current
    DESCRIPTION
        "A collection of objects."
    ::= { vtssSysutilMibGroups 2 }

vtssSysutilConfigSystemTimeInfoGroup OBJECT-GROUP
    OBJECTS     { vtssSysutilConfigSystemTimeSystemCurTime,
                  vtssSysutilConfigSystemTimeSystemCurTimeFormat }
    STATUS      current
    DESCRIPTION
        "A collection of objects."
    ::= { vtssSysutilMibGroups 3 }

vtssSysutilConfigTemperatureMonitorInfoGroup OBJECT-GROUP
    OBJECTS     { vtssSysutilConfigTemperatureMonitorSensorId,
                  vtssSysutilConfigTemperatureMonitorLowThreshold,
                  vtssSysutilConfigTemperatureMonitorHighThreshold,
                  vtssSysutilConfigTemperatureMonitorCriticalThreshold,
                  vtssSysutilConfigTemperatureMonitorHysteresis }
    STATUS      current
    DESCRIPTION
        "A collection of objects."
    ::= { vtssSysutilMibGroups 4 }

vtssSysutilStatusCpuLoadInfoGroup OBJECT-GROUP
    OBJECTS     { vtssSysutilStatusCpuLoadAverage100msec,
                  vtssSysutilStatusCpuLoadAverage1sec,
                  vtssSysutilStatusCpuLoadAverage10sec }
    STATUS      current
    DESCRIPTION
        "A collection of objects."
    ::= { vtssSysutilMibGroups 5 }

vtssSysutilStatusPowerSupplyInfoGroup OBJECT-GROUP
    OBJECTS     { vtssSysutilStatusPowerSupplySwitchId,
                  vtssSysutilStatusPowerSupplyPsuId,
                  vtssSysutilStatusPowerSupplyState,
                  vtssSysutilStatusPowerSupplyDescription }
    STATUS      current
    DESCRIPTION
        "A collection of objects."
    ::= { vtssSysutilMibGroups 6 }

vtssSysutilStatusSystemLedInfoGroup OBJECT-GROUP
    OBJECTS     { vtssSysutilStatusSystemLedSwitchId,
                  vtssSysutilStatusSystemLedDescription }
    STATUS      current
    DESCRIPTION
        "A collection of objects."
    ::= { vtssSysutilMibGroups 7 }

vtssSysutilStatusSystemUptimeInfoGroup OBJECT-GROUP
    OBJECTS     { vtssSysutilStatusSystemUptimeSystemUptime }
    STATUS      current
    DESCRIPTION
        "A collection of objects."
    ::= { vtssSysutilMibGroups 8 }

vtssSysutilStatusBoardInfoInfoGroup OBJECT-GROUP
    OBJECTS     { vtssSysutilStatusBoardInfoBoardMacAddress,
                  vtssSysutilStatusBoardInfoBoardID,
                  vtssSysutilStatusBoardInfoBoardSerial,
                  vtssSysutilStatusBoardInfoBoardType }
    STATUS      current
    DESCRIPTION
        "A collection of objects."
    ::= { vtssSysutilMibGroups 9 }

vtssSysutilStatusTemperatureMonitorInfoGroup OBJECT-GROUP
    OBJECTS     { vtssSysutilStatusTemperatureMonitorSensorId,
                  vtssSysutilStatusTemperatureMonitorLowAlarm,
                  vtssSysutilStatusTemperatureMonitorHighAlarm,
                  vtssSysutilStatusTemperatureMonitorCriticalAlarm,
                  vtssSysutilStatusTemperatureMonitorTemperature }
    STATUS      current
    DESCRIPTION
        "A collection of objects."
    ::= { vtssSysutilMibGroups 10 }

vtssSysutilControlRebootInfoGroup OBJECT-GROUP
    OBJECTS     { vtssSysutilControlRebootSwitchId,
                  vtssSysutilControlRebootType }
    STATUS      current
    DESCRIPTION
        "A collection of objects."
    ::= { vtssSysutilMibGroups 11 }

vtssSysutilControlSystemLedInfoGroup OBJECT-GROUP
    OBJECTS     { vtssSysutilControlSystemLedSwitchId,
                  vtssSysutilControlSystemLedClearStatus }
    STATUS      current
    DESCRIPTION
        "A collection of objects."
    ::= { vtssSysutilMibGroups 12 }

vtssSysutilMibCompliance MODULE-COMPLIANCE
    STATUS      current
    DESCRIPTION
        "The compliance statement for the implementation."

    MODULE      -- this module

    MANDATORY-GROUPS { vtssSysutilCapabilitiesInfoGroup,
                       vtssSysutilConfigSystemInfoInfoGroup,
                       vtssSysutilConfigSystemTimeInfoGroup,
                       vtssSysutilConfigTemperatureMonitorInfoGroup,
                       vtssSysutilStatusCpuLoadInfoGroup,
                       vtssSysutilStatusPowerSupplyInfoGroup,
                       vtssSysutilStatusSystemLedInfoGroup,
                       vtssSysutilStatusSystemUptimeInfoGroup,
                       vtssSysutilStatusBoardInfoInfoGroup,
                       vtssSysutilStatusTemperatureMonitorInfoGroup,
                       vtssSysutilControlRebootInfoGroup,
                       vtssSysutilControlSystemLedInfoGroup }

    ::= { vtssSysutilMibCompliances 1 }

END
