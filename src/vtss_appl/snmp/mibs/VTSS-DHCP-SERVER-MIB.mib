-- *****************************************************************
-- DHCP-SERVER-MIB:  Microsemi ENT private MIB
-- ****************************************************************

VTSS-DHCP-SERVER-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    IpAddress FROM SNMPv2-SMI
    Unsigned32 FROM SNMPv2-SMI
    MacAddress FROM SNMPv2-TC
    TruthValue FROM SNMPv2-TC
    VTSSDisplayString FROM VTSS-TC
    VTSSInterfaceIndex FROM VTSS-TC
    VTSSRowEditorState FROM VTSS-TC
    VTSSUnsigned16 FROM VTSS-TC
    ;

vtssDhcpServerMib MODULE-IDENTITY
    LAST-UPDATED "201903110000Z"
    ORGANIZATION
        "Microsemi Corporation"
    CONTACT-INFO
        "Application support: http://www.microchip.com/support"
    DESCRIPTION
        "This is a private version of DhcpServer"
    REVISION    "201903110000Z"
    DESCRIPTION
        "add support for dhcp server per port"
    REVISION    "201508240000Z"
    DESCRIPTION
        "revise fqdn as name"
    REVISION    "201411270000Z"
    DESCRIPTION
        "revise descriptions by Palle"
    REVISION    "201407010000Z"
    DESCRIPTION
        "Initial version"
    ::= { vtssSwitchMgmt 109 }


VTSSDhcpServerBindingEnum ::= TEXTUAL-CONVENTION
    STATUS      current
    DESCRIPTION
        "This enumeration defines the type of binding."
    SYNTAX      INTEGER { none(0), automatic(1), manual(2),
                          expired(3) }

VTSSDhcpServerBindingStateEnum ::= TEXTUAL-CONVENTION
    STATUS      current
    DESCRIPTION
        "This enumeration defines the state of binding."
    SYNTAX      INTEGER { none(0), allocated(1), committed(2),
                          expired(3) }

VTSSDhcpServerClientIdentifierEnum ::= TEXTUAL-CONVENTION
    STATUS      current
    DESCRIPTION
        "This enumeration defines the type of client identifier."
    SYNTAX      INTEGER { none(0), name(1), mac(2) }

VTSSDhcpServerNetbiosNodeEnum ::= TEXTUAL-CONVENTION
    STATUS      current
    DESCRIPTION
        "This enumeration defines the type of NetBIOS node."
    SYNTAX      INTEGER { nodeNone(0), nodeB(1), nodeP(2), nodeM(3),
                          nodeH(4) }

VTSSDhcpServerPoolEnum ::= TEXTUAL-CONVENTION
    STATUS      current
    DESCRIPTION
        "This enumeration defines the type of DHCP pool."
    SYNTAX      INTEGER { none(0), network(1), host(2) }

vtssDhcpServerMibObjects OBJECT IDENTIFIER
    ::= { vtssDhcpServerMib 1 }

vtssDhcpServerConfig OBJECT IDENTIFIER
    ::= { vtssDhcpServerMibObjects 2 }

vtssDhcpServerConfigGlobals OBJECT IDENTIFIER
    ::= { vtssDhcpServerConfig 1 }

vtssDhcpServerConfigGlobalsMode OBJECT-TYPE
    SYNTAX      TruthValue
    MAX-ACCESS  read-write
    STATUS      current
    DESCRIPTION
        "Global mode of DHCP server. true is to enable the functions of DHCP
         server and false is to disable it."
    ::= { vtssDhcpServerConfigGlobals 1 }

vtssDhcpServerConfigVlanTable OBJECT-TYPE
    SYNTAX      SEQUENCE OF VTSSDhcpServerConfigVlanEntry
    MAX-ACCESS  not-accessible
    STATUS      current
    DESCRIPTION
        "This is the table of DHCP server VLAN configuration. The index is VLAN
         ID."
    ::= { vtssDhcpServerConfig 2 }

vtssDhcpServerConfigVlanEntry OBJECT-TYPE
    SYNTAX      VTSSDhcpServerConfigVlanEntry
    MAX-ACCESS  not-accessible
    STATUS      current
    DESCRIPTION
        "Each VLAN has a set of parameters"
    INDEX       { vtssDhcpServerConfigVlanIfIndex }
    ::= { vtssDhcpServerConfigVlanTable 1 }

VTSSDhcpServerConfigVlanEntry ::= SEQUENCE {
    vtssDhcpServerConfigVlanIfIndex  VTSSInterfaceIndex,
    vtssDhcpServerConfigVlanMode     TruthValue
}

vtssDhcpServerConfigVlanIfIndex OBJECT-TYPE
    SYNTAX      VTSSInterfaceIndex
    MAX-ACCESS  accessible-for-notify
    STATUS      current
    DESCRIPTION
        "Logical interface number of VLAN."
    ::= { vtssDhcpServerConfigVlanEntry 1 }

vtssDhcpServerConfigVlanMode OBJECT-TYPE
    SYNTAX      TruthValue
    MAX-ACCESS  read-write
    STATUS      current
    DESCRIPTION
        "VLAN mode of DHCP server. true is to enable DHCP server per VLAN and
         false is to disable it per VLAN."
    ::= { vtssDhcpServerConfigVlanEntry 2 }

vtssDhcpServerConfigExcludedTable OBJECT-TYPE
    SYNTAX      SEQUENCE OF VTSSDhcpServerConfigExcludedEntry
    MAX-ACCESS  not-accessible
    STATUS      current
    DESCRIPTION
        "The table is DHCP server excluded IP onfiguration table. The indexes
         are low IP and high IP address."
    ::= { vtssDhcpServerConfig 3 }

vtssDhcpServerConfigExcludedEntry OBJECT-TYPE
    SYNTAX      VTSSDhcpServerConfigExcludedEntry
    MAX-ACCESS  not-accessible
    STATUS      current
    DESCRIPTION
        "Each entry has a set of parameters"
    INDEX       { vtssDhcpServerConfigExcludedLowIpAddress,
                  vtssDhcpServerConfigExcludedHighIpAddress }
    ::= { vtssDhcpServerConfigExcludedTable 1 }

VTSSDhcpServerConfigExcludedEntry ::= SEQUENCE {
    vtssDhcpServerConfigExcludedLowIpAddress   IpAddress,
    vtssDhcpServerConfigExcludedHighIpAddress  IpAddress,
    vtssDhcpServerConfigExcludedAction         VTSSRowEditorState
}

vtssDhcpServerConfigExcludedLowIpAddress OBJECT-TYPE
    SYNTAX      IpAddress
    MAX-ACCESS  accessible-for-notify
    STATUS      current
    DESCRIPTION
        "Low IP address."
    ::= { vtssDhcpServerConfigExcludedEntry 1 }

vtssDhcpServerConfigExcludedHighIpAddress OBJECT-TYPE
    SYNTAX      IpAddress
    MAX-ACCESS  accessible-for-notify
    STATUS      current
    DESCRIPTION
        "High IP address."
    ::= { vtssDhcpServerConfigExcludedEntry 2 }

vtssDhcpServerConfigExcludedAction OBJECT-TYPE
    SYNTAX      VTSSRowEditorState
    MAX-ACCESS  read-write
    STATUS      current
    DESCRIPTION
        "Action"
    ::= { vtssDhcpServerConfigExcludedEntry 100 }

vtssDhcpServerConfigExcludedIpTableRowEditor OBJECT IDENTIFIER
    ::= { vtssDhcpServerConfig 4 }

vtssDhcpServerConfigExcludedIpTableRowEditorLowIpAddress OBJECT-TYPE
    SYNTAX      IpAddress
    MAX-ACCESS  read-write
    STATUS      current
    DESCRIPTION
        "Low IP address."
    ::= { vtssDhcpServerConfigExcludedIpTableRowEditor 1 }

vtssDhcpServerConfigExcludedIpTableRowEditorHighIpAddress OBJECT-TYPE
    SYNTAX      IpAddress
    MAX-ACCESS  read-write
    STATUS      current
    DESCRIPTION
        "High IP address."
    ::= { vtssDhcpServerConfigExcludedIpTableRowEditor 2 }

vtssDhcpServerConfigExcludedIpTableRowEditorAction OBJECT-TYPE
    SYNTAX      VTSSRowEditorState
    MAX-ACCESS  read-write
    STATUS      current
    DESCRIPTION
        "Action"
    ::= { vtssDhcpServerConfigExcludedIpTableRowEditor 100 }

vtssDhcpServerConfigPoolTable OBJECT-TYPE
    SYNTAX      SEQUENCE OF VTSSDhcpServerConfigPoolEntry
    MAX-ACCESS  not-accessible
    STATUS      current
    DESCRIPTION
        "The table is DHCP server pool onfiguration table. The indexe is pool
         name."
    ::= { vtssDhcpServerConfig 5 }

vtssDhcpServerConfigPoolEntry OBJECT-TYPE
    SYNTAX      VTSSDhcpServerConfigPoolEntry
    MAX-ACCESS  not-accessible
    STATUS      current
    DESCRIPTION
        "Each entry has a set of parameters"
    INDEX       { vtssDhcpServerConfigPoolPoolName }
    ::= { vtssDhcpServerConfigPoolTable 1 }

VTSSDhcpServerConfigPoolEntry ::= SEQUENCE {
    vtssDhcpServerConfigPoolPoolName               VTSSDisplayString,
    vtssDhcpServerConfigPoolPoolType               VTSSDhcpServerPoolEnum,
    vtssDhcpServerConfigPoolIpv4Address            IpAddress,
    vtssDhcpServerConfigPoolSubnetMask             IpAddress,
    vtssDhcpServerConfigPoolSubnetBroadcast        IpAddress,
    vtssDhcpServerConfigPoolLeaseDay               Unsigned32,
    vtssDhcpServerConfigPoolLeaseHour              Unsigned32,
    vtssDhcpServerConfigPoolLeaseMinute            Unsigned32,
    vtssDhcpServerConfigPoolDomainName             VTSSDisplayString,
    vtssDhcpServerConfigPoolDefaultRouter1         IpAddress,
    vtssDhcpServerConfigPoolDefaultRouter2         IpAddress,
    vtssDhcpServerConfigPoolDefaultRouter3         IpAddress,
    vtssDhcpServerConfigPoolDefaultRouter4         IpAddress,
    vtssDhcpServerConfigPoolDnsServer1             IpAddress,
    vtssDhcpServerConfigPoolDnsServer2             IpAddress,
    vtssDhcpServerConfigPoolDnsServer3             IpAddress,
    vtssDhcpServerConfigPoolDnsServer4             IpAddress,
    vtssDhcpServerConfigPoolNtpServer1             IpAddress,
    vtssDhcpServerConfigPoolNtpServer2             IpAddress,
    vtssDhcpServerConfigPoolNtpServer3             IpAddress,
    vtssDhcpServerConfigPoolNtpServer4             IpAddress,
    vtssDhcpServerConfigPoolNetbiosNodeType        VTSSDhcpServerNetbiosNodeEnum,
    vtssDhcpServerConfigPoolNetbiosScope           VTSSDisplayString,
    vtssDhcpServerConfigPoolNetbiosNameServer1     IpAddress,
    vtssDhcpServerConfigPoolNetbiosNameServer2     IpAddress,
    vtssDhcpServerConfigPoolNetbiosNameServer3     IpAddress,
    vtssDhcpServerConfigPoolNetbiosNameServer4     IpAddress,
    vtssDhcpServerConfigPoolNisDomainName          VTSSDisplayString,
    vtssDhcpServerConfigPoolNisServer1             IpAddress,
    vtssDhcpServerConfigPoolNisServer2             IpAddress,
    vtssDhcpServerConfigPoolNisServer3             IpAddress,
    vtssDhcpServerConfigPoolNisServer4             IpAddress,
    vtssDhcpServerConfigPoolClientIdentifierType   VTSSDhcpServerClientIdentifierEnum,
    vtssDhcpServerConfigPoolClientIdentifierName   VTSSDisplayString,
    vtssDhcpServerConfigPoolClientIdentifierMac    MacAddress,
    vtssDhcpServerConfigPoolClientHardwareAddress  MacAddress,
    vtssDhcpServerConfigPoolClientName             VTSSDisplayString,
    vtssDhcpServerConfigPoolVendorClassId1         VTSSDisplayString,
    vtssDhcpServerConfigPoolVendorSpecificInfo1    VTSSDisplayString,
    vtssDhcpServerConfigPoolVendorClassId2         VTSSDisplayString,
    vtssDhcpServerConfigPoolVendorSpecificInfo2    VTSSDisplayString,
    vtssDhcpServerConfigPoolVendorClassId3         VTSSDisplayString,
    vtssDhcpServerConfigPoolVendorSpecificInfo3    VTSSDisplayString,
    vtssDhcpServerConfigPoolVendorClassId4         VTSSDisplayString,
    vtssDhcpServerConfigPoolVendorSpecificInfo4    VTSSDisplayString,
    vtssDhcpServerConfigPoolReservedOnly           TruthValue,
    vtssDhcpServerConfigPoolAction                 VTSSRowEditorState
}

vtssDhcpServerConfigPoolPoolName OBJECT-TYPE
    SYNTAX      VTSSDisplayString (SIZE(0..32))
    MAX-ACCESS  accessible-for-notify
    STATUS      current
    DESCRIPTION
        "Name of DHCP pool."
    ::= { vtssDhcpServerConfigPoolEntry 1 }

vtssDhcpServerConfigPoolPoolType OBJECT-TYPE
    SYNTAX      VTSSDhcpServerPoolEnum
    MAX-ACCESS  read-write
    STATUS      current
    DESCRIPTION
        "Type of pool. none(0) means the pool type is not defined yet.
         network(1) means the pool defines a pool of IP addresses to service
         more than one DHCP client. host(2) means the pool services for a
         specific DHCP client identified by client identifier or hardware
         address."
    ::= { vtssDhcpServerConfigPoolEntry 2 }

vtssDhcpServerConfigPoolIpv4Address OBJECT-TYPE
    SYNTAX      IpAddress
    MAX-ACCESS  read-write
    STATUS      current
    DESCRIPTION
        "Network number of the subnet. If the pool type is of network, the IP
         address can be any general IP address. If the pool type is of host, the
         IP address must be a unicast IP address."
    ::= { vtssDhcpServerConfigPoolEntry 3 }

vtssDhcpServerConfigPoolSubnetMask OBJECT-TYPE
    SYNTAX      IpAddress
    MAX-ACCESS  read-write
    STATUS      current
    DESCRIPTION
        "Subnet Mask. DHCP option 1. Specify subnet mask of the DHCP address
         pool, excluding 0.0.0.0 and 255.255.255.255."
    ::= { vtssDhcpServerConfigPoolEntry 4 }

vtssDhcpServerConfigPoolSubnetBroadcast OBJECT-TYPE
    SYNTAX      IpAddress
    MAX-ACCESS  read-write
    STATUS      current
    DESCRIPTION
        "Broadcast IP address in the subnet. DHCP option 28. Specify the
         broadcast address in use on the client's subnet."
    ::= { vtssDhcpServerConfigPoolEntry 5 }

vtssDhcpServerConfigPoolLeaseDay OBJECT-TYPE
    SYNTAX      Unsigned32
    MAX-ACCESS  read-write
    STATUS      current
    DESCRIPTION
        "Number of days of lease time. DHCP option 51, 58 and 59. The value
         range is 0-365. Specify lease time that allows the client to request a
         lease time for the IP address. If all of LeaseDay, LeaseHour and
         LeaseMinute are 0's, then it means the lease time is infinite."
    ::= { vtssDhcpServerConfigPoolEntry 6 }

vtssDhcpServerConfigPoolLeaseHour OBJECT-TYPE
    SYNTAX      Unsigned32
    MAX-ACCESS  read-write
    STATUS      current
    DESCRIPTION
        "Number of hours of lease time. DHCP option 51, 58 and 59. The value
         range is 0-23. Specify lease time that allows the client to request a
         lease time for the IP address. If all of LeaseDay, LeaseHour and
         LeaseMinute are 0's, then it means the lease time is infinite."
    ::= { vtssDhcpServerConfigPoolEntry 7 }

vtssDhcpServerConfigPoolLeaseMinute OBJECT-TYPE
    SYNTAX      Unsigned32
    MAX-ACCESS  read-write
    STATUS      current
    DESCRIPTION
        "Number of minutes of lease time. DHCP option 51, 58 and 59. The value
         range is 0-59. Specify lease time that allows the client to request a
         lease time for the IP address. If all of LeaseDay, LeaseHour and
         LeaseMinute are 0's, then it means the lease time is infinite."
    ::= { vtssDhcpServerConfigPoolEntry 8 }

vtssDhcpServerConfigPoolDomainName OBJECT-TYPE
    SYNTAX      VTSSDisplayString (SIZE(0..32))
    MAX-ACCESS  read-write
    STATUS      current
    DESCRIPTION
        "Domain name. DHCP option 15. Specify domain name that client should use
         when resolving hostname via DNS."
    ::= { vtssDhcpServerConfigPoolEntry 9 }

vtssDhcpServerConfigPoolDefaultRouter1 OBJECT-TYPE
    SYNTAX      IpAddress
    MAX-ACCESS  read-write
    STATUS      current
    DESCRIPTION
        "Default router 1."
    ::= { vtssDhcpServerConfigPoolEntry 10 }

vtssDhcpServerConfigPoolDefaultRouter2 OBJECT-TYPE
    SYNTAX      IpAddress
    MAX-ACCESS  read-write
    STATUS      current
    DESCRIPTION
        "Default router 2."
    ::= { vtssDhcpServerConfigPoolEntry 11 }

vtssDhcpServerConfigPoolDefaultRouter3 OBJECT-TYPE
    SYNTAX      IpAddress
    MAX-ACCESS  read-write
    STATUS      current
    DESCRIPTION
        "Default router 3."
    ::= { vtssDhcpServerConfigPoolEntry 12 }

vtssDhcpServerConfigPoolDefaultRouter4 OBJECT-TYPE
    SYNTAX      IpAddress
    MAX-ACCESS  read-write
    STATUS      current
    DESCRIPTION
        "Default router 4."
    ::= { vtssDhcpServerConfigPoolEntry 13 }

vtssDhcpServerConfigPoolDnsServer1 OBJECT-TYPE
    SYNTAX      IpAddress
    MAX-ACCESS  read-write
    STATUS      current
    DESCRIPTION
        "DNS server 1."
    ::= { vtssDhcpServerConfigPoolEntry 14 }

vtssDhcpServerConfigPoolDnsServer2 OBJECT-TYPE
    SYNTAX      IpAddress
    MAX-ACCESS  read-write
    STATUS      current
    DESCRIPTION
        "DNS server 2."
    ::= { vtssDhcpServerConfigPoolEntry 15 }

vtssDhcpServerConfigPoolDnsServer3 OBJECT-TYPE
    SYNTAX      IpAddress
    MAX-ACCESS  read-write
    STATUS      current
    DESCRIPTION
        "DNS server 3."
    ::= { vtssDhcpServerConfigPoolEntry 16 }

vtssDhcpServerConfigPoolDnsServer4 OBJECT-TYPE
    SYNTAX      IpAddress
    MAX-ACCESS  read-write
    STATUS      current
    DESCRIPTION
        "DNS server 4."
    ::= { vtssDhcpServerConfigPoolEntry 17 }

vtssDhcpServerConfigPoolNtpServer1 OBJECT-TYPE
    SYNTAX      IpAddress
    MAX-ACCESS  read-write
    STATUS      current
    DESCRIPTION
        "NTP server 1."
    ::= { vtssDhcpServerConfigPoolEntry 18 }

vtssDhcpServerConfigPoolNtpServer2 OBJECT-TYPE
    SYNTAX      IpAddress
    MAX-ACCESS  read-write
    STATUS      current
    DESCRIPTION
        "NTP server 2."
    ::= { vtssDhcpServerConfigPoolEntry 19 }

vtssDhcpServerConfigPoolNtpServer3 OBJECT-TYPE
    SYNTAX      IpAddress
    MAX-ACCESS  read-write
    STATUS      current
    DESCRIPTION
        "NTP server 3."
    ::= { vtssDhcpServerConfigPoolEntry 20 }

vtssDhcpServerConfigPoolNtpServer4 OBJECT-TYPE
    SYNTAX      IpAddress
    MAX-ACCESS  read-write
    STATUS      current
    DESCRIPTION
        "NTP server 4."
    ::= { vtssDhcpServerConfigPoolEntry 21 }

vtssDhcpServerConfigPoolNetbiosNodeType OBJECT-TYPE
    SYNTAX      VTSSDhcpServerNetbiosNodeEnum
    MAX-ACCESS  read-write
    STATUS      current
    DESCRIPTION
        "Type of NetBIOS node. DHCP option 46. Specify NetBIOS node type option
         to allow Netbios over TCP/IP clients which are configurable to be
         configured as described in RFC 1001/1002. nodeNone(0) means the node
         type is not defined yet. nodeB(1) means the node type is type of B.
         nodeP(2) means the node type is type of P. nodeM(3) means the node type
         is type of M. nodeH(4) means the node type is type of H."
    ::= { vtssDhcpServerConfigPoolEntry 22 }

vtssDhcpServerConfigPoolNetbiosScope OBJECT-TYPE
    SYNTAX      VTSSDisplayString (SIZE(0..32))
    MAX-ACCESS  read-write
    STATUS      current
    DESCRIPTION
        "NetBIOS scope. DHCP option 47. Specify the NetBIOS over TCP/IP scope
         parameter for the client as specified in RFC 1001/1002."
    ::= { vtssDhcpServerConfigPoolEntry 23 }

vtssDhcpServerConfigPoolNetbiosNameServer1 OBJECT-TYPE
    SYNTAX      IpAddress
    MAX-ACCESS  read-write
    STATUS      current
    DESCRIPTION
        "NetBIOS name server 1."
    ::= { vtssDhcpServerConfigPoolEntry 24 }

vtssDhcpServerConfigPoolNetbiosNameServer2 OBJECT-TYPE
    SYNTAX      IpAddress
    MAX-ACCESS  read-write
    STATUS      current
    DESCRIPTION
        "NetBIOS name server 2."
    ::= { vtssDhcpServerConfigPoolEntry 25 }

vtssDhcpServerConfigPoolNetbiosNameServer3 OBJECT-TYPE
    SYNTAX      IpAddress
    MAX-ACCESS  read-write
    STATUS      current
    DESCRIPTION
        "NetBIOS name server 3."
    ::= { vtssDhcpServerConfigPoolEntry 26 }

vtssDhcpServerConfigPoolNetbiosNameServer4 OBJECT-TYPE
    SYNTAX      IpAddress
    MAX-ACCESS  read-write
    STATUS      current
    DESCRIPTION
        "NetBIOS name server 4."
    ::= { vtssDhcpServerConfigPoolEntry 27 }

vtssDhcpServerConfigPoolNisDomainName OBJECT-TYPE
    SYNTAX      VTSSDisplayString (SIZE(0..32))
    MAX-ACCESS  read-write
    STATUS      current
    DESCRIPTION
        "NIS Domain Name. DHCP option 40. Specify the name of the client's NIS
         domain."
    ::= { vtssDhcpServerConfigPoolEntry 28 }

vtssDhcpServerConfigPoolNisServer1 OBJECT-TYPE
    SYNTAX      IpAddress
    MAX-ACCESS  read-write
    STATUS      current
    DESCRIPTION
        "NIS server 1."
    ::= { vtssDhcpServerConfigPoolEntry 29 }

vtssDhcpServerConfigPoolNisServer2 OBJECT-TYPE
    SYNTAX      IpAddress
    MAX-ACCESS  read-write
    STATUS      current
    DESCRIPTION
        "NIS server 2."
    ::= { vtssDhcpServerConfigPoolEntry 30 }

vtssDhcpServerConfigPoolNisServer3 OBJECT-TYPE
    SYNTAX      IpAddress
    MAX-ACCESS  read-write
    STATUS      current
    DESCRIPTION
        "NIS server 3."
    ::= { vtssDhcpServerConfigPoolEntry 31 }

vtssDhcpServerConfigPoolNisServer4 OBJECT-TYPE
    SYNTAX      IpAddress
    MAX-ACCESS  read-write
    STATUS      current
    DESCRIPTION
        "NIS server 4."
    ::= { vtssDhcpServerConfigPoolEntry 32 }

vtssDhcpServerConfigPoolClientIdentifierType OBJECT-TYPE
    SYNTAX      VTSSDhcpServerClientIdentifierEnum
    MAX-ACCESS  read-write
    STATUS      current
    DESCRIPTION
        "Type of client identifier. DHCP option 61. Specify client's unique
         identifier to be used when the pool is the type of host. none(0) means
         the client identifier type is not defined yet. name(1) means the client
         identifier type is other than hardware. mac(2) means the client
         identifier type is type of MAC address."
    ::= { vtssDhcpServerConfigPoolEntry 33 }

vtssDhcpServerConfigPoolClientIdentifierName OBJECT-TYPE
    SYNTAX      VTSSDisplayString (SIZE(0..64))
    MAX-ACCESS  read-write
    STATUS      current
    DESCRIPTION
        "Client identifier which type is other than hardware. DHCP option 61.
         Specify client's unique identifier to be used when the pool is the type
         of host. This takes effect only if ClientIdentifierType is defined
         name(1)."
    ::= { vtssDhcpServerConfigPoolEntry 34 }

vtssDhcpServerConfigPoolClientIdentifierMac OBJECT-TYPE
    SYNTAX      MacAddress
    MAX-ACCESS  read-write
    STATUS      current
    DESCRIPTION
        "Client's MAC address. DHCP option 61. Specify client's unique
         identifier to be used when the pool is the type of host. This takes
         effect only if ClientIdentifierType is defined as mac(2)."
    ::= { vtssDhcpServerConfigPoolEntry 35 }

vtssDhcpServerConfigPoolClientHardwareAddress OBJECT-TYPE
    SYNTAX      MacAddress
    MAX-ACCESS  read-write
    STATUS      current
    DESCRIPTION
        "Client's hardware address. Specify client's hardware(MAC) address to be
         used when the pool is the type of host."
    ::= { vtssDhcpServerConfigPoolEntry 36 }

vtssDhcpServerConfigPoolClientName OBJECT-TYPE
    SYNTAX      VTSSDisplayString (SIZE(0..32))
    MAX-ACCESS  read-write
    STATUS      current
    DESCRIPTION
        "Client name. DHCP option 12. Specify the name of client to be used when
         the pool is the type of host."
    ::= { vtssDhcpServerConfigPoolEntry 37 }

vtssDhcpServerConfigPoolVendorClassId1 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolEntry 38 }

vtssDhcpServerConfigPoolVendorSpecificInfo1 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolEntry 39 }

vtssDhcpServerConfigPoolVendorClassId2 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolEntry 40 }

vtssDhcpServerConfigPoolVendorSpecificInfo2 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolEntry 41 }

vtssDhcpServerConfigPoolVendorClassId3 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolEntry 42 }

vtssDhcpServerConfigPoolVendorSpecificInfo3 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolEntry 43 }

vtssDhcpServerConfigPoolVendorClassId4 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolEntry 44 }

vtssDhcpServerConfigPoolVendorSpecificInfo4 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolEntry 45 }

vtssDhcpServerConfigPoolReservedOnly OBJECT-TYPE
    SYNTAX      TruthValue
    MAX-ACCESS  read-write
    STATUS      current
    DESCRIPTION
        "Whether to only hand out reserved addresses (TRUE) or not (FALSE)."
    ::= { vtssDhcpServerConfigPoolEntry 46 }

vtssDhcpServerConfigPoolAction OBJECT-TYPE
    SYNTAX      VTSSRowEditorState
    MAX-ACCESS  read-write
    STATUS      current
    DESCRIPTION
        "Action"
    ::= { vtssDhcpServerConfigPoolEntry 100 }

vtssDhcpServerConfigPoolTableRowEditor OBJECT IDENTIFIER
    ::= { vtssDhcpServerConfig 6 }

vtssDhcpServerConfigPoolTableRowEditorPoolName OBJECT-TYPE
    SYNTAX      VTSSDisplayString (SIZE(0..32))
    MAX-ACCESS  read-write
    STATUS      current
    DESCRIPTION
        "Name of DHCP pool."
    ::= { vtssDhcpServerConfigPoolTableRowEditor 1 }

vtssDhcpServerConfigPoolTableRowEditorPoolType OBJECT-TYPE
    SYNTAX      VTSSDhcpServerPoolEnum
    MAX-ACCESS  read-write
    STATUS      current
    DESCRIPTION
        "Type of pool. none(0) means the pool type is not defined yet.
         network(1) means the pool defines a pool of IP addresses to service
         more than one DHCP client. host(2) means the pool services for a
         specific DHCP client identified by client identifier or hardware
         address."
    ::= { vtssDhcpServerConfigPoolTableRowEditor 2 }

vtssDhcpServerConfigPoolTableRowEditorIpv4Address OBJECT-TYPE
    SYNTAX      IpAddress
    MAX-ACCESS  read-write
    STATUS      current
    DESCRIPTION
        "Network number of the subnet. If the pool type is of network, the IP
         address can be any general IP address. If the pool type is of host, the
         IP address must be a unicast IP address."
    ::= { vtssDhcpServerConfigPoolTableRowEditor 3 }

vtssDhcpServerConfigPoolTableRowEditorSubnetMask OBJECT-TYPE
    SYNTAX      IpAddress
    MAX-ACCESS  read-write
    STATUS      current
    DESCRIPTION
        "Subnet Mask. DHCP option 1. Specify subnet mask of the DHCP address
         pool, excluding 0.0.0.0 and 255.255.255.255."
    ::= { vtssDhcpServerConfigPoolTableRowEditor 4 }

vtssDhcpServerConfigPoolTableRowEditorSubnetBroadcast OBJECT-TYPE
    SYNTAX      IpAddress
    MAX-ACCESS  read-write
    STATUS      current
    DESCRIPTION
        "Broadcast IP address in the subnet. DHCP option 28. Specify the
         broadcast address in use on the client's subnet."
    ::= { vtssDhcpServerConfigPoolTableRowEditor 5 }

vtssDhcpServerConfigPoolTableRowEditorLeaseDay OBJECT-TYPE
    SYNTAX      Unsigned32
    MAX-ACCESS  read-write
    STATUS      current
    DESCRIPTION
        "Number of days of lease time. DHCP option 51, 58 and 59. The value
         range is 0-365. Specify lease time that allows the client to request a
         lease time for the IP address. If all of LeaseDay, LeaseHour and
         LeaseMinute are 0's, then it means the lease time is infinite."
    ::= { vtssDhcpServerConfigPoolTableRowEditor 6 }

vtssDhcpServerConfigPoolTableRowEditorLeaseHour OBJECT-TYPE
    SYNTAX      Unsigned32
    MAX-ACCESS  read-write
    STATUS      current
    DESCRIPTION
        "Number of hours of lease time. DHCP option 51, 58 and 59. The value
         range is 0-23. Specify lease time that allows the client to request a
         lease time for the IP address. If all of LeaseDay, LeaseHour and
         LeaseMinute are 0's, then it means the lease time is infinite."
    ::= { vtssDhcpServerConfigPoolTableRowEditor 7 }

vtssDhcpServerConfigPoolTableRowEditorLeaseMinute OBJECT-TYPE
    SYNTAX      Unsigned32
    MAX-ACCESS  read-write
    STATUS      current
    DESCRIPTION
        "Number of minutes of lease time. DHCP option 51, 58 and 59. The value
         range is 0-59. Specify lease time that allows the client to request a
         lease time for the IP address. If all of LeaseDay, LeaseHour and
         LeaseMinute are 0's, then it means the lease time is infinite."
    ::= { vtssDhcpServerConfigPoolTableRowEditor 8 }

vtssDhcpServerConfigPoolTableRowEditorDomainName OBJECT-TYPE
    SYNTAX      VTSSDisplayString (SIZE(0..32))
    MAX-ACCESS  read-write
    STATUS      current
    DESCRIPTION
        "Domain name. DHCP option 15. Specify domain name that client should use
         when resolving hostname via DNS."
    ::= { vtssDhcpServerConfigPoolTableRowEditor 9 }

vtssDhcpServerConfigPoolTableRowEditorDefaultRouter1 OBJECT-TYPE
    SYNTAX      IpAddress
    MAX-ACCESS  read-write
    STATUS      current
    DESCRIPTION
        "Default router 1."
    ::= { vtssDhcpServerConfigPoolTableRowEditor 10 }

vtssDhcpServerConfigPoolTableRowEditorDefaultRouter2 OBJECT-TYPE
    SYNTAX      IpAddress
    MAX-ACCESS  read-write
    STATUS      current
    DESCRIPTION
        "Default router 2."
    ::= { vtssDhcpServerConfigPoolTableRowEditor 11 }

vtssDhcpServerConfigPoolTableRowEditorDefaultRouter3 OBJECT-TYPE
    SYNTAX      IpAddress
    MAX-ACCESS  read-write
    STATUS      current
    DESCRIPTION
        "Default router 3."
    ::= { vtssDhcpServerConfigPoolTableRowEditor 12 }

vtssDhcpServerConfigPoolTableRowEditorDefaultRouter4 OBJECT-TYPE
    SYNTAX      IpAddress
    MAX-ACCESS  read-write
    STATUS      current
    DESCRIPTION
        "Default router 4."
    ::= { vtssDhcpServerConfigPoolTableRowEditor 13 }

vtssDhcpServerConfigPoolTableRowEditorDnsServer1 OBJECT-TYPE
    SYNTAX      IpAddress
    MAX-ACCESS  read-write
    STATUS      current
    DESCRIPTION
        "DNS server 1."
    ::= { vtssDhcpServerConfigPoolTableRowEditor 14 }

vtssDhcpServerConfigPoolTableRowEditorDnsServer2 OBJECT-TYPE
    SYNTAX      IpAddress
    MAX-ACCESS  read-write
    STATUS      current
    DESCRIPTION
        "DNS server 2."
    ::= { vtssDhcpServerConfigPoolTableRowEditor 15 }

vtssDhcpServerConfigPoolTableRowEditorDnsServer3 OBJECT-TYPE
    SYNTAX      IpAddress
    MAX-ACCESS  read-write
    STATUS      current
    DESCRIPTION
        "DNS server 3."
    ::= { vtssDhcpServerConfigPoolTableRowEditor 16 }

vtssDhcpServerConfigPoolTableRowEditorDnsServer4 OBJECT-TYPE
    SYNTAX      IpAddress
    MAX-ACCESS  read-write
    STATUS      current
    DESCRIPTION
        "DNS server 4."
    ::= { vtssDhcpServerConfigPoolTableRowEditor 17 }

vtssDhcpServerConfigPoolTableRowEditorNtpServer1 OBJECT-TYPE
    SYNTAX      IpAddress
    MAX-ACCESS  read-write
    STATUS      current
    DESCRIPTION
        "NTP server 1."
    ::= { vtssDhcpServerConfigPoolTableRowEditor 18 }

vtssDhcpServerConfigPoolTableRowEditorNtpServer2 OBJECT-TYPE
    SYNTAX      IpAddress
    MAX-ACCESS  read-write
    STATUS      current
    DESCRIPTION
        "NTP server 2."
    ::= { vtssDhcpServerConfigPoolTableRowEditor 19 }

vtssDhcpServerConfigPoolTableRowEditorNtpServer3 OBJECT-TYPE
    SYNTAX      IpAddress
    MAX-ACCESS  read-write
    STATUS      current
    DESCRIPTION
        "NTP server 3."
    ::= { vtssDhcpServerConfigPoolTableRowEditor 20 }

vtssDhcpServerConfigPoolTableRowEditorNtpServer4 OBJECT-TYPE
    SYNTAX      IpAddress
    MAX-ACCESS  read-write
    STATUS      current
    DESCRIPTION
        "NTP server 4."
    ::= { vtssDhcpServerConfigPoolTableRowEditor 21 }

vtssDhcpServerConfigPoolTableRowEditorNetbiosNodeType OBJECT-TYPE
    SYNTAX      VTSSDhcpServerNetbiosNodeEnum
    MAX-ACCESS  read-write
    STATUS      current
    DESCRIPTION
        "Type of NetBIOS node. DHCP option 46. Specify NetBIOS node type option
         to allow Netbios over TCP/IP clients which are configurable to be
         configured as described in RFC 1001/1002. nodeNone(0) means the node
         type is not defined yet. nodeB(1) means the node type is type of B.
         nodeP(2) means the node type is type of P. nodeM(3) means the node type
         is type of M. nodeH(4) means the node type is type of H."
    ::= { vtssDhcpServerConfigPoolTableRowEditor 22 }

vtssDhcpServerConfigPoolTableRowEditorNetbiosScope OBJECT-TYPE
    SYNTAX      VTSSDisplayString (SIZE(0..32))
    MAX-ACCESS  read-write
    STATUS      current
    DESCRIPTION
        "NetBIOS scope. DHCP option 47. Specify the NetBIOS over TCP/IP scope
         parameter for the client as specified in RFC 1001/1002."
    ::= { vtssDhcpServerConfigPoolTableRowEditor 23 }

vtssDhcpServerConfigPoolTableRowEditorNetbiosNameServer1 OBJECT-TYPE
    SYNTAX      IpAddress
    MAX-ACCESS  read-write
    STATUS      current
    DESCRIPTION
        "NetBIOS name server 1."
    ::= { vtssDhcpServerConfigPoolTableRowEditor 24 }

vtssDhcpServerConfigPoolTableRowEditorNetbiosNameServer2 OBJECT-TYPE
    SYNTAX      IpAddress
    MAX-ACCESS  read-write
    STATUS      current
    DESCRIPTION
        "NetBIOS name server 2."
    ::= { vtssDhcpServerConfigPoolTableRowEditor 25 }

vtssDhcpServerConfigPoolTableRowEditorNetbiosNameServer3 OBJECT-TYPE
    SYNTAX      IpAddress
    MAX-ACCESS  read-write
    STATUS      current
    DESCRIPTION
        "NetBIOS name server 3."
    ::= { vtssDhcpServerConfigPoolTableRowEditor 26 }

vtssDhcpServerConfigPoolTableRowEditorNetbiosNameServer4 OBJECT-TYPE
    SYNTAX      IpAddress
    MAX-ACCESS  read-write
    STATUS      current
    DESCRIPTION
        "NetBIOS name server 4."
    ::= { vtssDhcpServerConfigPoolTableRowEditor 27 }

vtssDhcpServerConfigPoolTableRowEditorNisDomainName OBJECT-TYPE
    SYNTAX      VTSSDisplayString (SIZE(0..32))
    MAX-ACCESS  read-write
    STATUS      current
    DESCRIPTION
        "NIS Domain Name. DHCP option 40. Specify the name of the client's NIS
         domain."
    ::= { vtssDhcpServerConfigPoolTableRowEditor 28 }

vtssDhcpServerConfigPoolTableRowEditorNisServer1 OBJECT-TYPE
    SYNTAX      IpAddress
    MAX-ACCESS  read-write
    STATUS      current
    DESCRIPTION
        "NIS server 1."
    ::= { vtssDhcpServerConfigPoolTableRowEditor 29 }

vtssDhcpServerConfigPoolTableRowEditorNisServer2 OBJECT-TYPE
    SYNTAX      IpAddress
    MAX-ACCESS  read-write
    STATUS      current
    DESCRIPTION
        "NIS server 2."
    ::= { vtssDhcpServerConfigPoolTableRowEditor 30 }

vtssDhcpServerConfigPoolTableRowEditorNisServer3 OBJECT-TYPE
    SYNTAX      IpAddress
    MAX-ACCESS  read-write
    STATUS      current
    DESCRIPTION
        "NIS server 3."
    ::= { vtssDhcpServerConfigPoolTableRowEditor 31 }

vtssDhcpServerConfigPoolTableRowEditorNisServer4 OBJECT-TYPE
    SYNTAX      IpAddress
    MAX-ACCESS  read-write
    STATUS      current
    DESCRIPTION
        "NIS server 4."
    ::= { vtssDhcpServerConfigPoolTableRowEditor 32 }

vtssDhcpServerConfigPoolTableRowEditorClientIdentifierType OBJECT-TYPE
    SYNTAX      VTSSDhcpServerClientIdentifierEnum
    MAX-ACCESS  read-write
    STATUS      current
    DESCRIPTION
        "Type of client identifier. DHCP option 61. Specify client's unique
         identifier to be used when the pool is the type of host. none(0) means
         the client identifier type is not defined yet. name(1) means the client
         identifier type is other than hardware. mac(2) means the client
         identifier type is type of MAC address."
    ::= { vtssDhcpServerConfigPoolTableRowEditor 33 }

vtssDhcpServerConfigPoolTableRowEditorClientIdentifierName OBJECT-TYPE
    SYNTAX      VTSSDisplayString (SIZE(0..64))
    MAX-ACCESS  read-write
    STATUS      current
    DESCRIPTION
        "Client identifier which type is other than hardware. DHCP option 61.
         Specify client's unique identifier to be used when the pool is the type
         of host. This takes effect only if ClientIdentifierType is defined
         name(1)."
    ::= { vtssDhcpServerConfigPoolTableRowEditor 34 }

vtssDhcpServerConfigPoolTableRowEditorClientIdentifierMac OBJECT-TYPE
    SYNTAX      MacAddress
    MAX-ACCESS  read-write
    STATUS      current
    DESCRIPTION
        "Client's MAC address. DHCP option 61. Specify client's unique
         identifier to be used when the pool is the type of host. This takes
         effect only if ClientIdentifierType is defined as mac(2)."
    ::= { vtssDhcpServerConfigPoolTableRowEditor 35 }

vtssDhcpServerConfigPoolTableRowEditorClientHardwareAddress OBJECT-TYPE
    SYNTAX      MacAddress
    MAX-ACCESS  read-write
    STATUS      current
    DESCRIPTION
        "Client's hardware address. Specify client's hardware(MAC) address to be
         used when the pool is the type of host."
    ::= { vtssDhcpServerConfigPoolTableRowEditor 36 }

vtssDhcpServerConfigPoolTableRowEditorClientName OBJECT-TYPE
    SYNTAX      VTSSDisplayString (SIZE(0..32))
    MAX-ACCESS  read-write
    STATUS      current
    DESCRIPTION
        "Client name. DHCP option 12. Specify the name of client to be used when
         the pool is the type of host."
    ::= { vtssDhcpServerConfigPoolTableRowEditor 37 }

vtssDhcpServerConfigPoolTableRowEditorVendorClassId1 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolTableRowEditor 38 }

vtssDhcpServerConfigPoolTableRowEditorVendorSpecificInfo1 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolTableRowEditor 39 }

vtssDhcpServerConfigPoolTableRowEditorVendorClassId2 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolTableRowEditor 40 }

vtssDhcpServerConfigPoolTableRowEditorVendorSpecificInfo2 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolTableRowEditor 41 }

vtssDhcpServerConfigPoolTableRowEditorVendorClassId3 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolTableRowEditor 42 }

vtssDhcpServerConfigPoolTableRowEditorVendorSpecificInfo3 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolTableRowEditor 43 }

vtssDhcpServerConfigPoolTableRowEditorVendorClassId4 OBJECT-TYPE
    SYNTAX      VTSSDisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { vtssDhcpServerConfigPoolTableRowEditor 44 }

vtssDhcpServerConfigPoolTableRowEditorVendorSpecificInfo4 OBJECT-TYPE
    SYNTAX      VTSSDisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { vtssDhcpServerConfigPoolTableRowEditor 45 }

vtssDhcpServerConfigPoolTableRowEditorReservedOnly OBJECT-TYPE
    SYNTAX      TruthValue
    MAX-ACCESS  read-write
    STATUS      current
    DESCRIPTION
        "Whether to only hand out reserved addresses (TRUE) or not (FALSE)."
    ::= { vtssDhcpServerConfigPoolTableRowEditor 46 }

vtssDhcpServerConfigPoolTableRowEditorAction OBJECT-TYPE
    SYNTAX      VTSSRowEditorState
    MAX-ACCESS  read-write
    STATUS      current
    DESCRIPTION
        "Action"
    ::= { vtssDhcpServerConfigPoolTableRowEditor 100 }

vtssDhcpServerConfigReservedTable OBJECT-TYPE
    SYNTAX      SEQUENCE OF VTSSDhcpServerConfigReservedEntry
    MAX-ACCESS  not-accessible
    STATUS      current
    DESCRIPTION
        "The table is DHCP server reserved entries. The index is the name of the
         pool and the ip address"
    ::= { vtssDhcpServerConfig 7 }

vtssDhcpServerConfigReservedEntry OBJECT-TYPE
    SYNTAX      VTSSDhcpServerConfigReservedEntry
    MAX-ACCESS  not-accessible
    STATUS      current
    DESCRIPTION
        "Each entry has a set of parameters"
    INDEX       { vtssDhcpServerConfigReservedPoolName,
                  vtssDhcpServerConfigReservedIpAddress }
    ::= { vtssDhcpServerConfigReservedTable 1 }

VTSSDhcpServerConfigReservedEntry ::= SEQUENCE {
    vtssDhcpServerConfigReservedPoolName   VTSSDisplayString,
    vtssDhcpServerConfigReservedIpAddress  IpAddress,
    vtssDhcpServerConfigReservedIfIndex    VTSSInterfaceIndex,
    vtssDhcpServerConfigReservedAction     VTSSRowEditorState
}

vtssDhcpServerConfigReservedPoolName OBJECT-TYPE
    SYNTAX      VTSSDisplayString (SIZE(0..32))
    MAX-ACCESS  accessible-for-notify
    STATUS      current
    DESCRIPTION
        "Name of DHCP pool."
    ::= { vtssDhcpServerConfigReservedEntry 1 }

vtssDhcpServerConfigReservedIpAddress OBJECT-TYPE
    SYNTAX      IpAddress
    MAX-ACCESS  accessible-for-notify
    STATUS      current
    DESCRIPTION
        "Reserved IP address."
    ::= { vtssDhcpServerConfigReservedEntry 2 }

vtssDhcpServerConfigReservedIfIndex OBJECT-TYPE
    SYNTAX      VTSSInterfaceIndex
    MAX-ACCESS  read-write
    STATUS      current
    DESCRIPTION
        "Logical interface number for the interface for which the ip address is
         reserved."
    ::= { vtssDhcpServerConfigReservedEntry 3 }

vtssDhcpServerConfigReservedAction OBJECT-TYPE
    SYNTAX      VTSSRowEditorState
    MAX-ACCESS  read-write
    STATUS      current
    DESCRIPTION
        "Action"
    ::= { vtssDhcpServerConfigReservedEntry 100 }

vtssDhcpServerConfigReservedIpTableRowEditor OBJECT IDENTIFIER
    ::= { vtssDhcpServerConfig 8 }

vtssDhcpServerConfigReservedIpTableRowEditorPoolName OBJECT-TYPE
    SYNTAX      VTSSDisplayString (SIZE(0..32))
    MAX-ACCESS  read-write
    STATUS      current
    DESCRIPTION
        "Name of DHCP pool."
    ::= { vtssDhcpServerConfigReservedIpTableRowEditor 1 }

vtssDhcpServerConfigReservedIpTableRowEditorIpAddress OBJECT-TYPE
    SYNTAX      IpAddress
    MAX-ACCESS  read-write
    STATUS      current
    DESCRIPTION
        "Reserved IP address."
    ::= { vtssDhcpServerConfigReservedIpTableRowEditor 2 }

vtssDhcpServerConfigReservedIpTableRowEditorIfIndex OBJECT-TYPE
    SYNTAX      VTSSInterfaceIndex
    MAX-ACCESS  read-write
    STATUS      current
    DESCRIPTION
        "Logical interface number for the interface for which the ip address is
         reserved."
    ::= { vtssDhcpServerConfigReservedIpTableRowEditor 3 }

vtssDhcpServerConfigReservedIpTableRowEditorAction OBJECT-TYPE
    SYNTAX      VTSSRowEditorState
    MAX-ACCESS  read-write
    STATUS      current
    DESCRIPTION
        "Action"
    ::= { vtssDhcpServerConfigReservedIpTableRowEditor 100 }

vtssDhcpServerStatus OBJECT IDENTIFIER
    ::= { vtssDhcpServerMibObjects 3 }

vtssDhcpServerStatusDeclinedTable OBJECT-TYPE
    SYNTAX      SEQUENCE OF VTSSDhcpServerStatusDeclinedEntry
    MAX-ACCESS  not-accessible
    STATUS      current
    DESCRIPTION
        "This is a table of IP addresses declined by DHCP client."
    ::= { vtssDhcpServerStatus 1 }

vtssDhcpServerStatusDeclinedEntry OBJECT-TYPE
    SYNTAX      VTSSDhcpServerStatusDeclinedEntry
    MAX-ACCESS  not-accessible
    STATUS      current
    DESCRIPTION
        "Each entry has a declined IP address."
    INDEX       { vtssDhcpServerStatusDeclinedEntryNo }
    ::= { vtssDhcpServerStatusDeclinedTable 1 }

VTSSDhcpServerStatusDeclinedEntry ::= SEQUENCE {
    vtssDhcpServerStatusDeclinedEntryNo      Integer32,
    vtssDhcpServerStatusDeclinedIpv4Address  IpAddress
}

vtssDhcpServerStatusDeclinedEntryNo OBJECT-TYPE
    SYNTAX      Integer32 (0..2147483647)
    MAX-ACCESS  accessible-for-notify
    STATUS      current
    DESCRIPTION
        "The number of entry. The number starts from 1."
    ::= { vtssDhcpServerStatusDeclinedEntry 1 }

vtssDhcpServerStatusDeclinedIpv4Address OBJECT-TYPE
    SYNTAX      IpAddress
    MAX-ACCESS  read-only
    STATUS      current
    DESCRIPTION
        "IPv4 address declined by DHCP client."
    ::= { vtssDhcpServerStatusDeclinedEntry 2 }

vtssDhcpServerStatusStatistics OBJECT IDENTIFIER
    ::= { vtssDhcpServerStatus 2 }

vtssDhcpServerStatusStatisticsDiscoverCnt OBJECT-TYPE
    SYNTAX      Unsigned32
    MAX-ACCESS  read-only
    STATUS      current
    DESCRIPTION
        "Number of DHCP DISCOVER messages received."
    ::= { vtssDhcpServerStatusStatistics 1 }

vtssDhcpServerStatusStatisticsOfferCnt OBJECT-TYPE
    SYNTAX      Unsigned32
    MAX-ACCESS  read-only
    STATUS      current
    DESCRIPTION
        "Number of DHCP OFFER messages sent."
    ::= { vtssDhcpServerStatusStatistics 2 }

vtssDhcpServerStatusStatisticsRequestCnt OBJECT-TYPE
    SYNTAX      Unsigned32
    MAX-ACCESS  read-only
    STATUS      current
    DESCRIPTION
        "Number of DHCP REQUEST messages received."
    ::= { vtssDhcpServerStatusStatistics 3 }

vtssDhcpServerStatusStatisticsAckCnt OBJECT-TYPE
    SYNTAX      Unsigned32
    MAX-ACCESS  read-only
    STATUS      current
    DESCRIPTION
        "Number of DHCP ACK messages sent."
    ::= { vtssDhcpServerStatusStatistics 4 }

vtssDhcpServerStatusStatisticsNakCnt OBJECT-TYPE
    SYNTAX      Unsigned32
    MAX-ACCESS  read-only
    STATUS      current
    DESCRIPTION
        "Number of DHCP NAK messages sent."
    ::= { vtssDhcpServerStatusStatistics 5 }

vtssDhcpServerStatusStatisticsDeclineCnt OBJECT-TYPE
    SYNTAX      Unsigned32
    MAX-ACCESS  read-only
    STATUS      current
    DESCRIPTION
        "Number of DHCP DECLINE messages received."
    ::= { vtssDhcpServerStatusStatistics 6 }

vtssDhcpServerStatusStatisticsReleaseCnt OBJECT-TYPE
    SYNTAX      Unsigned32
    MAX-ACCESS  read-only
    STATUS      current
    DESCRIPTION
        "Number of DHCP RELEASE messages received."
    ::= { vtssDhcpServerStatusStatistics 7 }

vtssDhcpServerStatusStatisticsInformCnt OBJECT-TYPE
    SYNTAX      Unsigned32
    MAX-ACCESS  read-only
    STATUS      current
    DESCRIPTION
        "Number of DHCP INFORM messages received."
    ::= { vtssDhcpServerStatusStatistics 8 }

vtssDhcpServerStatusBindingTable OBJECT-TYPE
    SYNTAX      SEQUENCE OF VTSSDhcpServerStatusBindingEntry
    MAX-ACCESS  not-accessible
    STATUS      current
    DESCRIPTION
        "This is a table of binding data."
    ::= { vtssDhcpServerStatus 3 }

vtssDhcpServerStatusBindingEntry OBJECT-TYPE
    SYNTAX      VTSSDhcpServerStatusBindingEntry
    MAX-ACCESS  not-accessible
    STATUS      current
    DESCRIPTION
        "Each entry has the binding data."
    INDEX       { vtssDhcpServerStatusBindingIpAddress }
    ::= { vtssDhcpServerStatusBindingTable 1 }

VTSSDhcpServerStatusBindingEntry ::= SEQUENCE {
    vtssDhcpServerStatusBindingIpAddress             IpAddress,
    vtssDhcpServerStatusBindingState                 VTSSDhcpServerBindingStateEnum,
    vtssDhcpServerStatusBindingType                  VTSSDhcpServerBindingEnum,
    vtssDhcpServerStatusBindingPoolName              VTSSDisplayString,
    vtssDhcpServerStatusBindingServerId              IpAddress,
    vtssDhcpServerStatusBindingVlanId                VTSSUnsigned16,
    vtssDhcpServerStatusBindingSubnetMask            IpAddress,
    vtssDhcpServerStatusBindingClientIdentifierType  VTSSDhcpServerClientIdentifierEnum,
    vtssDhcpServerStatusBindingClientIdentifierName  VTSSDisplayString,
    vtssDhcpServerStatusBindingClientIdentifierMac   MacAddress,
    vtssDhcpServerStatusBindingMacAddress            MacAddress,
    vtssDhcpServerStatusBindingLease                 VTSSDisplayString,
    vtssDhcpServerStatusBindingTimeToExpire          VTSSDisplayString
}

vtssDhcpServerStatusBindingIpAddress OBJECT-TYPE
    SYNTAX      IpAddress
    MAX-ACCESS  accessible-for-notify
    STATUS      current
    DESCRIPTION
        "IP address."
    ::= { vtssDhcpServerStatusBindingEntry 1 }

vtssDhcpServerStatusBindingState OBJECT-TYPE
    SYNTAX      VTSSDhcpServerBindingStateEnum
    MAX-ACCESS  read-only
    STATUS      current
    DESCRIPTION
        "State of binding. none(0) means the binding is not in use. allocated(1)
         means the binding is allocated to the new DHCP client who send
         DHCPDISCOVER. committed(2) means the binding is committed as the DHCP
         process is completed successfully. expired(3) means the lease of the
         binding expired."
    ::= { vtssDhcpServerStatusBindingEntry 2 }

vtssDhcpServerStatusBindingType OBJECT-TYPE
    SYNTAX      VTSSDhcpServerBindingEnum
    MAX-ACCESS  read-only
    STATUS      current
    DESCRIPTION
        "Type of binding. none(0) means the binding is not in use. automatic(1)
         means the binding is mapped to network-type pool. manual(2) means the
         binding is mapped to host-type pool. expired(3) means the lease of the
         binding expired."
    ::= { vtssDhcpServerStatusBindingEntry 3 }

vtssDhcpServerStatusBindingPoolName OBJECT-TYPE
    SYNTAX      VTSSDisplayString (SIZE(0..32))
    MAX-ACCESS  read-only
    STATUS      current
    DESCRIPTION
        "Name of the pool that creates the binding."
    ::= { vtssDhcpServerStatusBindingEntry 4 }

vtssDhcpServerStatusBindingServerId OBJECT-TYPE
    SYNTAX      IpAddress
    MAX-ACCESS  read-only
    STATUS      current
    DESCRIPTION
        "IP address of the DHCP server to service the binding."
    ::= { vtssDhcpServerStatusBindingEntry 5 }

vtssDhcpServerStatusBindingVlanId OBJECT-TYPE
    SYNTAX      VTSSUnsigned16
    MAX-ACCESS  read-only
    STATUS      current
    DESCRIPTION
        "The VLAN where the binding works on."
    ::= { vtssDhcpServerStatusBindingEntry 6 }

vtssDhcpServerStatusBindingSubnetMask OBJECT-TYPE
    SYNTAX      IpAddress
    MAX-ACCESS  read-only
    STATUS      current
    DESCRIPTION
        "Subnet mask of the DHCP client."
    ::= { vtssDhcpServerStatusBindingEntry 7 }

vtssDhcpServerStatusBindingClientIdentifierType OBJECT-TYPE
    SYNTAX      VTSSDhcpServerClientIdentifierEnum
    MAX-ACCESS  read-only
    STATUS      current
    DESCRIPTION
        "Type of client identifier. DHCP option 61. Specify client's unique
         identifier to be used when the pool is the type of host. none(0) means
         the client identifier type is not defined yet. name(1) means the client
         identifier type is other than hardware. mac(2) means the client
         identifier type is type of MAC address."
    ::= { vtssDhcpServerStatusBindingEntry 8 }

vtssDhcpServerStatusBindingClientIdentifierName OBJECT-TYPE
    SYNTAX      VTSSDisplayString (SIZE(0..64))
    MAX-ACCESS  read-only
    STATUS      current
    DESCRIPTION
        "Client identifier which type is other than hardware. DHCP option 61."
    ::= { vtssDhcpServerStatusBindingEntry 9 }

vtssDhcpServerStatusBindingClientIdentifierMac OBJECT-TYPE
    SYNTAX      MacAddress
    MAX-ACCESS  read-only
    STATUS      current
    DESCRIPTION
        "Client's MAC address. DHCP option 61."
    ::= { vtssDhcpServerStatusBindingEntry 10 }

vtssDhcpServerStatusBindingMacAddress OBJECT-TYPE
    SYNTAX      MacAddress
    MAX-ACCESS  read-only
    STATUS      current
    DESCRIPTION
        "MAC address of the DHCP client."
    ::= { vtssDhcpServerStatusBindingEntry 11 }

vtssDhcpServerStatusBindingLease OBJECT-TYPE
    SYNTAX      VTSSDisplayString (SIZE(0..64))
    MAX-ACCESS  read-only
    STATUS      current
    DESCRIPTION
        "Lease time of the binding."
    ::= { vtssDhcpServerStatusBindingEntry 12 }

vtssDhcpServerStatusBindingTimeToExpire OBJECT-TYPE
    SYNTAX      VTSSDisplayString (SIZE(0..64))
    MAX-ACCESS  read-only
    STATUS      current
    DESCRIPTION
        "remaining time to expire."
    ::= { vtssDhcpServerStatusBindingEntry 13 }

vtssDhcpServerControl OBJECT IDENTIFIER
    ::= { vtssDhcpServerMibObjects 4 }

vtssDhcpServerControlStatistics OBJECT IDENTIFIER
    ::= { vtssDhcpServerControl 1 }

vtssDhcpServerControlStatisticsClear OBJECT-TYPE
    SYNTAX      TruthValue
    MAX-ACCESS  read-write
    STATUS      current
    DESCRIPTION
        "Clear all statistics."
    ::= { vtssDhcpServerControlStatistics 1 }

vtssDhcpServerControlBinding OBJECT IDENTIFIER
    ::= { vtssDhcpServerControl 2 }

vtssDhcpServerControlBindingClearByIp OBJECT-TYPE
    SYNTAX      IpAddress
    MAX-ACCESS  read-write
    STATUS      current
    DESCRIPTION
        "Clear binding with the IP address. If 0.0.0.0 then do nothing."
    ::= { vtssDhcpServerControlBinding 1 }

vtssDhcpServerControlBindingClearByType OBJECT-TYPE
    SYNTAX      VTSSDhcpServerBindingEnum
    MAX-ACCESS  read-write
    STATUS      current
    DESCRIPTION
        "Clear binding by binding type. If none(0) then do nothing."
    ::= { vtssDhcpServerControlBinding 2 }

vtssDhcpServerMibConformance OBJECT IDENTIFIER
    ::= { vtssDhcpServerMib 2 }

vtssDhcpServerMibCompliances OBJECT IDENTIFIER
    ::= { vtssDhcpServerMibConformance 1 }

vtssDhcpServerMibGroups OBJECT IDENTIFIER
    ::= { vtssDhcpServerMibConformance 2 }

vtssDhcpServerConfigGlobalsInfoGroup OBJECT-GROUP
    OBJECTS     { vtssDhcpServerConfigGlobalsMode }
    STATUS      current
    DESCRIPTION
        "A collection of objects."
    ::= { vtssDhcpServerMibGroups 1 }

vtssDhcpServerConfigVlanTableInfoGroup OBJECT-GROUP
    OBJECTS     { vtssDhcpServerConfigVlanIfIndex,
                  vtssDhcpServerConfigVlanMode }
    STATUS      current
    DESCRIPTION
        "A collection of objects."
    ::= { vtssDhcpServerMibGroups 2 }

vtssDhcpServerConfigExcludedTableInfoGroup OBJECT-GROUP
    OBJECTS     { vtssDhcpServerConfigExcludedLowIpAddress,
                  vtssDhcpServerConfigExcludedHighIpAddress,
                  vtssDhcpServerConfigExcludedAction }
    STATUS      current
    DESCRIPTION
        "A collection of objects."
    ::= { vtssDhcpServerMibGroups 3 }

vtssDhcpServerConfigExcludedIpTableRowEditorInfoGroup OBJECT-GROUP
    OBJECTS     {                   vtssDhcpServerConfigExcludedIpTableRowEditorLowIpAddress,
                  vtssDhcpServerConfigExcludedIpTableRowEditorHighIpAddress,
                  vtssDhcpServerConfigExcludedIpTableRowEditorAction }
    STATUS      current
    DESCRIPTION
        "A collection of objects."
    ::= { vtssDhcpServerMibGroups 4 }

vtssDhcpServerConfigPoolTableInfoGroup OBJECT-GROUP
    OBJECTS     { vtssDhcpServerConfigPoolPoolName,
                  vtssDhcpServerConfigPoolPoolType,
                  vtssDhcpServerConfigPoolIpv4Address,
                  vtssDhcpServerConfigPoolSubnetMask,
                  vtssDhcpServerConfigPoolSubnetBroadcast,
                  vtssDhcpServerConfigPoolLeaseDay,
                  vtssDhcpServerConfigPoolLeaseHour,
                  vtssDhcpServerConfigPoolLeaseMinute,
                  vtssDhcpServerConfigPoolDomainName,
                  vtssDhcpServerConfigPoolDefaultRouter1,
                  vtssDhcpServerConfigPoolDefaultRouter2,
                  vtssDhcpServerConfigPoolDefaultRouter3,
                  vtssDhcpServerConfigPoolDefaultRouter4,
                  vtssDhcpServerConfigPoolDnsServer1,
                  vtssDhcpServerConfigPoolDnsServer2,
                  vtssDhcpServerConfigPoolDnsServer3,
                  vtssDhcpServerConfigPoolDnsServer4,
                  vtssDhcpServerConfigPoolNtpServer1,
                  vtssDhcpServerConfigPoolNtpServer2,
                  vtssDhcpServerConfigPoolNtpServer3,
                  vtssDhcpServerConfigPoolNtpServer4,
                  vtssDhcpServerConfigPoolNetbiosNodeType,
                  vtssDhcpServerConfigPoolNetbiosScope,
                  vtssDhcpServerConfigPoolNetbiosNameServer1,
                  vtssDhcpServerConfigPoolNetbiosNameServer2,
                  vtssDhcpServerConfigPoolNetbiosNameServer3,
                  vtssDhcpServerConfigPoolNetbiosNameServer4,
                  vtssDhcpServerConfigPoolNisDomainName,
                  vtssDhcpServerConfigPoolNisServer1,
                  vtssDhcpServerConfigPoolNisServer2,
                  vtssDhcpServerConfigPoolNisServer3,
                  vtssDhcpServerConfigPoolNisServer4,
                  vtssDhcpServerConfigPoolClientIdentifierType,
                  vtssDhcpServerConfigPoolClientIdentifierName,
                  vtssDhcpServerConfigPoolClientIdentifierMac,
                  vtssDhcpServerConfigPoolClientHardwareAddress,
                  vtssDhcpServerConfigPoolClientName,
                  vtssDhcpServerConfigPoolVendorClassId1,
                  vtssDhcpServerConfigPoolVendorSpecificInfo1,
                  vtssDhcpServerConfigPoolVendorClassId2,
                  vtssDhcpServerConfigPoolVendorSpecificInfo2,
                  vtssDhcpServerConfigPoolVendorClassId3,
                  vtssDhcpServerConfigPoolVendorSpecificInfo3,
                  vtssDhcpServerConfigPoolVendorClassId4,
                  vtssDhcpServerConfigPoolVendorSpecificInfo4,
                  vtssDhcpServerConfigPoolReservedOnly,
                  vtssDhcpServerConfigPoolAction }
    STATUS      current
    DESCRIPTION
        "A collection of objects."
    ::= { vtssDhcpServerMibGroups 5 }

vtssDhcpServerConfigPoolTableRowEditorInfoGroup OBJECT-GROUP
    OBJECTS     { vtssDhcpServerConfigPoolTableRowEditorPoolName,
                  vtssDhcpServerConfigPoolTableRowEditorPoolType,
                  vtssDhcpServerConfigPoolTableRowEditorIpv4Address,
                  vtssDhcpServerConfigPoolTableRowEditorSubnetMask,
                  vtssDhcpServerConfigPoolTableRowEditorSubnetBroadcast,
                  vtssDhcpServerConfigPoolTableRowEditorLeaseDay,
                  vtssDhcpServerConfigPoolTableRowEditorLeaseHour,
                  vtssDhcpServerConfigPoolTableRowEditorLeaseMinute,
                  vtssDhcpServerConfigPoolTableRowEditorDomainName,
                  vtssDhcpServerConfigPoolTableRowEditorDefaultRouter1,
                  vtssDhcpServerConfigPoolTableRowEditorDefaultRouter2,
                  vtssDhcpServerConfigPoolTableRowEditorDefaultRouter3,
                  vtssDhcpServerConfigPoolTableRowEditorDefaultRouter4,
                  vtssDhcpServerConfigPoolTableRowEditorDnsServer1,
                  vtssDhcpServerConfigPoolTableRowEditorDnsServer2,
                  vtssDhcpServerConfigPoolTableRowEditorDnsServer3,
                  vtssDhcpServerConfigPoolTableRowEditorDnsServer4,
                  vtssDhcpServerConfigPoolTableRowEditorNtpServer1,
                  vtssDhcpServerConfigPoolTableRowEditorNtpServer2,
                  vtssDhcpServerConfigPoolTableRowEditorNtpServer3,
                  vtssDhcpServerConfigPoolTableRowEditorNtpServer4,
                  vtssDhcpServerConfigPoolTableRowEditorNetbiosNodeType,
                  vtssDhcpServerConfigPoolTableRowEditorNetbiosScope,
                  vtssDhcpServerConfigPoolTableRowEditorNetbiosNameServer1,
                  vtssDhcpServerConfigPoolTableRowEditorNetbiosNameServer2,
                  vtssDhcpServerConfigPoolTableRowEditorNetbiosNameServer3,
                  vtssDhcpServerConfigPoolTableRowEditorNetbiosNameServer4,
                  vtssDhcpServerConfigPoolTableRowEditorNisDomainName,
                  vtssDhcpServerConfigPoolTableRowEditorNisServer1,
                  vtssDhcpServerConfigPoolTableRowEditorNisServer2,
                  vtssDhcpServerConfigPoolTableRowEditorNisServer3,
                  vtssDhcpServerConfigPoolTableRowEditorNisServer4,
                  vtssDhcpServerConfigPoolTableRowEditorClientIdentifierType,
                  vtssDhcpServerConfigPoolTableRowEditorClientIdentifierName,
                  vtssDhcpServerConfigPoolTableRowEditorClientIdentifierMac,
                  vtssDhcpServerConfigPoolTableRowEditorClientHardwareAddress,
                  vtssDhcpServerConfigPoolTableRowEditorClientName,
                  vtssDhcpServerConfigPoolTableRowEditorVendorClassId1,
                  vtssDhcpServerConfigPoolTableRowEditorVendorSpecificInfo1,
                  vtssDhcpServerConfigPoolTableRowEditorVendorClassId2,
                  vtssDhcpServerConfigPoolTableRowEditorVendorSpecificInfo2,
                  vtssDhcpServerConfigPoolTableRowEditorVendorClassId3,
                  vtssDhcpServerConfigPoolTableRowEditorVendorSpecificInfo3,
                  vtssDhcpServerConfigPoolTableRowEditorVendorClassId4,
                  vtssDhcpServerConfigPoolTableRowEditorVendorSpecificInfo4,
                  vtssDhcpServerConfigPoolTableRowEditorReservedOnly,
                  vtssDhcpServerConfigPoolTableRowEditorAction }
    STATUS      current
    DESCRIPTION
        "A collection of objects."
    ::= { vtssDhcpServerMibGroups 6 }

vtssDhcpServerConfigReservedTableInfoGroup OBJECT-GROUP
    OBJECTS     { vtssDhcpServerConfigReservedPoolName,
                  vtssDhcpServerConfigReservedIpAddress,
                  vtssDhcpServerConfigReservedIfIndex,
                  vtssDhcpServerConfigReservedAction }
    STATUS      current
    DESCRIPTION
        "A collection of objects."
    ::= { vtssDhcpServerMibGroups 7 }

vtssDhcpServerConfigReservedIpTableRowEditorInfoGroup OBJECT-GROUP
    OBJECTS     {                   vtssDhcpServerConfigReservedIpTableRowEditorPoolName,
                  vtssDhcpServerConfigReservedIpTableRowEditorIpAddress,
                  vtssDhcpServerConfigReservedIpTableRowEditorIfIndex,
                  vtssDhcpServerConfigReservedIpTableRowEditorAction }
    STATUS      current
    DESCRIPTION
        "A collection of objects."
    ::= { vtssDhcpServerMibGroups 8 }

vtssDhcpServerStatusDeclinedTableInfoGroup OBJECT-GROUP
    OBJECTS     { vtssDhcpServerStatusDeclinedEntryNo,
                  vtssDhcpServerStatusDeclinedIpv4Address }
    STATUS      current
    DESCRIPTION
        "A collection of objects."
    ::= { vtssDhcpServerMibGroups 9 }

vtssDhcpServerStatusStatisticsInfoGroup OBJECT-GROUP
    OBJECTS     { vtssDhcpServerStatusStatisticsDiscoverCnt,
                  vtssDhcpServerStatusStatisticsOfferCnt,
                  vtssDhcpServerStatusStatisticsRequestCnt,
                  vtssDhcpServerStatusStatisticsAckCnt,
                  vtssDhcpServerStatusStatisticsNakCnt,
                  vtssDhcpServerStatusStatisticsDeclineCnt,
                  vtssDhcpServerStatusStatisticsReleaseCnt,
                  vtssDhcpServerStatusStatisticsInformCnt }
    STATUS      current
    DESCRIPTION
        "A collection of objects."
    ::= { vtssDhcpServerMibGroups 10 }

vtssDhcpServerStatusBindingTableInfoGroup OBJECT-GROUP
    OBJECTS     { vtssDhcpServerStatusBindingIpAddress,
                  vtssDhcpServerStatusBindingState,
                  vtssDhcpServerStatusBindingType,
                  vtssDhcpServerStatusBindingPoolName,
                  vtssDhcpServerStatusBindingServerId,
                  vtssDhcpServerStatusBindingVlanId,
                  vtssDhcpServerStatusBindingSubnetMask,
                  vtssDhcpServerStatusBindingClientIdentifierType,
                  vtssDhcpServerStatusBindingClientIdentifierName,
                  vtssDhcpServerStatusBindingClientIdentifierMac,
                  vtssDhcpServerStatusBindingMacAddress,
                  vtssDhcpServerStatusBindingLease,
                  vtssDhcpServerStatusBindingTimeToExpire }
    STATUS      current
    DESCRIPTION
        "A collection of objects."
    ::= { vtssDhcpServerMibGroups 11 }

vtssDhcpServerControlStatisticsInfoGroup OBJECT-GROUP
    OBJECTS     { vtssDhcpServerControlStatisticsClear }
    STATUS      current
    DESCRIPTION
        "A collection of objects."
    ::= { vtssDhcpServerMibGroups 12 }

vtssDhcpServerControlBindingInfoGroup OBJECT-GROUP
    OBJECTS     { vtssDhcpServerControlBindingClearByIp,
                  vtssDhcpServerControlBindingClearByType }
    STATUS      current
    DESCRIPTION
        "A collection of objects."
    ::= { vtssDhcpServerMibGroups 13 }

vtssDhcpServerMibCompliance MODULE-COMPLIANCE
    STATUS      current
    DESCRIPTION
        "The compliance statement for the implementation."

    MODULE      -- this module

    MANDATORY-GROUPS { vtssDhcpServerConfigGlobalsInfoGroup,
                       vtssDhcpServerConfigVlanTableInfoGroup,
                       vtssDhcpServerConfigExcludedTableInfoGroup,
                       vtssDhcpServerConfigExcludedIpTableRowEditorInfoGroup,
                       vtssDhcpServerConfigPoolTableInfoGroup,
                       vtssDhcpServerConfigPoolTableRowEditorInfoGroup,
                       vtssDhcpServerConfigReservedTableInfoGroup,
                       vtssDhcpServerConfigReservedIpTableRowEditorInfoGroup,
                       vtssDhcpServerStatusDeclinedTableInfoGroup,
                       vtssDhcpServerStatusStatisticsInfoGroup,
                       vtssDhcpServerStatusBindingTableInfoGroup,
                       vtssDhcpServerControlStatisticsInfoGroup,
                       vtssDhcpServerControlBindingInfoGroup }

    ::= { vtssDhcpServerMibCompliances 1 }

END
