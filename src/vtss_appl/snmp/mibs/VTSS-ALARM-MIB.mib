-- *****************************************************************
-- ALARM-MIB:  Microsemi ENT private MIB
-- ****************************************************************

VTSS-ALARM-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    TruthValue FROM SNMPv2-TC
    VTSSDisplayString FROM VTSS-TC
    VTSSRowEditorState FROM VTSS-TC
    ;

vtssAlarmMib MODULE-IDENTITY
    LAST-UPDATED "201602080000Z"
    ORGANIZATION
        "Microsemi Corporation"
    CONTACT-INFO
        "Application support: http://www.microchip.com/support"
    DESCRIPTION
        "This is a private mib for alarms"
    REVISION    "201602080000Z"
    DESCRIPTION
        "Initial version"
    ::= { vtssSwitchMgmt 136 }


vtssAlarmMibObjects OBJECT IDENTIFIER
    ::= { vtssAlarmMib 1 }

vtssAlarmConfig OBJECT IDENTIFIER
    ::= { vtssAlarmMibObjects 2 }

vtssAlarmConfigTable OBJECT-TYPE
    SYNTAX      SEQUENCE OF VTSSAlarmConfigEntry
    MAX-ACCESS  not-accessible
    STATUS      current
    DESCRIPTION
        "The table is the list of configured alarms. The index is the name of
         the alarm"
    ::= { vtssAlarmConfig 1 }

vtssAlarmConfigEntry OBJECT-TYPE
    SYNTAX      VTSSAlarmConfigEntry
    MAX-ACCESS  not-accessible
    STATUS      current
    DESCRIPTION
        "An index is a dotted name e.g. alarm.port.status"
    INDEX       { vtssAlarmConfigAlarmName }
    ::= { vtssAlarmConfigTable 1 }

VTSSAlarmConfigEntry ::= SEQUENCE {
    vtssAlarmConfigAlarmName   VTSSDisplayString,
    vtssAlarmConfigExpression  VTSSDisplayString,
    vtssAlarmConfigAction      VTSSRowEditorState
}

vtssAlarmConfigAlarmName OBJECT-TYPE
    SYNTAX      VTSSDisplayString (SIZE(0..99))
    MAX-ACCESS  accessible-for-notify
    STATUS      current
    DESCRIPTION
        "The name of the alarm"
    ::= { vtssAlarmConfigEntry 1 }

vtssAlarmConfigExpression OBJECT-TYPE
    SYNTAX      VTSSDisplayString (SIZE(0..1023))
    MAX-ACCESS  read-write
    STATUS      current
    DESCRIPTION
        "The expression defining the alarm."
    ::= { vtssAlarmConfigEntry 2 }

vtssAlarmConfigAction OBJECT-TYPE
    SYNTAX      VTSSRowEditorState
    MAX-ACCESS  read-write
    STATUS      current
    DESCRIPTION
        "Action"
    ::= { vtssAlarmConfigEntry 100 }

vtssAlarmConfigTableRowEditor OBJECT IDENTIFIER
    ::= { vtssAlarmConfig 2 }

vtssAlarmConfigTableRowEditorAlarmName OBJECT-TYPE
    SYNTAX      VTSSDisplayString (SIZE(0..99))
    MAX-ACCESS  read-write
    STATUS      current
    DESCRIPTION
        "The name of the alarm"
    ::= { vtssAlarmConfigTableRowEditor 1 }

vtssAlarmConfigTableRowEditorExpression OBJECT-TYPE
    SYNTAX      VTSSDisplayString (SIZE(0..1023))
    MAX-ACCESS  read-write
    STATUS      current
    DESCRIPTION
        "The expression defining the alarm."
    ::= { vtssAlarmConfigTableRowEditor 2 }

vtssAlarmConfigTableRowEditorAction OBJECT-TYPE
    SYNTAX      VTSSRowEditorState
    MAX-ACCESS  read-write
    STATUS      current
    DESCRIPTION
        "Action"
    ::= { vtssAlarmConfigTableRowEditor 100 }

vtssAlarmStatus OBJECT IDENTIFIER
    ::= { vtssAlarmMibObjects 3 }

vtssAlarmStatusTable OBJECT-TYPE
    SYNTAX      SEQUENCE OF VTSSAlarmStatusEntry
    MAX-ACCESS  not-accessible
    STATUS      current
    DESCRIPTION
        "The table is the list of alarm nodes. The index is the name of the
         alarm node"
    ::= { vtssAlarmStatus 1 }

vtssAlarmStatusEntry OBJECT-TYPE
    SYNTAX      VTSSAlarmStatusEntry
    MAX-ACCESS  not-accessible
    STATUS      current
    DESCRIPTION
        "An index is a dotted name e.g. alarm.port.status"
    INDEX       { vtssAlarmStatusAlarmName }
    ::= { vtssAlarmStatusTable 1 }

VTSSAlarmStatusEntry ::= SEQUENCE {
    vtssAlarmStatusAlarmName      VTSSDisplayString,
    vtssAlarmStatusSuppressed     TruthValue,
    vtssAlarmStatusActive         TruthValue,
    vtssAlarmStatusExposedActive  TruthValue
}

vtssAlarmStatusAlarmName OBJECT-TYPE
    SYNTAX      VTSSDisplayString (SIZE(0..99))
    MAX-ACCESS  accessible-for-notify
    STATUS      current
    DESCRIPTION
        "The name of the alarm"
    ::= { vtssAlarmStatusEntry 1 }

vtssAlarmStatusSuppressed OBJECT-TYPE
    SYNTAX      TruthValue
    MAX-ACCESS  read-only
    STATUS      current
    DESCRIPTION
        "Indicates whether the alarm subtree is suppressed. When a subtree is
         suppressed, the status does not contribute to the state of the superior
         alarm tree."
    ::= { vtssAlarmStatusEntry 2 }

vtssAlarmStatusActive OBJECT-TYPE
    SYNTAX      TruthValue
    MAX-ACCESS  read-only
    STATUS      current
    DESCRIPTION
        "Indicates whether the alarm is active"
    ::= { vtssAlarmStatusEntry 3 }

vtssAlarmStatusExposedActive OBJECT-TYPE
    SYNTAX      TruthValue
    MAX-ACCESS  read-only
    STATUS      current
    DESCRIPTION
        "The exposed alarm status."
    ::= { vtssAlarmStatusEntry 4 }

vtssAlarmControl OBJECT IDENTIFIER
    ::= { vtssAlarmMibObjects 4 }

vtssAlarmControlTable OBJECT-TYPE
    SYNTAX      SEQUENCE OF VTSSAlarmControlEntry
    MAX-ACCESS  not-accessible
    STATUS      current
    DESCRIPTION
        "The table is the list of alarm nodes. The index is the name of the
         alarm node"
    ::= { vtssAlarmControl 1 }

vtssAlarmControlEntry OBJECT-TYPE
    SYNTAX      VTSSAlarmControlEntry
    MAX-ACCESS  not-accessible
    STATUS      current
    DESCRIPTION
        "An index is a dotted name e.g. alarm.port.status"
    INDEX       { vtssAlarmControlAlarmName }
    ::= { vtssAlarmControlTable 1 }

VTSSAlarmControlEntry ::= SEQUENCE {
    vtssAlarmControlAlarmName  VTSSDisplayString,
    vtssAlarmControlSuppress   TruthValue
}

vtssAlarmControlAlarmName OBJECT-TYPE
    SYNTAX      VTSSDisplayString (SIZE(0..99))
    MAX-ACCESS  accessible-for-notify
    STATUS      current
    DESCRIPTION
        "The name of the alarm"
    ::= { vtssAlarmControlEntry 1 }

vtssAlarmControlSuppress OBJECT-TYPE
    SYNTAX      TruthValue
    MAX-ACCESS  read-write
    STATUS      current
    DESCRIPTION
        "Indicates whether to suppress the alarm subtree. When a subtree is
         suppressed, the status does not contribute to the state of the superior
         alarm tree."
    ::= { vtssAlarmControlEntry 2 }

vtssAlarmTrap OBJECT IDENTIFIER
    ::= { vtssAlarmMibObjects 6 }

vtssAlarmTrapStatusAdd NOTIFICATION-TYPE
    OBJECTS     { vtssAlarmStatusAlarmName, vtssAlarmStatusSuppressed,
                  vtssAlarmStatusActive, vtssAlarmStatusExposedActive }
    STATUS      current
    DESCRIPTION
        "This trap signals that a row has been added. The index(es) and value(s)
         of the row is included in the trap."

    ::= { vtssAlarmTrap 1 }

vtssAlarmTrapStatusMod NOTIFICATION-TYPE
    OBJECTS     { vtssAlarmStatusAlarmName, vtssAlarmStatusSuppressed,
                  vtssAlarmStatusActive, vtssAlarmStatusExposedActive }
    STATUS      current
    DESCRIPTION
        "This trap signals that one or more of the objects included in the trap
          has been updated."

    ::= { vtssAlarmTrap 2 }

vtssAlarmTrapStatusDel NOTIFICATION-TYPE
    OBJECTS     { vtssAlarmStatusAlarmName }
    STATUS      current
    DESCRIPTION
        "This trap signals that a row has been deleted. The index(es) of the
         row is included in the trap."

    ::= { vtssAlarmTrap 3 }

vtssAlarmMibConformance OBJECT IDENTIFIER
    ::= { vtssAlarmMib 2 }

vtssAlarmMibCompliances OBJECT IDENTIFIER
    ::= { vtssAlarmMibConformance 1 }

vtssAlarmMibGroups OBJECT IDENTIFIER
    ::= { vtssAlarmMibConformance 2 }

vtssAlarmConfigTableInfoGroup OBJECT-GROUP
    OBJECTS     { vtssAlarmConfigAlarmName, vtssAlarmConfigExpression,
                  vtssAlarmConfigAction }
    STATUS      current
    DESCRIPTION
        "A collection of objects."
    ::= { vtssAlarmMibGroups 1 }

vtssAlarmConfigTableRowEditorInfoGroup OBJECT-GROUP
    OBJECTS     { vtssAlarmConfigTableRowEditorAlarmName,
                  vtssAlarmConfigTableRowEditorExpression,
                  vtssAlarmConfigTableRowEditorAction }
    STATUS      current
    DESCRIPTION
        "A collection of objects."
    ::= { vtssAlarmMibGroups 2 }

vtssAlarmStatusInfoGroup OBJECT-GROUP
    OBJECTS     { vtssAlarmStatusAlarmName, vtssAlarmStatusSuppressed,
                  vtssAlarmStatusActive, vtssAlarmStatusExposedActive }
    STATUS      current
    DESCRIPTION
        "A collection of objects."
    ::= { vtssAlarmMibGroups 3 }

vtssAlarmControlTableInfoGroup OBJECT-GROUP
    OBJECTS     { vtssAlarmControlAlarmName, vtssAlarmControlSuppress }
    STATUS      current
    DESCRIPTION
        "A collection of objects."
    ::= { vtssAlarmMibGroups 4 }

vtssAlarmTrapStatusAddInfoGroup NOTIFICATION-GROUP
    NOTIFICATIONS { vtssAlarmTrapStatusAdd }
    STATUS      current
    DESCRIPTION
        "Information group containing a trap."
    ::= { vtssAlarmMibGroups 5 }

vtssAlarmTrapStatusModInfoGroup NOTIFICATION-GROUP
    NOTIFICATIONS { vtssAlarmTrapStatusMod }
    STATUS      current
    DESCRIPTION
        "Information group containing a trap."
    ::= { vtssAlarmMibGroups 6 }

vtssAlarmTrapStatusDelInfoGroup NOTIFICATION-GROUP
    NOTIFICATIONS { vtssAlarmTrapStatusDel }
    STATUS      current
    DESCRIPTION
        "Information group containing a trap."
    ::= { vtssAlarmMibGroups 7 }

vtssAlarmMibCompliance MODULE-COMPLIANCE
    STATUS      current
    DESCRIPTION
        "The compliance statement for the implementation."

    MODULE      -- this module

    MANDATORY-GROUPS { vtssAlarmConfigTableInfoGroup,
                       vtssAlarmConfigTableRowEditorInfoGroup,
                       vtssAlarmStatusInfoGroup,
                       vtssAlarmControlTableInfoGroup,
                       vtssAlarmTrapStatusAddInfoGroup,
                       vtssAlarmTrapStatusModInfoGroup,
                       vtssAlarmTrapStatusDelInfoGroup }

    ::= { vtssAlarmMibCompliances 1 }

END
