-- *****************************************************************
-- UPNP-MIB:  Microsemi ENT private MIB
-- ****************************************************************

VTSS-UPNP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    TruthValue FROM SNMPv2-TC
    VTSSInterfaceIndex FROM VTSS-TC
    VTSSUnsigned8 FROM VTSS-TC
    ;

vtssUpnpMib MODULE-IDENTITY
    LAST-UPDATED "201508170000Z"
    ORGANIZATION
        "Microsemi Corporation"
    CONTACT-INFO
        "Application support: http://www.microchip.com/support"
    DESCRIPTION
        "This is a private version of UPnP"
    REVISION    "201508170000Z"
    DESCRIPTION
        "Add parameters: IpAddressingMode/IpInterfaceId"
    REVISION    "201410100000Z"
    DESCRIPTION
        "Editorial changes"
    REVISION    "201407010000Z"
    DESCRIPTION
        "Initial version"
    ::= { vtssSwitchMgmt 52 }


VTSSUpnpIpAddressingModeType ::= TEXTUAL-CONVENTION
    STATUS      current
    DESCRIPTION
        "This enumeration indicates the type of IP addressing mode."
    SYNTAX      INTEGER { dynamic(0), static(1) }

vtssUpnpMibObjects OBJECT IDENTIFIER
    ::= { vtssUpnpMib 1 }

vtssUpnpCapabilities OBJECT IDENTIFIER
    ::= { vtssUpnpMibObjects 1 }

vtssUpnpCapabilitiesSupportTtlWrite OBJECT-TYPE
    SYNTAX      TruthValue
    MAX-ACCESS  read-only
    STATUS      current
    DESCRIPTION
        "The capability to support the authority of writing function."
    ::= { vtssUpnpCapabilities 1 }

vtssUpnpConfig OBJECT IDENTIFIER
    ::= { vtssUpnpMibObjects 2 }

vtssUpnpConfigGlobals OBJECT IDENTIFIER
    ::= { vtssUpnpConfig 1 }

vtssUpnpConfigGlobalsMode OBJECT-TYPE
    SYNTAX      TruthValue
    MAX-ACCESS  read-write
    STATUS      current
    DESCRIPTION
        "Global mode of UPnP. true is to enable the functions of HTTPS and false
         is to disable it."
    ::= { vtssUpnpConfigGlobals 1 }

vtssUpnpConfigGlobalsTtl OBJECT-TYPE
    SYNTAX      VTSSUnsigned8 (1..255)
    MAX-ACCESS  read-write
    STATUS      current
    DESCRIPTION
        "The TTL value is used by UPnP to send SSDP advertisement messages.Valid
         values are in the range 1 to 255. "
    ::= { vtssUpnpConfigGlobals 2 }

vtssUpnpConfigGlobalsAdvertisingDuration OBJECT-TYPE
    SYNTAX      Integer32 (100..86400)
    MAX-ACCESS  read-write
    STATUS      current
    DESCRIPTION
        "The duration, carried in SSDP packets, is used to inform a control
         point or control points how often it or they should receive an SSDP
         advertisement message from this switch. If a control point does not
         receive any message within the duration, it will think that the switch
         no longer exists. Due to the unreliable nature of UDP, in the standard
         it is recommended that such refreshing of advertisements to be done at
         less than one-half of the advertising duration. In the implementation,
         the switch sends SSDP messages periodically at the interval one-half of
         the advertising duration minus 30 seconds. Valid values are in the
         range 100 to 86400. "
    ::= { vtssUpnpConfigGlobals 3 }

vtssUpnpConfigGlobalsIpAddressingMode OBJECT-TYPE
    SYNTAX      VTSSUpnpIpAddressingModeType
    MAX-ACCESS  read-write
    STATUS      current
    DESCRIPTION
        "IP addressing mode provides two ways to determine IP address
         assignment: dynamic(0) and static(1). Dynamic: Default selection for
         UPnP. UPnP module helps users choosing the IP address of the switch
         device. It finds the first available system IP address. Static: User
         specifies the IP interface VLAN for choosing the IP address of the
         switch device."
    ::= { vtssUpnpConfigGlobals 4 }

vtssUpnpConfigGlobalsStaticIpInterfaceId OBJECT-TYPE
    SYNTAX      VTSSInterfaceIndex
    MAX-ACCESS  read-write
    STATUS      current
    DESCRIPTION
        "The index of the specific IP VLAN interface. It will only be applied
         when IP Addressing Mode is static. Valid configurable values ranges
         from 1 to 4095. Default value is 1."
    ::= { vtssUpnpConfigGlobals 5 }

vtssUpnpMibConformance OBJECT IDENTIFIER
    ::= { vtssUpnpMib 2 }

vtssUpnpMibCompliances OBJECT IDENTIFIER
    ::= { vtssUpnpMibConformance 1 }

vtssUpnpMibGroups OBJECT IDENTIFIER
    ::= { vtssUpnpMibConformance 2 }

vtssUpnpCapabilitiesInfoGroup OBJECT-GROUP
    OBJECTS     { vtssUpnpCapabilitiesSupportTtlWrite }
    STATUS      current
    DESCRIPTION
        "A collection of objects."
    ::= { vtssUpnpMibGroups 1 }

vtssUpnpConfigGlobalsInfoGroup OBJECT-GROUP
    OBJECTS     { vtssUpnpConfigGlobalsMode, vtssUpnpConfigGlobalsTtl,
                  vtssUpnpConfigGlobalsAdvertisingDuration,
                  vtssUpnpConfigGlobalsIpAddressingMode,
                  vtssUpnpConfigGlobalsStaticIpInterfaceId }
    STATUS      current
    DESCRIPTION
        "A collection of objects."
    ::= { vtssUpnpMibGroups 2 }

vtssUpnpMibCompliance MODULE-COMPLIANCE
    STATUS      current
    DESCRIPTION
        "The compliance statement for the implementation."

    MODULE      -- this module

    MANDATORY-GROUPS { vtssUpnpCapabilitiesInfoGroup,
                       vtssUpnpConfigGlobalsInfoGroup }

    ::= { vtssUpnpMibCompliances 1 }

END
