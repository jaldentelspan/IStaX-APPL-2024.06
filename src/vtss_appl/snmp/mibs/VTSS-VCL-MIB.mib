-- *****************************************************************
-- VCL-MIB:  Microsemi ENT private MIB
-- ****************************************************************

VTSS-VCL-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    IpAddress FROM SNMPv2-SMI
    MacAddress FROM SNMPv2-TC
    VTSSDisplayString FROM VTSS-TC
    VTSSPortList FROM VTSS-TC
    VTSSRowEditorState FROM VTSS-TC
    VTSSVclProtoEncap FROM VTSS-TC
    ;

vtssVclMib MODULE-IDENTITY
    LAST-UPDATED "201603210000Z"
    ORGANIZATION
        "Microsemi Corporation"
    CONTACT-INFO
        "Application support: http://www.microchip.com/support"
    DESCRIPTION
        "Private VCL MIB."
    REVISION    "201603210000Z"
    DESCRIPTION
        "Allow subnet length zero."
    REVISION    "201407010000Z"
    DESCRIPTION
        "Initial version"
    ::= { vtssSwitchMgmt 79 }


vtssVclMibObjects OBJECT IDENTIFIER
    ::= { vtssVclMib 1 }

vtssVclConfig OBJECT IDENTIFIER
    ::= { vtssVclMibObjects 2 }

vtssVclConfigMac OBJECT IDENTIFIER
    ::= { vtssVclConfig 1 }

vtssVclConfigMacTable OBJECT-TYPE
    SYNTAX      SEQUENCE OF VTSSVclConfigMacEntry
    MAX-ACCESS  not-accessible
    STATUS      current
    DESCRIPTION
        "This is the MAC address to VLAN ID configuration table."
    ::= { vtssVclConfigMac 1 }

vtssVclConfigMacEntry OBJECT-TYPE
    SYNTAX      VTSSVclConfigMacEntry
    MAX-ACCESS  not-accessible
    STATUS      current
    DESCRIPTION
        "Each entry in this table represents a configured MAC-based
         classification.
         
         "
    INDEX       { vtssVclConfigMacMacAddress }
    ::= { vtssVclConfigMacTable 1 }

VTSSVclConfigMacEntry ::= SEQUENCE {
    vtssVclConfigMacMacAddress  MacAddress,
    vtssVclConfigMacVlanId      Integer32,
    vtssVclConfigMacPortList    VTSSPortList,
    vtssVclConfigMacAction      VTSSRowEditorState
}

vtssVclConfigMacMacAddress OBJECT-TYPE
    SYNTAX      MacAddress
    MAX-ACCESS  accessible-for-notify
    STATUS      current
    DESCRIPTION
        "The MAC address for which this entry is applicable."
    ::= { vtssVclConfigMacEntry 1 }

vtssVclConfigMacVlanId OBJECT-TYPE
    SYNTAX      Integer32 (1..4095)
    MAX-ACCESS  read-write
    STATUS      current
    DESCRIPTION
        "Vlan id of the mapping."
    ::= { vtssVclConfigMacEntry 2 }

vtssVclConfigMacPortList OBJECT-TYPE
    SYNTAX      VTSSPortList
    MAX-ACCESS  read-write
    STATUS      current
    DESCRIPTION
        "List of stack/switch ports on which this entry is active."
    ::= { vtssVclConfigMacEntry 3 }

vtssVclConfigMacAction OBJECT-TYPE
    SYNTAX      VTSSRowEditorState
    MAX-ACCESS  read-write
    STATUS      current
    DESCRIPTION
        "Action"
    ::= { vtssVclConfigMacEntry 100 }

vtssVclConfigMacRowEditor OBJECT IDENTIFIER
    ::= { vtssVclConfigMac 2 }

vtssVclConfigMacRowEditorMacAddress OBJECT-TYPE
    SYNTAX      MacAddress
    MAX-ACCESS  read-write
    STATUS      current
    DESCRIPTION
        "The MAC address for which this entry is applicable."
    ::= { vtssVclConfigMacRowEditor 1 }

vtssVclConfigMacRowEditorVlanId OBJECT-TYPE
    SYNTAX      Integer32 (1..4095)
    MAX-ACCESS  read-write
    STATUS      current
    DESCRIPTION
        "Vlan id of the mapping."
    ::= { vtssVclConfigMacRowEditor 2 }

vtssVclConfigMacRowEditorPortList OBJECT-TYPE
    SYNTAX      VTSSPortList
    MAX-ACCESS  read-write
    STATUS      current
    DESCRIPTION
        "List of stack/switch ports on which this entry is active."
    ::= { vtssVclConfigMacRowEditor 3 }

vtssVclConfigMacRowEditorAction OBJECT-TYPE
    SYNTAX      VTSSRowEditorState
    MAX-ACCESS  read-write
    STATUS      current
    DESCRIPTION
        "Action"
    ::= { vtssVclConfigMacRowEditor 100 }

vtssVclConfigIp OBJECT IDENTIFIER
    ::= { vtssVclConfig 2 }

vtssVclConfigIpTable OBJECT-TYPE
    SYNTAX      SEQUENCE OF VTSSVclConfigIpEntry
    MAX-ACCESS  not-accessible
    STATUS      current
    DESCRIPTION
        "This is the IP Subnet to VLAN ID configuration table. The key of this
         table is the IP subnet expressed as x.x.x.x/x, where the first 4 octets
         represent the IPv4 address and the last one is the mask length.
         
         NOTE#1: Inside the VCL module these entries are actually sorted based
         on a priority defined by the mask length, so that subnets with larger
         mask lengths are first in the list, followed by entries with smaller
         mask lengths. SNMP cannot follow this sorting, therefore the order the
         entries are retrieved by the iterator may not be the same as the
         actually stored order. (This is not an issue, but should be taken into
         consideration when using the SNMP interface to create a user interface.
         
         NOTE#2: Even though only the subnet address is stored in the table
         (i.e. both 192.168.1.0/4 and 192.168.2.0/4 will end up as 192.0.0.0/4),
         the SNMP iterator will NOT take this into consideration. So, when
         searching the next subnet of 192.168.1.0/4, the result could be
         193.0.0.0/4 but not 192.168.1.0/24 (granted that these entries are
         present)"
    ::= { vtssVclConfigIp 1 }

vtssVclConfigIpEntry OBJECT-TYPE
    SYNTAX      VTSSVclConfigIpEntry
    MAX-ACCESS  not-accessible
    STATUS      current
    DESCRIPTION
        "Each entry in this table represents a configured IP Subnet-based
         classification.
         
         "
    INDEX       { vtssVclConfigIpIpSubnetAddress,
                  vtssVclConfigIpIpSubnetMaskLength }
    ::= { vtssVclConfigIpTable 1 }

VTSSVclConfigIpEntry ::= SEQUENCE {
    vtssVclConfigIpIpSubnetAddress     IpAddress,
    vtssVclConfigIpIpSubnetMaskLength  Integer32,
    vtssVclConfigIpVlanId              Integer32,
    vtssVclConfigIpPortList            VTSSPortList,
    vtssVclConfigIpAction              VTSSRowEditorState
}

vtssVclConfigIpIpSubnetAddress OBJECT-TYPE
    SYNTAX      IpAddress
    MAX-ACCESS  accessible-for-notify
    STATUS      current
    DESCRIPTION
        "The IP subnet address for which this entry is applicable."
    ::= { vtssVclConfigIpEntry 1 }

vtssVclConfigIpIpSubnetMaskLength OBJECT-TYPE
    SYNTAX      Integer32 (0..32)
    MAX-ACCESS  accessible-for-notify
    STATUS      current
    DESCRIPTION
        "The IP subnet mask length for which this entry is applicable."
    ::= { vtssVclConfigIpEntry 2 }

vtssVclConfigIpVlanId OBJECT-TYPE
    SYNTAX      Integer32 (1..4095)
    MAX-ACCESS  read-write
    STATUS      current
    DESCRIPTION
        "Vlan id of the mapping."
    ::= { vtssVclConfigIpEntry 3 }

vtssVclConfigIpPortList OBJECT-TYPE
    SYNTAX      VTSSPortList
    MAX-ACCESS  read-write
    STATUS      current
    DESCRIPTION
        "List of stack/switch ports on which this entry is active."
    ::= { vtssVclConfigIpEntry 4 }

vtssVclConfigIpAction OBJECT-TYPE
    SYNTAX      VTSSRowEditorState
    MAX-ACCESS  read-write
    STATUS      current
    DESCRIPTION
        "Action"
    ::= { vtssVclConfigIpEntry 100 }

vtssVclConfigIpRowEditor OBJECT IDENTIFIER
    ::= { vtssVclConfigIp 2 }

vtssVclConfigIpRowEditorIpSubnetAddress OBJECT-TYPE
    SYNTAX      IpAddress
    MAX-ACCESS  read-write
    STATUS      current
    DESCRIPTION
        "The IP subnet address for which this entry is applicable."
    ::= { vtssVclConfigIpRowEditor 1 }

vtssVclConfigIpRowEditorIpSubnetMaskLength OBJECT-TYPE
    SYNTAX      Integer32 (0..32)
    MAX-ACCESS  read-write
    STATUS      current
    DESCRIPTION
        "The IP subnet mask length for which this entry is applicable."
    ::= { vtssVclConfigIpRowEditor 2 }

vtssVclConfigIpRowEditorVlanId OBJECT-TYPE
    SYNTAX      Integer32 (1..4095)
    MAX-ACCESS  read-write
    STATUS      current
    DESCRIPTION
        "Vlan id of the mapping."
    ::= { vtssVclConfigIpRowEditor 3 }

vtssVclConfigIpRowEditorPortList OBJECT-TYPE
    SYNTAX      VTSSPortList
    MAX-ACCESS  read-write
    STATUS      current
    DESCRIPTION
        "List of stack/switch ports on which this entry is active."
    ::= { vtssVclConfigIpRowEditor 4 }

vtssVclConfigIpRowEditorAction OBJECT-TYPE
    SYNTAX      VTSSRowEditorState
    MAX-ACCESS  read-write
    STATUS      current
    DESCRIPTION
        "Action"
    ::= { vtssVclConfigIpRowEditor 100 }

vtssVclConfigProtocol OBJECT IDENTIFIER
    ::= { vtssVclConfig 3 }

vtssVclConfigProtocolProto OBJECT IDENTIFIER
    ::= { vtssVclConfigProtocol 1 }

vtssVclConfigProtocolProtoTable OBJECT-TYPE
    SYNTAX      SEQUENCE OF VTSSVclConfigProtocolProtoEntry
    MAX-ACCESS  not-accessible
    STATUS      current
    DESCRIPTION
        "This is the Protocol to Protocol Group mapping table."
    ::= { vtssVclConfigProtocolProto 1 }

vtssVclConfigProtocolProtoEntry OBJECT-TYPE
    SYNTAX      VTSSVclConfigProtocolProtoEntry
    MAX-ACCESS  not-accessible
    STATUS      current
    DESCRIPTION
        "Each entry in this table represents a Protocol to Group mapping.
         
         "
    INDEX       { vtssVclConfigProtocolProtoProtocolEncapsulation }
    ::= { vtssVclConfigProtocolProtoTable 1 }

VTSSVclConfigProtocolProtoEntry ::= SEQUENCE {
    vtssVclConfigProtocolProtoProtocolEncapsulation  VTSSVclProtoEncap,
    vtssVclConfigProtocolProtoProtocolGroupName      VTSSDisplayString,
    vtssVclConfigProtocolProtoAction                 VTSSRowEditorState
}

vtssVclConfigProtocolProtoProtocolEncapsulation OBJECT-TYPE
    SYNTAX      VTSSVclProtoEncap
    MAX-ACCESS  accessible-for-notify
    STATUS      current
    DESCRIPTION
        "The protocol encapsulation of the Protocol to Group mapping."
    ::= { vtssVclConfigProtocolProtoEntry 1 }

vtssVclConfigProtocolProtoProtocolGroupName OBJECT-TYPE
    SYNTAX      VTSSDisplayString (SIZE(0..16))
    MAX-ACCESS  read-write
    STATUS      current
    DESCRIPTION
        "This is a name identifying the protocol group."
    ::= { vtssVclConfigProtocolProtoEntry 2 }

vtssVclConfigProtocolProtoAction OBJECT-TYPE
    SYNTAX      VTSSRowEditorState
    MAX-ACCESS  read-write
    STATUS      current
    DESCRIPTION
        "Action"
    ::= { vtssVclConfigProtocolProtoEntry 100 }

vtssVclConfigProtocolProtoRowEditor OBJECT IDENTIFIER
    ::= { vtssVclConfigProtocolProto 2 }

vtssVclConfigProtocolProtoRowEditorProtocolEncapsulation OBJECT-TYPE
    SYNTAX      VTSSVclProtoEncap
    MAX-ACCESS  read-write
    STATUS      current
    DESCRIPTION
        "The protocol encapsulation of the Protocol to Group mapping."
    ::= { vtssVclConfigProtocolProtoRowEditor 1 }

vtssVclConfigProtocolProtoRowEditorProtocolGroupName OBJECT-TYPE
    SYNTAX      VTSSDisplayString (SIZE(0..16))
    MAX-ACCESS  read-write
    STATUS      current
    DESCRIPTION
        "This is a name identifying the protocol group."
    ::= { vtssVclConfigProtocolProtoRowEditor 2 }

vtssVclConfigProtocolProtoRowEditorAction OBJECT-TYPE
    SYNTAX      VTSSRowEditorState
    MAX-ACCESS  read-write
    STATUS      current
    DESCRIPTION
        "Action"
    ::= { vtssVclConfigProtocolProtoRowEditor 100 }

vtssVclConfigProtocolGroup OBJECT IDENTIFIER
    ::= { vtssVclConfigProtocol 2 }

vtssVclConfigProtocolGroupTable OBJECT-TYPE
    SYNTAX      SEQUENCE OF VTSSVclConfigProtocolGroupEntry
    MAX-ACCESS  not-accessible
    STATUS      current
    DESCRIPTION
        "This is the Protocol Group to VLAN ID configuration table."
    ::= { vtssVclConfigProtocolGroup 1 }

vtssVclConfigProtocolGroupEntry OBJECT-TYPE
    SYNTAX      VTSSVclConfigProtocolGroupEntry
    MAX-ACCESS  not-accessible
    STATUS      current
    DESCRIPTION
        "Each entry in this table represents a Protocol Group to VLAN ID
         mapping.
         
         "
    INDEX       { vtssVclConfigProtocolGroupProtocolGroupName }
    ::= { vtssVclConfigProtocolGroupTable 1 }

VTSSVclConfigProtocolGroupEntry ::= SEQUENCE {
    vtssVclConfigProtocolGroupProtocolGroupName  VTSSDisplayString,
    vtssVclConfigProtocolGroupVlanId             Integer32,
    vtssVclConfigProtocolGroupPortList           VTSSPortList,
    vtssVclConfigProtocolGroupAction             VTSSRowEditorState
}

vtssVclConfigProtocolGroupProtocolGroupName OBJECT-TYPE
    SYNTAX      VTSSDisplayString (SIZE(0..16))
    MAX-ACCESS  accessible-for-notify
    STATUS      current
    DESCRIPTION
        "This is a name identifying the protocol group."
    ::= { vtssVclConfigProtocolGroupEntry 1 }

vtssVclConfigProtocolGroupVlanId OBJECT-TYPE
    SYNTAX      Integer32 (1..4095)
    MAX-ACCESS  read-write
    STATUS      current
    DESCRIPTION
        "Vlan id of the mapping."
    ::= { vtssVclConfigProtocolGroupEntry 2 }

vtssVclConfigProtocolGroupPortList OBJECT-TYPE
    SYNTAX      VTSSPortList
    MAX-ACCESS  read-write
    STATUS      current
    DESCRIPTION
        "List of stack/switch ports on which this entry is active."
    ::= { vtssVclConfigProtocolGroupEntry 3 }

vtssVclConfigProtocolGroupAction OBJECT-TYPE
    SYNTAX      VTSSRowEditorState
    MAX-ACCESS  read-write
    STATUS      current
    DESCRIPTION
        "Action"
    ::= { vtssVclConfigProtocolGroupEntry 100 }

vtssVclConfigProtocolGroupRowEditor OBJECT IDENTIFIER
    ::= { vtssVclConfigProtocolGroup 2 }

vtssVclConfigProtocolGroupRowEditorProtocolGroupName OBJECT-TYPE
    SYNTAX      VTSSDisplayString (SIZE(0..16))
    MAX-ACCESS  read-write
    STATUS      current
    DESCRIPTION
        "This is a name identifying the protocol group."
    ::= { vtssVclConfigProtocolGroupRowEditor 1 }

vtssVclConfigProtocolGroupRowEditorVlanId OBJECT-TYPE
    SYNTAX      Integer32 (1..4095)
    MAX-ACCESS  read-write
    STATUS      current
    DESCRIPTION
        "Vlan id of the mapping."
    ::= { vtssVclConfigProtocolGroupRowEditor 2 }

vtssVclConfigProtocolGroupRowEditorPortList OBJECT-TYPE
    SYNTAX      VTSSPortList
    MAX-ACCESS  read-write
    STATUS      current
    DESCRIPTION
        "List of stack/switch ports on which this entry is active."
    ::= { vtssVclConfigProtocolGroupRowEditor 3 }

vtssVclConfigProtocolGroupRowEditorAction OBJECT-TYPE
    SYNTAX      VTSSRowEditorState
    MAX-ACCESS  read-write
    STATUS      current
    DESCRIPTION
        "Action"
    ::= { vtssVclConfigProtocolGroupRowEditor 100 }

vtssVclMibConformance OBJECT IDENTIFIER
    ::= { vtssVclMib 2 }

vtssVclMibCompliances OBJECT IDENTIFIER
    ::= { vtssVclMibConformance 1 }

vtssVclMibGroups OBJECT IDENTIFIER
    ::= { vtssVclMibConformance 2 }

vtssVclConfigMacTableInfoGroup OBJECT-GROUP
    OBJECTS     { vtssVclConfigMacMacAddress, vtssVclConfigMacVlanId,
                  vtssVclConfigMacPortList, vtssVclConfigMacAction }
    STATUS      current
    DESCRIPTION
        "A collection of objects."
    ::= { vtssVclMibGroups 1 }

vtssVclConfigMacRowEditorInfoGroup OBJECT-GROUP
    OBJECTS     { vtssVclConfigMacRowEditorMacAddress,
                  vtssVclConfigMacRowEditorVlanId,
                  vtssVclConfigMacRowEditorPortList,
                  vtssVclConfigMacRowEditorAction }
    STATUS      current
    DESCRIPTION
        "A collection of objects."
    ::= { vtssVclMibGroups 2 }

vtssVclConfigIpTableInfoGroup OBJECT-GROUP
    OBJECTS     { vtssVclConfigIpIpSubnetAddress,
                  vtssVclConfigIpIpSubnetMaskLength,
                  vtssVclConfigIpVlanId, vtssVclConfigIpPortList,
                  vtssVclConfigIpAction }
    STATUS      current
    DESCRIPTION
        "A collection of objects."
    ::= { vtssVclMibGroups 3 }

vtssVclConfigIpRowEditorInfoGroup OBJECT-GROUP
    OBJECTS     { vtssVclConfigIpRowEditorIpSubnetAddress,
                  vtssVclConfigIpRowEditorIpSubnetMaskLength,
                  vtssVclConfigIpRowEditorVlanId,
                  vtssVclConfigIpRowEditorPortList,
                  vtssVclConfigIpRowEditorAction }
    STATUS      current
    DESCRIPTION
        "A collection of objects."
    ::= { vtssVclMibGroups 4 }

vtssVclConfigProtocolProtoTableInfoGroup OBJECT-GROUP
    OBJECTS     { vtssVclConfigProtocolProtoProtocolEncapsulation,
                  vtssVclConfigProtocolProtoProtocolGroupName,
                  vtssVclConfigProtocolProtoAction }
    STATUS      current
    DESCRIPTION
        "A collection of objects."
    ::= { vtssVclMibGroups 5 }

vtssVclConfigProtocolProtoRowEditorInfoGroup OBJECT-GROUP
    OBJECTS     {                   vtssVclConfigProtocolProtoRowEditorProtocolEncapsulation,
                  vtssVclConfigProtocolProtoRowEditorProtocolGroupName,
                  vtssVclConfigProtocolProtoRowEditorAction }
    STATUS      current
    DESCRIPTION
        "A collection of objects."
    ::= { vtssVclMibGroups 6 }

vtssVclConfigProtocolGroupTableInfoGroup OBJECT-GROUP
    OBJECTS     { vtssVclConfigProtocolGroupProtocolGroupName,
                  vtssVclConfigProtocolGroupVlanId,
                  vtssVclConfigProtocolGroupPortList,
                  vtssVclConfigProtocolGroupAction }
    STATUS      current
    DESCRIPTION
        "A collection of objects."
    ::= { vtssVclMibGroups 7 }

vtssVclConfigProtocolGroupRowEditorInfoGroup OBJECT-GROUP
    OBJECTS     {                   vtssVclConfigProtocolGroupRowEditorProtocolGroupName,
                  vtssVclConfigProtocolGroupRowEditorVlanId,
                  vtssVclConfigProtocolGroupRowEditorPortList,
                  vtssVclConfigProtocolGroupRowEditorAction }
    STATUS      current
    DESCRIPTION
        "A collection of objects."
    ::= { vtssVclMibGroups 8 }

vtssVclMibCompliance MODULE-COMPLIANCE
    STATUS      current
    DESCRIPTION
        "The compliance statement for the implementation."

    MODULE      -- this module

    MANDATORY-GROUPS { vtssVclConfigMacTableInfoGroup,
                       vtssVclConfigMacRowEditorInfoGroup,
                       vtssVclConfigIpTableInfoGroup,
                       vtssVclConfigIpRowEditorInfoGroup,
                       vtssVclConfigProtocolProtoTableInfoGroup,
                       vtssVclConfigProtocolProtoRowEditorInfoGroup,
                       vtssVclConfigProtocolGroupTableInfoGroup,
                       vtssVclConfigProtocolGroupRowEditorInfoGroup }

    ::= { vtssVclMibCompliances 1 }

END
