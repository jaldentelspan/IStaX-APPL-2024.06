-- *****************************************************************
-- JSON-RPC-NOTIFICATION-MIB:  Microsemi ENT private MIB
-- ****************************************************************

VTSS-JSON-RPC-NOTIFICATION-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    VTSSDisplayString FROM VTSS-TC
    VTSSRowEditorState FROM VTSS-TC
    ;

vtssJsonRpcNotificationMib MODULE-IDENTITY
    LAST-UPDATED "201410030000Z"
    ORGANIZATION
        "Microsemi Corporation"
    CONTACT-INFO
        "Application support: http://www.microchip.com/support"
    DESCRIPTION
        "Private JSON-RPC Notification MIB."
    REVISION    "201410030000Z"
    DESCRIPTION
        "Initial version."
    ::= { vtssSwitchMgmt 129 }


VTSSJsonRpcNotificationDestAuthType ::= TEXTUAL-CONVENTION
    STATUS      current
    DESCRIPTION
        "Type of authentication (if any)."
    SYNTAX      INTEGER { none(0), basic(1) }

vtssJsonRpcNotificationMibObjects OBJECT IDENTIFIER
    ::= { vtssJsonRpcNotificationMib 1 }

vtssJsonRpcNotificationConfig OBJECT IDENTIFIER
    ::= { vtssJsonRpcNotificationMibObjects 2 }

vtssJsonRpcNotificationConfigDestinationTable OBJECT-TYPE
    SYNTAX      SEQUENCE OF VTSSJsonRpcNotificationConfigDestinationEntry
    MAX-ACCESS  not-accessible
    STATUS      current
    DESCRIPTION
        "Table of JSON-RPC Notification destinations."
    ::= { vtssJsonRpcNotificationConfig 1 }

vtssJsonRpcNotificationConfigDestinationEntry OBJECT-TYPE
    SYNTAX      VTSSJsonRpcNotificationConfigDestinationEntry
    MAX-ACCESS  not-accessible
    STATUS      current
    DESCRIPTION
        "Entries in this table represent a JSON-RPC Notification destination
         which can be referred to in the notification subscription table."
    INDEX       { vtssJsonRpcNotificationConfigDestinationName }
    ::= { vtssJsonRpcNotificationConfigDestinationTable 1 }

VTSSJsonRpcNotificationConfigDestinationEntry ::= SEQUENCE {
    vtssJsonRpcNotificationConfigDestinationName      VTSSDisplayString,
    vtssJsonRpcNotificationConfigDestinationUrl       VTSSDisplayString,
    vtssJsonRpcNotificationConfigDestinationAuthType  VTSSJsonRpcNotificationDestAuthType,
    vtssJsonRpcNotificationConfigDestinationUsername  VTSSDisplayString,
    vtssJsonRpcNotificationConfigDestinationPassword  VTSSDisplayString,
    vtssJsonRpcNotificationConfigDestinationAction    VTSSRowEditorState
}

vtssJsonRpcNotificationConfigDestinationName OBJECT-TYPE
    SYNTAX      VTSSDisplayString (SIZE(0..16))
    MAX-ACCESS  accessible-for-notify
    STATUS      current
    DESCRIPTION
        "Name of destination"
    ::= { vtssJsonRpcNotificationConfigDestinationEntry 1 }

vtssJsonRpcNotificationConfigDestinationUrl OBJECT-TYPE
    SYNTAX      VTSSDisplayString (SIZE(0..254))
    MAX-ACCESS  read-write
    STATUS      current
    DESCRIPTION
        "URL of the destination where the events are delivered to."
    ::= { vtssJsonRpcNotificationConfigDestinationEntry 2 }

vtssJsonRpcNotificationConfigDestinationAuthType OBJECT-TYPE
    SYNTAX      VTSSJsonRpcNotificationDestAuthType
    MAX-ACCESS  read-write
    STATUS      current
    DESCRIPTION
        "Type of authentication to use (if any)"
    ::= { vtssJsonRpcNotificationConfigDestinationEntry 3 }

vtssJsonRpcNotificationConfigDestinationUsername OBJECT-TYPE
    SYNTAX      VTSSDisplayString (SIZE(0..32))
    MAX-ACCESS  read-write
    STATUS      current
    DESCRIPTION
        "User name for the authentication process"
    ::= { vtssJsonRpcNotificationConfigDestinationEntry 4 }

vtssJsonRpcNotificationConfigDestinationPassword OBJECT-TYPE
    SYNTAX      VTSSDisplayString (SIZE(0..32))
    MAX-ACCESS  read-write
    STATUS      current
    DESCRIPTION
        "Password for the authentication process"
    ::= { vtssJsonRpcNotificationConfigDestinationEntry 5 }

vtssJsonRpcNotificationConfigDestinationAction OBJECT-TYPE
    SYNTAX      VTSSRowEditorState
    MAX-ACCESS  read-write
    STATUS      current
    DESCRIPTION
        "Action"
    ::= { vtssJsonRpcNotificationConfigDestinationEntry 100 }

vtssJsonRpcNotificationConfigDestinationRowEditor OBJECT IDENTIFIER
    ::= { vtssJsonRpcNotificationConfig 2 }

vtssJsonRpcNotificationConfigDestinationRowEditorName OBJECT-TYPE
    SYNTAX      VTSSDisplayString (SIZE(0..16))
    MAX-ACCESS  read-write
    STATUS      current
    DESCRIPTION
        "Name of destination"
    ::= { vtssJsonRpcNotificationConfigDestinationRowEditor 1 }

vtssJsonRpcNotificationConfigDestinationRowEditorUrl OBJECT-TYPE
    SYNTAX      VTSSDisplayString (SIZE(0..254))
    MAX-ACCESS  read-write
    STATUS      current
    DESCRIPTION
        "URL of the destination where the events are delivered to."
    ::= { vtssJsonRpcNotificationConfigDestinationRowEditor 2 }

vtssJsonRpcNotificationConfigDestinationRowEditorAuthType OBJECT-TYPE
    SYNTAX      VTSSJsonRpcNotificationDestAuthType
    MAX-ACCESS  read-write
    STATUS      current
    DESCRIPTION
        "Type of authentication to use (if any)"
    ::= { vtssJsonRpcNotificationConfigDestinationRowEditor 3 }

vtssJsonRpcNotificationConfigDestinationRowEditorUsername OBJECT-TYPE
    SYNTAX      VTSSDisplayString (SIZE(0..32))
    MAX-ACCESS  read-write
    STATUS      current
    DESCRIPTION
        "User name for the authentication process"
    ::= { vtssJsonRpcNotificationConfigDestinationRowEditor 4 }

vtssJsonRpcNotificationConfigDestinationRowEditorPassword OBJECT-TYPE
    SYNTAX      VTSSDisplayString (SIZE(0..32))
    MAX-ACCESS  read-write
    STATUS      current
    DESCRIPTION
        "Password for the authentication process"
    ::= { vtssJsonRpcNotificationConfigDestinationRowEditor 5 }

vtssJsonRpcNotificationConfigDestinationRowEditorAction OBJECT-TYPE
    SYNTAX      VTSSRowEditorState
    MAX-ACCESS  read-write
    STATUS      current
    DESCRIPTION
        "Action"
    ::= { vtssJsonRpcNotificationConfigDestinationRowEditor 100 }

vtssJsonRpcNotificationConfigNotificationTable OBJECT-TYPE
    SYNTAX      SEQUENCE OF VTSSJsonRpcNotificationConfigNotificationEntry
    MAX-ACCESS  not-accessible
    STATUS      current
    DESCRIPTION
        "Table of JSON-RPC Notifications subscriptions."
    ::= { vtssJsonRpcNotificationConfig 3 }

vtssJsonRpcNotificationConfigNotificationEntry OBJECT-TYPE
    SYNTAX      VTSSJsonRpcNotificationConfigNotificationEntry
    MAX-ACCESS  not-accessible
    STATUS      current
    DESCRIPTION
        "Each entry represents a subscription of a given notification to a given
         destination. If the corresponding destination is deleted, then
         subscription is deleted as well."
    INDEX       {                   vtssJsonRpcNotificationConfigNotificationDestination,
                  vtssJsonRpcNotificationConfigNotificationNotification }
    ::= { vtssJsonRpcNotificationConfigNotificationTable 1 }

VTSSJsonRpcNotificationConfigNotificationEntry ::= SEQUENCE {
    vtssJsonRpcNotificationConfigNotificationDestination   VTSSDisplayString,
    vtssJsonRpcNotificationConfigNotificationNotification  VTSSDisplayString,
    vtssJsonRpcNotificationConfigNotificationAction        VTSSRowEditorState
}

vtssJsonRpcNotificationConfigNotificationDestination OBJECT-TYPE
    SYNTAX      VTSSDisplayString (SIZE(0..16))
    MAX-ACCESS  accessible-for-notify
    STATUS      current
    DESCRIPTION
        "Name of destination"
    ::= { vtssJsonRpcNotificationConfigNotificationEntry 1 }

vtssJsonRpcNotificationConfigNotificationNotification OBJECT-TYPE
    SYNTAX      VTSSDisplayString (SIZE(0..96))
    MAX-ACCESS  accessible-for-notify
    STATUS      current
    DESCRIPTION
        "Name of notification"
    ::= { vtssJsonRpcNotificationConfigNotificationEntry 2 }

vtssJsonRpcNotificationConfigNotificationAction OBJECT-TYPE
    SYNTAX      VTSSRowEditorState
    MAX-ACCESS  read-write
    STATUS      current
    DESCRIPTION
        "Action"
    ::= { vtssJsonRpcNotificationConfigNotificationEntry 100 }

vtssJsonRpcNotificationConfigNotificationRowEditor OBJECT IDENTIFIER
    ::= { vtssJsonRpcNotificationConfig 4 }

vtssJsonRpcNotificationConfigNotificationRowEditorDestination OBJECT-TYPE
    SYNTAX      VTSSDisplayString (SIZE(0..16))
    MAX-ACCESS  read-write
    STATUS      current
    DESCRIPTION
        "Name of destination"
    ::= { vtssJsonRpcNotificationConfigNotificationRowEditor 1 }

vtssJsonRpcNotificationConfigNotificationRowEditorNotification OBJECT-TYPE
    SYNTAX      VTSSDisplayString (SIZE(0..96))
    MAX-ACCESS  read-write
    STATUS      current
    DESCRIPTION
        "Name of notification"
    ::= { vtssJsonRpcNotificationConfigNotificationRowEditor 2 }

vtssJsonRpcNotificationConfigNotificationRowEditorAction OBJECT-TYPE
    SYNTAX      VTSSRowEditorState
    MAX-ACCESS  read-write
    STATUS      current
    DESCRIPTION
        "Action"
    ::= { vtssJsonRpcNotificationConfigNotificationRowEditor 100 }

vtssJsonRpcNotificationMibConformance OBJECT IDENTIFIER
    ::= { vtssJsonRpcNotificationMib 2 }

vtssJsonRpcNotificationMibCompliances OBJECT IDENTIFIER
    ::= { vtssJsonRpcNotificationMibConformance 1 }

vtssJsonRpcNotificationMibGroups OBJECT IDENTIFIER
    ::= { vtssJsonRpcNotificationMibConformance 2 }

vtssJsonRpcNotificationConfigDestinationTableInfoGroup OBJECT-GROUP
    OBJECTS     { vtssJsonRpcNotificationConfigDestinationName,
                  vtssJsonRpcNotificationConfigDestinationUrl,
                  vtssJsonRpcNotificationConfigDestinationAuthType,
                  vtssJsonRpcNotificationConfigDestinationUsername,
                  vtssJsonRpcNotificationConfigDestinationPassword,
                  vtssJsonRpcNotificationConfigDestinationAction }
    STATUS      current
    DESCRIPTION
        "A collection of objects."
    ::= { vtssJsonRpcNotificationMibGroups 1 }

vtssJsonRpcNotificationConfigDestinationRowEditorInfoGroup OBJECT-GROUP
    OBJECTS     {                   vtssJsonRpcNotificationConfigDestinationRowEditorName,
                  vtssJsonRpcNotificationConfigDestinationRowEditorUrl,
                  vtssJsonRpcNotificationConfigDestinationRowEditorAuthType,
                  vtssJsonRpcNotificationConfigDestinationRowEditorUsername,
                  vtssJsonRpcNotificationConfigDestinationRowEditorPassword,
                  vtssJsonRpcNotificationConfigDestinationRowEditorAction }
    STATUS      current
    DESCRIPTION
        "A collection of objects."
    ::= { vtssJsonRpcNotificationMibGroups 2 }

vtssJsonRpcNotificationConfigNotificationTableInfoGroup OBJECT-GROUP
    OBJECTS     {                   vtssJsonRpcNotificationConfigNotificationDestination,
                  vtssJsonRpcNotificationConfigNotificationNotification,
                  vtssJsonRpcNotificationConfigNotificationAction }
    STATUS      current
    DESCRIPTION
        "A collection of objects."
    ::= { vtssJsonRpcNotificationMibGroups 3 }

vtssJsonRpcNotificationConfigNotificationRowEditorInfoGroup OBJECT-GROUP
    OBJECTS     {                   vtssJsonRpcNotificationConfigNotificationRowEditorDestination,
                  vtssJsonRpcNotificationConfigNotificationRowEditorNotification,
                  vtssJsonRpcNotificationConfigNotificationRowEditorAction }
    STATUS      current
    DESCRIPTION
        "A collection of objects."
    ::= { vtssJsonRpcNotificationMibGroups 4 }

vtssJsonRpcNotificationMibCompliance MODULE-COMPLIANCE
    STATUS      current
    DESCRIPTION
        "The compliance statement for the implementation."

    MODULE      -- this module

    MANDATORY-GROUPS {                        vtssJsonRpcNotificationConfigDestinationTableInfoGroup,
                       vtssJsonRpcNotificationConfigDestinationRowEditorInfoGroup,
                       vtssJsonRpcNotificationConfigNotificationTableInfoGroup,
                       vtssJsonRpcNotificationConfigNotificationRowEditorInfoGroup }

    ::= { vtssJsonRpcNotificationMibCompliances 1 }

END
