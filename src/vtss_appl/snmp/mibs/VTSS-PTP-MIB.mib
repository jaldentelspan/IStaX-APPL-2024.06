-- *****************************************************************
-- PTP-MIB:  Microsemi ENT private MIB
-- ****************************************************************

VTSS-PTP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    IpAddress FROM SNMPv2-SMI
    Unsigned32 FROM SNMPv2-SMI
    MacAddress FROM SNMPv2-TC
    TruthValue FROM SNMPv2-TC
    VTSSInteger16 FROM VTSS-TC
    VTSSInteger32e-9 FROM VTSS-TC
    VTSSInteger64 FROM VTSS-TC
    VTSSInteger8 FROM VTSS-TC
    VTSSInterfaceIndex FROM VTSS-TC
    VTSSRowEditorState FROM VTSS-TC
    VTSSUnsigned16 FROM VTSS-TC
    VTSSUnsigned64 FROM VTSS-TC
    VTSSUnsigned8 FROM VTSS-TC
    ;

vtssPtpMib MODULE-IDENTITY
    LAST-UPDATED "202208010000Z"
    ORGANIZATION
        "Microsemi Corporation"
    CONTACT-INFO
        "Application support: http://www.microchip.com/support"
    DESCRIPTION
        "Private PTP MIB."
    REVISION    "202208010000Z"
    DESCRIPTION
        "Changed ptpFilterType and ptpDelayMechanism from an integer to an
         enumeration."
    REVISION    "201905080000Z"
    DESCRIPTION
        "Updated new protocol ethip4ip6."
    REVISION    "201902120000Z"
    DESCRIPTION
        "Updated 802.1as CMLDS names,descriptions and reorganised CMLDS
         DefaultDS MIB objects."
    REVISION    "201806270000Z"
    DESCRIPTION
        "Added 802.1AS Intervals."
    REVISION    "201604290000Z"
    DESCRIPTION
        "Added statistic parameters for PTP port."
    REVISION    "201604200000Z"
    DESCRIPTION
        "Removed vlanTagEnable parameter."
    REVISION    "201511100000Z"
    DESCRIPTION
        "Added virtual port parameters."
    REVISION    "201510280000Z"
    DESCRIPTION
        "Added parameters for specifying leap event."
    REVISION    "201506030000Z"
    DESCRIPTION
        "Added MS-PDV parameters"
    REVISION    "201503260000Z"
    DESCRIPTION
        "Added attribute Dscp to PtpConfigClocksDefaultDs"
    REVISION    "201407010000Z"
    DESCRIPTION
        "Initial version"
    ::= { vtssSwitchMgmt 65 }


VTSSptp8021asPortRole ::= TEXTUAL-CONVENTION
    STATUS      current
    DESCRIPTION
        "-"
    SYNTAX      INTEGER { disabledPort(3), masterPort(6),
                          passivePort(7), slavePort(9) }

VTSSptpClockPortState ::= TEXTUAL-CONVENTION
    STATUS      current
    DESCRIPTION
        "-"
    SYNTAX      INTEGER { initializing(0), faulty(1), disabled(2),
                          listening(3), preMaster(4), master(5),
                          passive(6), uncalibrated(7), slave(8),
                          p2pTransparent(9), e2eTransparent(10),
                          frontend(11) }

VTSSptpDelayMechanism ::= TEXTUAL-CONVENTION
    STATUS      current
    DESCRIPTION
        "-"
    SYNTAX      INTEGER { e2e(1), p2p(2), commonP2P(3), disabled(254) }

VTSSptpDestAdrType ::= TEXTUAL-CONVENTION
    STATUS      current
    DESCRIPTION
        "-"
    SYNTAX      INTEGER { default(0), linkLocal(1) }

VTSSptpDeviceType ::= TEXTUAL-CONVENTION
    STATUS      current
    DESCRIPTION
        "-"
    SYNTAX      INTEGER { none(0), ordBound(1), p2pTransparent(2),
                          e2eTransparent(3), masterOnly(4),
                          slaveOnly(5), bcFrontend(6), aedGm(7),
                          internal(8) }

VTSSptpExtClock1pps ::= TEXTUAL-CONVENTION
    STATUS      current
    DESCRIPTION
        "-"
    SYNTAX      INTEGER { onePpsDisable(0), onePpsOutput(1) }

VTSSptpFilterType ::= TEXTUAL-CONVENTION
    STATUS      current
    DESCRIPTION
        "-"
    SYNTAX      INTEGER { default(0), freqXo(1), phaseXo(2),
                          freqTxco(3), phaseTxco(4), freqOcxoS3e(5),
                          phaseOcxoS3e(6), partialOnPathFreq(7),
                          partialOnPathPhase(8), fullOnPathFreq(9),
                          fullOnPathPhase(10),
                          fullOnPathPhaseFasterLockLowPktRate(11),
                          freqAccuracyFdd(12), freqAccuracyXdsl(13),
                          elecFreq(14), elecPhase(15),
                          phaseRelaxedC60w(16), phaseRelaxedC150(17),
                          phaseRelaxedC180(18), phaseRelaxedC240(19),
                          phaseOcx0S3eR461(20), basicPhase(21),
                          basicPhaseLow(22), basic(23), maxType(24) }

VTSSptpLeapSecondType ::= TEXTUAL-CONVENTION
    STATUS      current
    DESCRIPTION
        "-"
    SYNTAX      INTEGER { leap59(0), leap61(1) }

VTSSptpPreferredAdj ::= TEXTUAL-CONVENTION
    STATUS      current
    DESCRIPTION
        "-"
    SYNTAX      INTEGER { preferredAdjLtc(0), preferredAdjSingle(1),
                          preferredAdjIndependent(2),
                          preferredAdjCommon(3), preferredAdjAuto(4) }

VTSSptpProfile ::= TEXTUAL-CONVENTION
    STATUS      current
    DESCRIPTION
        "-"
    SYNTAX      INTEGER { noProfile(0), ieee1588(1), g8265(2),
                          g8275d1(3), g8275d2(4), ieee802d1as(5) }

VTSSptpProtocol ::= TEXTUAL-CONVENTION
    STATUS      current
    DESCRIPTION
        "-"
    SYNTAX      INTEGER { ethernet(0), ethernetMixed(1), ip4multi(2),
                          ip4mixed(3), ip4uni(4), oam(5), onePps(6),
                          ip6mixed(7), ethip4ip6combo(8) }

VTSSptpServoClockOption ::= TEXTUAL-CONVENTION
    STATUS      current
    DESCRIPTION
        "-"
    SYNTAX      INTEGER { clockFree(0), clockSyncE(1) }

VTSSptpSlaveClockState ::= TEXTUAL-CONVENTION
    STATUS      current
    DESCRIPTION
        "-"
    SYNTAX      INTEGER { slaveClockStateFreerun(0),
                          slaveClockStateFreqLocking(1),
                          slaveClockStateFreqLocked(2),
                          slaveClockStatePhaseLocking(3),
                          slaveClockStatePhaseLocked(4),
                          slaveClockStateHoldover(5),
                          slaveClockStateInvalid(6) }

VTSSptpSystemTimeSyncMode ::= TEXTUAL-CONVENTION
    STATUS      current
    DESCRIPTION
        "-"
    SYNTAX      INTEGER { systemTimeNoSync(0), systemTimeSyncGet(1),
                          systemTimeSyncSet(2) }

VTSSptpTodProtocol ::= TEXTUAL-CONVENTION
    STATUS      current
    DESCRIPTION
        "-"
    SYNTAX      INTEGER { nmeaProprietaryPolytFormat(0),
                          nmeaZdaFormat(1), nmeaGgaFormat(2),
                          nmeaRmcFormat(3), ptpPimProtocol(4),
                          noTodProtocol(5) }

VTSSptpUcCommState ::= TEXTUAL-CONVENTION
    STATUS      current
    DESCRIPTION
        "-"
    SYNTAX      INTEGER { idle(0), initializing(1), connected(2),
                          selected(3), synced(4) }

VTSSptpVirtualPortmode ::= TEXTUAL-CONVENTION
    STATUS      current
    DESCRIPTION
        "-"
    SYNTAX      INTEGER { noVirtualPortMode(0), mainAuto(1), sub(2),
                          mainMan(3), ppsIn(4), ppsOut(5), freqOut(6) }

vtssPtpMibObjects OBJECT IDENTIFIER
    ::= { vtssPtpMib 1 }

vtssPtpCapabilities OBJECT IDENTIFIER
    ::= { vtssPtpMibObjects 1 }

vtssPtpCapabilitiesGlobals OBJECT IDENTIFIER
    ::= { vtssPtpCapabilities 1 }

vtssPtpCapabilitiesGlobalsClockCount OBJECT-TYPE
    SYNTAX      Unsigned32
    MAX-ACCESS  read-only
    STATUS      current
    DESCRIPTION
        "The number of PTP clocks supported by the device."
    ::= { vtssPtpCapabilitiesGlobals 1 }

vtssPtpCapabilitiesGlobalsHasMsPdv OBJECT-TYPE
    SYNTAX      TruthValue
    MAX-ACCESS  read-only
    STATUS      current
    DESCRIPTION
        "If true, the build supports the MS-PDV."
    ::= { vtssPtpCapabilitiesGlobals 2 }

vtssPtpCapabilitiesGlobalsHasHwClkDomains OBJECT-TYPE
    SYNTAX      TruthValue
    MAX-ACCESS  read-only
    STATUS      current
    DESCRIPTION
        "If true, the build supports hardware clock domains."
    ::= { vtssPtpCapabilitiesGlobals 3 }

vtssPtpConfig OBJECT IDENTIFIER
    ::= { vtssPtpMibObjects 2 }

vtssPtpConfigGlobals OBJECT IDENTIFIER
    ::= { vtssPtpConfig 1 }

vtssPtpConfigGlobalsExternalClockMode OBJECT IDENTIFIER
    ::= { vtssPtpConfigGlobals 1 }

vtssPtpConfigGlobalsExternalClockModeOnePpsMode OBJECT-TYPE
    SYNTAX      VTSSptpExtClock1pps
    MAX-ACCESS  read-write
    STATUS      current
    DESCRIPTION
        "The mode of the PPS pin. Valid options : onePpsDisable, onePpsOutput."
    ::= { vtssPtpConfigGlobalsExternalClockMode 1 }

vtssPtpConfigGlobalsExternalClockModeExternalEnable OBJECT-TYPE
    SYNTAX      TruthValue
    MAX-ACCESS  read-write
    STATUS      current
    DESCRIPTION
        "External enable of PPS output."
    ::= { vtssPtpConfigGlobalsExternalClockMode 2 }

vtssPtpConfigGlobalsExternalClockModeAdjustMethod OBJECT-TYPE
    SYNTAX      VTSSptpPreferredAdj
    MAX-ACCESS  read-write
    STATUS      current
    DESCRIPTION
        "The adjustment method of the PTP timer.
         
         0: LTC
         
         1: Single DPLL
         
         2: Independent DPLL
         
         3: Common DPLL's 4: Auto"
    ::= { vtssPtpConfigGlobalsExternalClockMode 3 }

vtssPtpConfigGlobalsExternalClockModeClockFrequency OBJECT-TYPE
    SYNTAX      Unsigned32
    MAX-ACCESS  read-write
    STATUS      current
    DESCRIPTION
        "The frequency in hertz (Hz) of the PPS external output. Range 1 to
         25e6."
    ::= { vtssPtpConfigGlobalsExternalClockMode 4 }

vtssPtpConfigGlobalsExternalClockModePpsDomain OBJECT-TYPE
    SYNTAX      Unsigned32
    MAX-ACCESS  read-write
    STATUS      current
    DESCRIPTION
        "Clock domain from which 1PPS output need to be generated."
    ::= { vtssPtpConfigGlobalsExternalClockMode 5 }

vtssPtpConfigGlobalsSystemTimeSyncMode OBJECT IDENTIFIER
    ::= { vtssPtpConfigGlobals 2 }

vtssPtpConfigGlobalsSystemTimeSyncModeMode OBJECT-TYPE
    SYNTAX      VTSSptpSystemTimeSyncMode
    MAX-ACCESS  read-write
    STATUS      current
    DESCRIPTION
        "Mode of the System time <-> ptp time synchronization. Valid Options :
         systemTimeNoSync, systemTimeSyncGet and systemTimeSyncSet."
    ::= { vtssPtpConfigGlobalsSystemTimeSyncMode 1 }

vtssPtpConfigClocks OBJECT IDENTIFIER
    ::= { vtssPtpConfig 2 }

vtssPtpConfigClocksDefaultDsTable OBJECT-TYPE
    SYNTAX      SEQUENCE OF VTSSPtpConfigClocksDefaultDsEntry
    MAX-ACCESS  not-accessible
    STATUS      current
    DESCRIPTION
        "This is the configurable part of the PTP clocks DefaultDS."
    ::= { vtssPtpConfigClocks 1 }

vtssPtpConfigClocksDefaultDsEntry OBJECT-TYPE
    SYNTAX      VTSSPtpConfigClocksDefaultDsEntry
    MAX-ACCESS  not-accessible
    STATUS      current
    DESCRIPTION
        "The clockId index must be a value must be a value from 0 up to the
         number of PTP clocks minus one."
    INDEX       { vtssPtpConfigClocksDefaultDsClockId }
    ::= { vtssPtpConfigClocksDefaultDsTable 1 }

VTSSPtpConfigClocksDefaultDsEntry ::= SEQUENCE {
    vtssPtpConfigClocksDefaultDsClockId          Integer32,
    vtssPtpConfigClocksDefaultDsDeviceType       VTSSptpDeviceType,
    vtssPtpConfigClocksDefaultDsTwoStepFlag      TruthValue,
    vtssPtpConfigClocksDefaultDsPriority1        VTSSUnsigned8,
    vtssPtpConfigClocksDefaultDsPriority2        VTSSUnsigned8,
    vtssPtpConfigClocksDefaultDsOneWay           TruthValue,
    vtssPtpConfigClocksDefaultDsDomainNumber     VTSSUnsigned8,
    vtssPtpConfigClocksDefaultDsProtocol         VTSSptpProtocol,
    vtssPtpConfigClocksDefaultDsVid              VTSSUnsigned16,
    vtssPtpConfigClocksDefaultDsPcp              VTSSUnsigned8,
    vtssPtpConfigClocksDefaultDsMep              Integer32,
    vtssPtpConfigClocksDefaultDsClkDom           Unsigned32,
    vtssPtpConfigClocksDefaultDsDscp             VTSSUnsigned8,
    vtssPtpConfigClocksDefaultDsProfile          VTSSptpProfile,
    vtssPtpConfigClocksDefaultDsLocalPriority    VTSSUnsigned8,
    vtssPtpConfigClocksDefaultDsFilterType       VTSSptpFilterType,
    vtssPtpConfigClocksDefaultDsPathTraceEnable  TruthValue,
    vtssPtpConfigClocksDefaultDsAction           VTSSRowEditorState
}

vtssPtpConfigClocksDefaultDsClockId OBJECT-TYPE
    SYNTAX      Integer32 (0..32767)
    MAX-ACCESS  accessible-for-notify
    STATUS      current
    DESCRIPTION
        "-"
    ::= { vtssPtpConfigClocksDefaultDsEntry 1 }

vtssPtpConfigClocksDefaultDsDeviceType OBJECT-TYPE
    SYNTAX      VTSSptpDeviceType
    MAX-ACCESS  read-write
    STATUS      current
    DESCRIPTION
        "The PTP clock type. Valid options : none, ordBound, p2pTransparent,
         e2eTransparent, masterOnly, slaveOnly and bcFrontend."
    ::= { vtssPtpConfigClocksDefaultDsEntry 2 }

vtssPtpConfigClocksDefaultDsTwoStepFlag OBJECT-TYPE
    SYNTAX      TruthValue
    MAX-ACCESS  read-write
    STATUS      current
    DESCRIPTION
        "Determines whether clock uses follow-up packets."
    ::= { vtssPtpConfigClocksDefaultDsEntry 3 }

vtssPtpConfigClocksDefaultDsPriority1 OBJECT-TYPE
    SYNTAX      VTSSUnsigned8
    MAX-ACCESS  read-write
    STATUS      current
    DESCRIPTION
        "The priority1 value."
    ::= { vtssPtpConfigClocksDefaultDsEntry 4 }

vtssPtpConfigClocksDefaultDsPriority2 OBJECT-TYPE
    SYNTAX      VTSSUnsigned8
    MAX-ACCESS  read-write
    STATUS      current
    DESCRIPTION
        "The priority2 value."
    ::= { vtssPtpConfigClocksDefaultDsEntry 5 }

vtssPtpConfigClocksDefaultDsOneWay OBJECT-TYPE
    SYNTAX      TruthValue
    MAX-ACCESS  read-write
    STATUS      current
    DESCRIPTION
        "Determines whether clock uses sync packets only."
    ::= { vtssPtpConfigClocksDefaultDsEntry 6 }

vtssPtpConfigClocksDefaultDsDomainNumber OBJECT-TYPE
    SYNTAX      VTSSUnsigned8
    MAX-ACCESS  read-write
    STATUS      current
    DESCRIPTION
        "The domain number. Range 0 to 127."
    ::= { vtssPtpConfigClocksDefaultDsEntry 7 }

vtssPtpConfigClocksDefaultDsProtocol OBJECT-TYPE
    SYNTAX      VTSSptpProtocol
    MAX-ACCESS  read-write
    STATUS      current
    DESCRIPTION
        "The protocol to be used for the encapsulation of the PTP packets. Valid
         options : ethernet, ethernetMixed, ip4multi, ip4mixed, ip4uni, oam,
         onePps, ip6mixed and ethip4ip6combo."
    ::= { vtssPtpConfigClocksDefaultDsEntry 8 }

vtssPtpConfigClocksDefaultDsVid OBJECT-TYPE
    SYNTAX      VTSSUnsigned16
    MAX-ACCESS  read-write
    STATUS      current
    DESCRIPTION
        "The VLAN id for this PTP instance. Range 1 to 4095."
    ::= { vtssPtpConfigClocksDefaultDsEntry 10 }

vtssPtpConfigClocksDefaultDsPcp OBJECT-TYPE
    SYNTAX      VTSSUnsigned8
    MAX-ACCESS  read-write
    STATUS      current
    DESCRIPTION
        "The PCP value for this PTP instance. Range 0 to 7."
    ::= { vtssPtpConfigClocksDefaultDsEntry 11 }

vtssPtpConfigClocksDefaultDsMep OBJECT-TYPE
    SYNTAX      Integer32
    MAX-ACCESS  read-write
    STATUS      current
    DESCRIPTION
        "The mep instance number (if protocol is OAM). Range 0 to 100."
    ::= { vtssPtpConfigClocksDefaultDsEntry 12 }

vtssPtpConfigClocksDefaultDsClkDom OBJECT-TYPE
    SYNTAX      Unsigned32
    MAX-ACCESS  read-write
    STATUS      current
    DESCRIPTION
        "Clock domain used. Range 0 to 127.
         
         This object is only available if the capability object
         'vtssPtpCapabilitiesGlobalsHasHwClkDomains' is True."
    ::= { vtssPtpConfigClocksDefaultDsEntry 13 }

vtssPtpConfigClocksDefaultDsDscp OBJECT-TYPE
    SYNTAX      VTSSUnsigned8
    MAX-ACCESS  read-write
    STATUS      current
    DESCRIPTION
        "The DSCP field value (if protocol is IPv4). Range 0 to 3."
    ::= { vtssPtpConfigClocksDefaultDsEntry 14 }

vtssPtpConfigClocksDefaultDsProfile OBJECT-TYPE
    SYNTAX      VTSSptpProfile
    MAX-ACCESS  read-write
    STATUS      current
    DESCRIPTION
        "The PTP profile. Valid options : noProfile, ieee1588, g8265, g8275d1,
         g8275d2, ieee802d1as."
    ::= { vtssPtpConfigClocksDefaultDsEntry 15 }

vtssPtpConfigClocksDefaultDsLocalPriority OBJECT-TYPE
    SYNTAX      VTSSUnsigned8
    MAX-ACCESS  read-write
    STATUS      current
    DESCRIPTION
        "The local priority value."
    ::= { vtssPtpConfigClocksDefaultDsEntry 16 }

vtssPtpConfigClocksDefaultDsFilterType OBJECT-TYPE
    SYNTAX      VTSSptpFilterType
    MAX-ACCESS  read-write
    STATUS      current
    DESCRIPTION
        "Selects the type of filter/servo used. Valid Options : default, freqXo,
         phaseXo, freqTcxo, phaseTcxo, freqOcxoS3e, phaseOcxoS3e,
         partialOnPathFreq, partialOnPathPhase, fullOnPathFreq, fullOnPathPhase,
         fullOnPathPhaseFasterLockLowPktRate, freqAccuracyFdd, freqAccuracyXdsl,
         elecFreq, elecPhase, phaseRelaxedC60W, phaseRelaxedC150,
         phaseRelaxedC180, phaseRelaxedC240, phaseOcx0S3eR461, basicPhase,
         basicPhaseLow, basic."
    ::= { vtssPtpConfigClocksDefaultDsEntry 17 }

vtssPtpConfigClocksDefaultDsPathTraceEnable OBJECT-TYPE
    SYNTAX      TruthValue
    MAX-ACCESS  read-write
    STATUS      current
    DESCRIPTION
        "The Announce Path Trace supported."
    ::= { vtssPtpConfigClocksDefaultDsEntry 18 }

vtssPtpConfigClocksDefaultDsAction OBJECT-TYPE
    SYNTAX      VTSSRowEditorState
    MAX-ACCESS  read-write
    STATUS      current
    DESCRIPTION
        "Action"
    ::= { vtssPtpConfigClocksDefaultDsEntry 100 }

vtssPtpConfigClocksDefaultDsTableRowEditor OBJECT IDENTIFIER
    ::= { vtssPtpConfigClocks 2 }

vtssPtpConfigClocksDefaultDsTableRowEditorClockId OBJECT-TYPE
    SYNTAX      Integer32 (0..32767)
    MAX-ACCESS  read-write
    STATUS      current
    DESCRIPTION
        "-"
    ::= { vtssPtpConfigClocksDefaultDsTableRowEditor 1 }

vtssPtpConfigClocksDefaultDsTableRowEditorDeviceType OBJECT-TYPE
    SYNTAX      VTSSptpDeviceType
    MAX-ACCESS  read-write
    STATUS      current
    DESCRIPTION
        "The PTP clock type. Valid options : none, ordBound, p2pTransparent,
         e2eTransparent, masterOnly, slaveOnly and bcFrontend."
    ::= { vtssPtpConfigClocksDefaultDsTableRowEditor 2 }

vtssPtpConfigClocksDefaultDsTableRowEditorTwoStepFlag OBJECT-TYPE
    SYNTAX      TruthValue
    MAX-ACCESS  read-write
    STATUS      current
    DESCRIPTION
        "Determines whether clock uses follow-up packets."
    ::= { vtssPtpConfigClocksDefaultDsTableRowEditor 3 }

vtssPtpConfigClocksDefaultDsTableRowEditorPriority1 OBJECT-TYPE
    SYNTAX      VTSSUnsigned8
    MAX-ACCESS  read-write
    STATUS      current
    DESCRIPTION
        "The priority1 value."
    ::= { vtssPtpConfigClocksDefaultDsTableRowEditor 4 }

vtssPtpConfigClocksDefaultDsTableRowEditorPriority2 OBJECT-TYPE
    SYNTAX      VTSSUnsigned8
    MAX-ACCESS  read-write
    STATUS      current
    DESCRIPTION
        "The priority2 value."
    ::= { vtssPtpConfigClocksDefaultDsTableRowEditor 5 }

vtssPtpConfigClocksDefaultDsTableRowEditorOneWay OBJECT-TYPE
    SYNTAX      TruthValue
    MAX-ACCESS  read-write
    STATUS      current
    DESCRIPTION
        "Determines whether clock uses sync packets only."
    ::= { vtssPtpConfigClocksDefaultDsTableRowEditor 6 }

vtssPtpConfigClocksDefaultDsTableRowEditorDomainNumber OBJECT-TYPE
    SYNTAX      VTSSUnsigned8
    MAX-ACCESS  read-write
    STATUS      current
    DESCRIPTION
        "The domain number. Range 0 to 127."
    ::= { vtssPtpConfigClocksDefaultDsTableRowEditor 7 }

vtssPtpConfigClocksDefaultDsTableRowEditorProtocol OBJECT-TYPE
    SYNTAX      VTSSptpProtocol
    MAX-ACCESS  read-write
    STATUS      current
    DESCRIPTION
        "The protocol to be used for the encapsulation of the PTP packets. Valid
         options : ethernet, ethernetMixed, ip4multi, ip4mixed, ip4uni, oam,
         onePps, ip6mixed and ethip4ip6combo."
    ::= { vtssPtpConfigClocksDefaultDsTableRowEditor 8 }

vtssPtpConfigClocksDefaultDsTableRowEditorVid OBJECT-TYPE
    SYNTAX      VTSSUnsigned16
    MAX-ACCESS  read-write
    STATUS      current
    DESCRIPTION
        "The VLAN id for this PTP instance. Range 1 to 4095."
    ::= { vtssPtpConfigClocksDefaultDsTableRowEditor 10 }

vtssPtpConfigClocksDefaultDsTableRowEditorPcp OBJECT-TYPE
    SYNTAX      VTSSUnsigned8
    MAX-ACCESS  read-write
    STATUS      current
    DESCRIPTION
        "The PCP value for this PTP instance. Range 0 to 7."
    ::= { vtssPtpConfigClocksDefaultDsTableRowEditor 11 }

vtssPtpConfigClocksDefaultDsTableRowEditorMep OBJECT-TYPE
    SYNTAX      Integer32
    MAX-ACCESS  read-write
    STATUS      current
    DESCRIPTION
        "The mep instance number (if protocol is OAM). Range 0 to 100."
    ::= { vtssPtpConfigClocksDefaultDsTableRowEditor 12 }

vtssPtpConfigClocksDefaultDsTableRowEditorClkDom OBJECT-TYPE
    SYNTAX      Unsigned32
    MAX-ACCESS  read-write
    STATUS      current
    DESCRIPTION
        "Clock domain used. Range 0 to 127.
         
         This object is only available if the capability object
         'vtssPtpCapabilitiesGlobalsHasHwClkDomains' is True."
    ::= { vtssPtpConfigClocksDefaultDsTableRowEditor 13 }

vtssPtpConfigClocksDefaultDsTableRowEditorDscp OBJECT-TYPE
    SYNTAX      VTSSUnsigned8
    MAX-ACCESS  read-write
    STATUS      current
    DESCRIPTION
        "The DSCP field value (if protocol is IPv4). Range 0 to 3."
    ::= { vtssPtpConfigClocksDefaultDsTableRowEditor 14 }

vtssPtpConfigClocksDefaultDsTableRowEditorProfile OBJECT-TYPE
    SYNTAX      VTSSptpProfile
    MAX-ACCESS  read-write
    STATUS      current
    DESCRIPTION
        "The PTP profile. Valid options : noProfile, ieee1588, g8265, g8275d1,
         g8275d2, ieee802d1as."
    ::= { vtssPtpConfigClocksDefaultDsTableRowEditor 15 }

vtssPtpConfigClocksDefaultDsTableRowEditorLocalPriority OBJECT-TYPE
    SYNTAX      VTSSUnsigned8
    MAX-ACCESS  read-write
    STATUS      current
    DESCRIPTION
        "The local priority value."
    ::= { vtssPtpConfigClocksDefaultDsTableRowEditor 16 }

vtssPtpConfigClocksDefaultDsTableRowEditorFilterType OBJECT-TYPE
    SYNTAX      VTSSptpFilterType
    MAX-ACCESS  read-write
    STATUS      current
    DESCRIPTION
        "Selects the type of filter/servo used. Valid Options : default, freqXo,
         phaseXo, freqTcxo, phaseTcxo, freqOcxoS3e, phaseOcxoS3e,
         partialOnPathFreq, partialOnPathPhase, fullOnPathFreq, fullOnPathPhase,
         fullOnPathPhaseFasterLockLowPktRate, freqAccuracyFdd, freqAccuracyXdsl,
         elecFreq, elecPhase, phaseRelaxedC60W, phaseRelaxedC150,
         phaseRelaxedC180, phaseRelaxedC240, phaseOcx0S3eR461, basicPhase,
         basicPhaseLow, basic."
    ::= { vtssPtpConfigClocksDefaultDsTableRowEditor 17 }

vtssPtpConfigClocksDefaultDsTableRowEditorPathTraceEnable OBJECT-TYPE
    SYNTAX      TruthValue
    MAX-ACCESS  read-write
    STATUS      current
    DESCRIPTION
        "The Announce Path Trace supported."
    ::= { vtssPtpConfigClocksDefaultDsTableRowEditor 18 }

vtssPtpConfigClocksDefaultDsTableRowEditorAction OBJECT-TYPE
    SYNTAX      VTSSRowEditorState
    MAX-ACCESS  read-write
    STATUS      current
    DESCRIPTION
        "Action"
    ::= { vtssPtpConfigClocksDefaultDsTableRowEditor 100 }

vtssPtpConfigClocksTimePropertiesDsTable OBJECT-TYPE
    SYNTAX      SEQUENCE OF VTSSPtpConfigClocksTimePropertiesDsEntry
    MAX-ACCESS  not-accessible
    STATUS      current
    DESCRIPTION
        "This is the configurable part of the PTP clocks TimePropertiesDS."
    ::= { vtssPtpConfigClocks 3 }

vtssPtpConfigClocksTimePropertiesDsEntry OBJECT-TYPE
    SYNTAX      VTSSPtpConfigClocksTimePropertiesDsEntry
    MAX-ACCESS  not-accessible
    STATUS      current
    DESCRIPTION
        "The clockId index must be a value must be a value from 0 up to the
         number of PTP clocks minus one."
    INDEX       { vtssPtpConfigClocksTimePropertiesDsClockId }
    ::= { vtssPtpConfigClocksTimePropertiesDsTable 1 }

VTSSPtpConfigClocksTimePropertiesDsEntry ::= SEQUENCE {
    vtssPtpConfigClocksTimePropertiesDsClockId                Integer32,
    vtssPtpConfigClocksTimePropertiesDsCurrentUtcOffset       VTSSInteger16,
    vtssPtpConfigClocksTimePropertiesDsCurrentUtcOffsetValid  TruthValue,
    vtssPtpConfigClocksTimePropertiesDsLeap59                 TruthValue,
    vtssPtpConfigClocksTimePropertiesDsLeap61                 TruthValue,
    vtssPtpConfigClocksTimePropertiesDsTimeTraceable          TruthValue,
    vtssPtpConfigClocksTimePropertiesDsFrequencyTraceable     TruthValue,
    vtssPtpConfigClocksTimePropertiesDsPtpTimescale           TruthValue,
    vtssPtpConfigClocksTimePropertiesDsTimeSource             VTSSUnsigned8,
    vtssPtpConfigClocksTimePropertiesDsPendingLeap            TruthValue,
    vtssPtpConfigClocksTimePropertiesDsLeapDate               VTSSUnsigned16,
    vtssPtpConfigClocksTimePropertiesDsLeapType               VTSSptpLeapSecondType
}

vtssPtpConfigClocksTimePropertiesDsClockId OBJECT-TYPE
    SYNTAX      Integer32 (0..32767)
    MAX-ACCESS  accessible-for-notify
    STATUS      current
    DESCRIPTION
        "-"
    ::= { vtssPtpConfigClocksTimePropertiesDsEntry 1 }

vtssPtpConfigClocksTimePropertiesDsCurrentUtcOffset OBJECT-TYPE
    SYNTAX      VTSSInteger16
    MAX-ACCESS  read-write
    STATUS      current
    DESCRIPTION
        "The current UTC time offset. Range 0 to 10000."
    ::= { vtssPtpConfigClocksTimePropertiesDsEntry 2 }

vtssPtpConfigClocksTimePropertiesDsCurrentUtcOffsetValid OBJECT-TYPE
    SYNTAX      TruthValue
    MAX-ACCESS  read-write
    STATUS      current
    DESCRIPTION
        "Indicates whether the current UTC time offset value is valid."
    ::= { vtssPtpConfigClocksTimePropertiesDsEntry 3 }

vtssPtpConfigClocksTimePropertiesDsLeap59 OBJECT-TYPE
    SYNTAX      TruthValue
    MAX-ACCESS  read-write
    STATUS      current
    DESCRIPTION
        "Indicates that the last minute of the day has only 59 seconds."
    ::= { vtssPtpConfigClocksTimePropertiesDsEntry 4 }

vtssPtpConfigClocksTimePropertiesDsLeap61 OBJECT-TYPE
    SYNTAX      TruthValue
    MAX-ACCESS  read-write
    STATUS      current
    DESCRIPTION
        "Indicates that the last minute of the day has 61 seconds."
    ::= { vtssPtpConfigClocksTimePropertiesDsEntry 5 }

vtssPtpConfigClocksTimePropertiesDsTimeTraceable OBJECT-TYPE
    SYNTAX      TruthValue
    MAX-ACCESS  read-write
    STATUS      current
    DESCRIPTION
        "Indicates that time is traceable to a primary reference."
    ::= { vtssPtpConfigClocksTimePropertiesDsEntry 6 }

vtssPtpConfigClocksTimePropertiesDsFrequencyTraceable OBJECT-TYPE
    SYNTAX      TruthValue
    MAX-ACCESS  read-write
    STATUS      current
    DESCRIPTION
        "Indicates that frequency is traceable to a primary reference."
    ::= { vtssPtpConfigClocksTimePropertiesDsEntry 7 }

vtssPtpConfigClocksTimePropertiesDsPtpTimescale OBJECT-TYPE
    SYNTAX      TruthValue
    MAX-ACCESS  read-write
    STATUS      current
    DESCRIPTION
        "Indicates whether timescale of the grandmaster clock is PTP."
    ::= { vtssPtpConfigClocksTimePropertiesDsEntry 8 }

vtssPtpConfigClocksTimePropertiesDsTimeSource OBJECT-TYPE
    SYNTAX      VTSSUnsigned8
    MAX-ACCESS  read-write
    STATUS      current
    DESCRIPTION
        "Source of time used by the grandmaster clock.
         
         Value representation : 16 (Atomic clock), 32 (GPS), 48 (Terrestrial
         radio), 64 (PTP), 80 (NTP), 96 (Hand set), 144 (Other), 160 (Internal
         oscillator)."
    ::= { vtssPtpConfigClocksTimePropertiesDsEntry 9 }

vtssPtpConfigClocksTimePropertiesDsPendingLeap OBJECT-TYPE
    SYNTAX      TruthValue
    MAX-ACCESS  read-write
    STATUS      current
    DESCRIPTION
        "Indicates whether a leap event is pending."
    ::= { vtssPtpConfigClocksTimePropertiesDsEntry 10 }

vtssPtpConfigClocksTimePropertiesDsLeapDate OBJECT-TYPE
    SYNTAX      VTSSUnsigned16
    MAX-ACCESS  read-write
    STATUS      current
    DESCRIPTION
        "Date of leap event represented as number of days after 1970/01/01"
    ::= { vtssPtpConfigClocksTimePropertiesDsEntry 11 }

vtssPtpConfigClocksTimePropertiesDsLeapType OBJECT-TYPE
    SYNTAX      VTSSptpLeapSecondType
    MAX-ACCESS  read-write
    STATUS      current
    DESCRIPTION
        "Type of leap event i.e. leap59 or leap61."
    ::= { vtssPtpConfigClocksTimePropertiesDsEntry 12 }

vtssPtpConfigClocksFilterParametersTable OBJECT-TYPE
    SYNTAX      SEQUENCE OF VTSSPtpConfigClocksFilterParametersEntry
    MAX-ACCESS  not-accessible
    STATUS      current
    DESCRIPTION
        "This is the configurable part of the PTP clocks filter parameters."
    ::= { vtssPtpConfigClocks 4 }

vtssPtpConfigClocksFilterParametersEntry OBJECT-TYPE
    SYNTAX      VTSSPtpConfigClocksFilterParametersEntry
    MAX-ACCESS  not-accessible
    STATUS      current
    DESCRIPTION
        "The clockId index must be a value must be a value from 0 up to the
         number of PTP clocks minus one."
    INDEX       { vtssPtpConfigClocksFilterParametersClockId }
    ::= { vtssPtpConfigClocksFilterParametersTable 1 }

VTSSPtpConfigClocksFilterParametersEntry ::= SEQUENCE {
    vtssPtpConfigClocksFilterParametersClockId      Integer32,
    vtssPtpConfigClocksFilterParametersDelayFilter  Unsigned32,
    vtssPtpConfigClocksFilterParametersPeriod       Unsigned32,
    vtssPtpConfigClocksFilterParametersDist         Unsigned32
}

vtssPtpConfigClocksFilterParametersClockId OBJECT-TYPE
    SYNTAX      Integer32 (0..32767)
    MAX-ACCESS  accessible-for-notify
    STATUS      current
    DESCRIPTION
        "-"
    ::= { vtssPtpConfigClocksFilterParametersEntry 1 }

vtssPtpConfigClocksFilterParametersDelayFilter OBJECT-TYPE
    SYNTAX      Unsigned32
    MAX-ACCESS  read-write
    STATUS      current
    DESCRIPTION
        "Defines the time constant of the delay filter."
    ::= { vtssPtpConfigClocksFilterParametersEntry 2 }

vtssPtpConfigClocksFilterParametersPeriod OBJECT-TYPE
    SYNTAX      Unsigned32
    MAX-ACCESS  read-write
    STATUS      current
    DESCRIPTION
        "Defines the period of the offset filter."
    ::= { vtssPtpConfigClocksFilterParametersEntry 4 }

vtssPtpConfigClocksFilterParametersDist OBJECT-TYPE
    SYNTAX      Unsigned32
    MAX-ACCESS  read-write
    STATUS      current
    DESCRIPTION
        "Sets the dist value of the offset filter."
    ::= { vtssPtpConfigClocksFilterParametersEntry 5 }

vtssPtpConfigClocksServoParametersTable OBJECT-TYPE
    SYNTAX      SEQUENCE OF VTSSPtpConfigClocksServoParametersEntry
    MAX-ACCESS  not-accessible
    STATUS      current
    DESCRIPTION
        "This is the configurable part of the PTP clocks servo parameters."
    ::= { vtssPtpConfigClocks 5 }

vtssPtpConfigClocksServoParametersEntry OBJECT-TYPE
    SYNTAX      VTSSPtpConfigClocksServoParametersEntry
    MAX-ACCESS  not-accessible
    STATUS      current
    DESCRIPTION
        "The clockId index must be a value must be a value from 0 up to the
         number of PTP clocks minus one."
    INDEX       { vtssPtpConfigClocksServoParametersClockId }
    ::= { vtssPtpConfigClocksServoParametersTable 1 }

VTSSPtpConfigClocksServoParametersEntry ::= SEQUENCE {
    vtssPtpConfigClocksServoParametersClockId             Integer32,
    vtssPtpConfigClocksServoParametersDisplay             TruthValue,
    vtssPtpConfigClocksServoParametersPEnable             TruthValue,
    vtssPtpConfigClocksServoParametersIEnable             TruthValue,
    vtssPtpConfigClocksServoParametersDEnable             TruthValue,
    vtssPtpConfigClocksServoParametersPval                Unsigned32,
    vtssPtpConfigClocksServoParametersIval                Unsigned32,
    vtssPtpConfigClocksServoParametersDval                Unsigned32,
    vtssPtpConfigClocksServoParametersSrvOption           VTSSptpServoClockOption,
    vtssPtpConfigClocksServoParametersSynceThreshold      Unsigned32,
    vtssPtpConfigClocksServoParametersSynceAp             Unsigned32,
    vtssPtpConfigClocksServoParametersHoFilter            Integer32,
    vtssPtpConfigClocksServoParametersStableAdjThreshold  VTSSUnsigned64,
    vtssPtpConfigClocksServoParametersGain                Unsigned32
}

vtssPtpConfigClocksServoParametersClockId OBJECT-TYPE
    SYNTAX      Integer32 (0..32767)
    MAX-ACCESS  accessible-for-notify
    STATUS      current
    DESCRIPTION
        "-"
    ::= { vtssPtpConfigClocksServoParametersEntry 1 }

vtssPtpConfigClocksServoParametersDisplay OBJECT-TYPE
    SYNTAX      TruthValue
    MAX-ACCESS  read-write
    STATUS      current
    DESCRIPTION
        "Indicates whether output shall be sent to the debug terminal."
    ::= { vtssPtpConfigClocksServoParametersEntry 2 }

vtssPtpConfigClocksServoParametersPEnable OBJECT-TYPE
    SYNTAX      TruthValue
    MAX-ACCESS  read-write
    STATUS      current
    DESCRIPTION
        "Indicates whether P-value of servo algorithm shall be used."
    ::= { vtssPtpConfigClocksServoParametersEntry 3 }

vtssPtpConfigClocksServoParametersIEnable OBJECT-TYPE
    SYNTAX      TruthValue
    MAX-ACCESS  read-write
    STATUS      current
    DESCRIPTION
        "Indicates whether I-value of servo algorithm shall be used."
    ::= { vtssPtpConfigClocksServoParametersEntry 4 }

vtssPtpConfigClocksServoParametersDEnable OBJECT-TYPE
    SYNTAX      TruthValue
    MAX-ACCESS  read-write
    STATUS      current
    DESCRIPTION
        "Indicates whether D-value of servo algorithm shall be used."
    ::= { vtssPtpConfigClocksServoParametersEntry 5 }

vtssPtpConfigClocksServoParametersPval OBJECT-TYPE
    SYNTAX      Unsigned32
    MAX-ACCESS  read-write
    STATUS      current
    DESCRIPTION
        "P-value of the offset filter. Range 1 to 10000."
    ::= { vtssPtpConfigClocksServoParametersEntry 6 }

vtssPtpConfigClocksServoParametersIval OBJECT-TYPE
    SYNTAX      Unsigned32
    MAX-ACCESS  read-write
    STATUS      current
    DESCRIPTION
        "I-value of the offset filter. Range 1 to 10000."
    ::= { vtssPtpConfigClocksServoParametersEntry 7 }

vtssPtpConfigClocksServoParametersDval OBJECT-TYPE
    SYNTAX      Unsigned32
    MAX-ACCESS  read-write
    STATUS      current
    DESCRIPTION
        "D-value of the offset filter. Range 1 to 10000."
    ::= { vtssPtpConfigClocksServoParametersEntry 8 }

vtssPtpConfigClocksServoParametersSrvOption OBJECT-TYPE
    SYNTAX      VTSSptpServoClockOption
    MAX-ACCESS  read-write
    STATUS      current
    DESCRIPTION
        "Indicates whether clock is free running or locked to SyncE. Valid
         options : clockFree, clockSyncE."
    ::= { vtssPtpConfigClocksServoParametersEntry 9 }

vtssPtpConfigClocksServoParametersSynceThreshold OBJECT-TYPE
    SYNTAX      Unsigned32
    MAX-ACCESS  read-write
    STATUS      current
    DESCRIPTION
        "SyncE Threshold. Range 1 to 1000."
    ::= { vtssPtpConfigClocksServoParametersEntry 10 }

vtssPtpConfigClocksServoParametersSynceAp OBJECT-TYPE
    SYNTAX      Unsigned32
    MAX-ACCESS  read-write
    STATUS      current
    DESCRIPTION
        "SyncE Ap. Range 1 to 40."
    ::= { vtssPtpConfigClocksServoParametersEntry 11 }

vtssPtpConfigClocksServoParametersHoFilter OBJECT-TYPE
    SYNTAX      Integer32
    MAX-ACCESS  read-write
    STATUS      current
    DESCRIPTION
        "Holdoff low pass filter constant. Range 10 to 86000."
    ::= { vtssPtpConfigClocksServoParametersEntry 12 }

vtssPtpConfigClocksServoParametersStableAdjThreshold OBJECT-TYPE
    SYNTAX      VTSSUnsigned64
    MAX-ACCESS  read-write
    STATUS      current
    DESCRIPTION
        "Threshold at which offset is assumed to be stable. Range 1 to 3000."
    ::= { vtssPtpConfigClocksServoParametersEntry 13 }

vtssPtpConfigClocksServoParametersGain OBJECT-TYPE
    SYNTAX      Unsigned32
    MAX-ACCESS  read-write
    STATUS      current
    DESCRIPTION
        "gain-value of the offset filter. Range 1 to 10000."
    ::= { vtssPtpConfigClocksServoParametersEntry 14 }

vtssPtpConfigClocksSlaveConfigTable OBJECT-TYPE
    SYNTAX      SEQUENCE OF VTSSPtpConfigClocksSlaveConfigEntry
    MAX-ACCESS  not-accessible
    STATUS      current
    DESCRIPTION
        "This is the configurable part of the PTP clocks slave configuration."
    ::= { vtssPtpConfigClocks 6 }

vtssPtpConfigClocksSlaveConfigEntry OBJECT-TYPE
    SYNTAX      VTSSPtpConfigClocksSlaveConfigEntry
    MAX-ACCESS  not-accessible
    STATUS      current
    DESCRIPTION
        "The clockId index must be a value must be a value from 0 up to the
         number of PTP clocks minus one."
    INDEX       { vtssPtpConfigClocksSlaveConfigClockId }
    ::= { vtssPtpConfigClocksSlaveConfigTable 1 }

VTSSPtpConfigClocksSlaveConfigEntry ::= SEQUENCE {
    vtssPtpConfigClocksSlaveConfigClockId       Integer32,
    vtssPtpConfigClocksSlaveConfigStableOffset  Unsigned32,
    vtssPtpConfigClocksSlaveConfigOffsetOk      Unsigned32,
    vtssPtpConfigClocksSlaveConfigOffsetFail    Unsigned32
}

vtssPtpConfigClocksSlaveConfigClockId OBJECT-TYPE
    SYNTAX      Integer32 (0..32767)
    MAX-ACCESS  accessible-for-notify
    STATUS      current
    DESCRIPTION
        "-"
    ::= { vtssPtpConfigClocksSlaveConfigEntry 1 }

vtssPtpConfigClocksSlaveConfigStableOffset OBJECT-TYPE
    SYNTAX      Unsigned32
    MAX-ACCESS  read-write
    STATUS      current
    DESCRIPTION
        "Stable offset threshold in ns."
    ::= { vtssPtpConfigClocksSlaveConfigEntry 2 }

vtssPtpConfigClocksSlaveConfigOffsetOk OBJECT-TYPE
    SYNTAX      Unsigned32
    MAX-ACCESS  read-write
    STATUS      current
    DESCRIPTION
        "Offset OK threshold in ns."
    ::= { vtssPtpConfigClocksSlaveConfigEntry 3 }

vtssPtpConfigClocksSlaveConfigOffsetFail OBJECT-TYPE
    SYNTAX      Unsigned32
    MAX-ACCESS  read-write
    STATUS      current
    DESCRIPTION
        "Offset fail threshold in ns."
    ::= { vtssPtpConfigClocksSlaveConfigEntry 4 }

vtssPtpConfigClocksUnicastSlaveConfigTable OBJECT-TYPE
    SYNTAX      SEQUENCE OF VTSSPtpConfigClocksUnicastSlaveConfigEntry
    MAX-ACCESS  not-accessible
    STATUS      current
    DESCRIPTION
        "This is the configurable part of the PTP clocks unicast slave
         configuration."
    ::= { vtssPtpConfigClocks 7 }

vtssPtpConfigClocksUnicastSlaveConfigEntry OBJECT-TYPE
    SYNTAX      VTSSPtpConfigClocksUnicastSlaveConfigEntry
    MAX-ACCESS  not-accessible
    STATUS      current
    DESCRIPTION
        "The clockId index must be a value must be a value from 0 up to the
         number of PTP clocks minus one."
    INDEX       { vtssPtpConfigClocksUnicastSlaveConfigClockId,
                  vtssPtpConfigClocksUnicastSlaveConfigMasterId }
    ::= { vtssPtpConfigClocksUnicastSlaveConfigTable 1 }

VTSSPtpConfigClocksUnicastSlaveConfigEntry ::= SEQUENCE {
    vtssPtpConfigClocksUnicastSlaveConfigClockId    Integer32,
    vtssPtpConfigClocksUnicastSlaveConfigMasterId   Integer32,
    vtssPtpConfigClocksUnicastSlaveConfigDuration   Unsigned32,
    vtssPtpConfigClocksUnicastSlaveConfigIpAddress  IpAddress
}

vtssPtpConfigClocksUnicastSlaveConfigClockId OBJECT-TYPE
    SYNTAX      Integer32 (0..32767)
    MAX-ACCESS  accessible-for-notify
    STATUS      current
    DESCRIPTION
        "-"
    ::= { vtssPtpConfigClocksUnicastSlaveConfigEntry 1 }

vtssPtpConfigClocksUnicastSlaveConfigMasterId OBJECT-TYPE
    SYNTAX      Integer32 (0..32767)
    MAX-ACCESS  accessible-for-notify
    STATUS      current
    DESCRIPTION
        "-"
    ::= { vtssPtpConfigClocksUnicastSlaveConfigEntry 2 }

vtssPtpConfigClocksUnicastSlaveConfigDuration OBJECT-TYPE
    SYNTAX      Unsigned32
    MAX-ACCESS  read-write
    STATUS      current
    DESCRIPTION
        "Number of seconds for which the Announce/Sync messages are requested."
    ::= { vtssPtpConfigClocksUnicastSlaveConfigEntry 3 }

vtssPtpConfigClocksUnicastSlaveConfigIpAddress OBJECT-TYPE
    SYNTAX      IpAddress
    MAX-ACCESS  read-write
    STATUS      current
    DESCRIPTION
        "IPv4 address of requested master clock."
    ::= { vtssPtpConfigClocksUnicastSlaveConfigEntry 4 }

vtssPtpConfigClocksPortDsTable OBJECT-TYPE
    SYNTAX      SEQUENCE OF VTSSPtpConfigClocksPortDsEntry
    MAX-ACCESS  not-accessible
    STATUS      current
    DESCRIPTION
        "This is the configurable part of the PTP clocks PortDS."
    ::= { vtssPtpConfigClocks 8 }

vtssPtpConfigClocksPortDsEntry OBJECT-TYPE
    SYNTAX      VTSSPtpConfigClocksPortDsEntry
    MAX-ACCESS  not-accessible
    STATUS      current
    DESCRIPTION
        "The clockId index must be a value must be a value from 0 up to the
         number of PTP clocks minus one."
    INDEX       { vtssPtpConfigClocksPortDsClockId,
                  vtssPtpConfigClocksPortDsPortId }
    ::= { vtssPtpConfigClocksPortDsTable 1 }

VTSSPtpConfigClocksPortDsEntry ::= SEQUENCE {
    vtssPtpConfigClocksPortDsClockId                                  Integer32,
    vtssPtpConfigClocksPortDsPortId                                   VTSSInterfaceIndex,
    vtssPtpConfigClocksPortDsEnabled                                  TruthValue,
    vtssPtpConfigClocksPortDsLogAnnounceInterval                      VTSSInteger16,
    vtssPtpConfigClocksPortDsAnnounceReceiptTimeout                   VTSSUnsigned8,
    vtssPtpConfigClocksPortDsLogSyncInterval                          VTSSInteger16,
    vtssPtpConfigClocksPortDsDelayMechanism                           VTSSptpDelayMechanism,
    vtssPtpConfigClocksPortDsLogMinPdelayReqInterval                  VTSSInteger16,
    vtssPtpConfigClocksPortDsDelayAsymmetry                           VTSSInteger64,
    vtssPtpConfigClocksPortDsIngressLatency                           VTSSInteger64,
    vtssPtpConfigClocksPortDsEgressLatency                            VTSSInteger64,
    vtssPtpConfigClocksPortDsPortInternal                             TruthValue,
    vtssPtpConfigClocksPortDsVersionNumber                            VTSSUnsigned16,
    vtssPtpConfigClocksPortDsMcastAddr                                VTSSptpDestAdrType,
    vtssPtpConfigClocksPortDsMasterOnly                               TruthValue,
    vtssPtpConfigClocksPortDsLocalPriority                            VTSSUnsigned8,
    vtssPtpConfigClocksPortDsNotMaster                                TruthValue,
    vtssPtpConfigClocksPortDsAs2020                                   TruthValue,
    vtssPtpConfigClocksPortDsC8021asNeighborPropDelayThresh           VTSSInteger64,
    vtssPtpConfigClocksPortDsC8021asSyncReceiptTimeout                VTSSUnsigned8,
    vtssPtpConfigClocksPortDsC8021asAllowedLostResponses              VTSSUnsigned8,
    vtssPtpConfigClocksPortDsC8021asAllowedFaults                     VTSSUnsigned8,
    vtssPtpConfigClocksPortDsC8021asUseMgtSettableLogAnnounceIntvl    TruthValue,
    vtssPtpConfigClocksPortDsC8021asUseMgtSettableLogSyncIntvl        TruthValue,
    vtssPtpConfigClocksPortDsC8021asUseMgtSettableLogPdelayReqIntvl   TruthValue,
    vtssPtpConfigClocksPortDsC8021asMgtSettableLogAnnounceIntvl       VTSSInteger8,
    vtssPtpConfigClocksPortDsC8021asMgtSettableLogSyncIntvl           VTSSInteger8,
    vtssPtpConfigClocksPortDsC8021asMgtSettableLogPdelayReqIntvl      VTSSInteger8,
    vtssPtpConfigClocksPortDsC8021asUseMgtSettableLogGptpCapMsgIntvl  TruthValue,
    vtssPtpConfigClocksPortDsC8021asMgtSettableLogGptpCapMsgIntvl     VTSSInteger8,
    vtssPtpConfigClocksPortDsC8021GptpCapableReceiptTimeout           VTSSUnsigned8,
    vtssPtpConfigClocksPortDsC8021InitialLogGptpCapableMessageIntvl   VTSSInteger8,
    vtssPtpConfigClocksPortDsC8021asUseMgtSetCompNbrRateRatio         TruthValue,
    vtssPtpConfigClocksPortDsC8021asMgtSetCompNbrRateRatio            TruthValue,
    vtssPtpConfigClocksPortDsC8021asUseMgtSetCompMeanLinkDelay        TruthValue,
    vtssPtpConfigClocksPortDsC8021asmgtSetCompMeanLinkDelay           TruthValue
}

vtssPtpConfigClocksPortDsClockId OBJECT-TYPE
    SYNTAX      Integer32 (0..32767)
    MAX-ACCESS  accessible-for-notify
    STATUS      current
    DESCRIPTION
        "-"
    ::= { vtssPtpConfigClocksPortDsEntry 1 }

vtssPtpConfigClocksPortDsPortId OBJECT-TYPE
    SYNTAX      VTSSInterfaceIndex
    MAX-ACCESS  accessible-for-notify
    STATUS      current
    DESCRIPTION
        "-"
    ::= { vtssPtpConfigClocksPortDsEntry 2 }

vtssPtpConfigClocksPortDsEnabled OBJECT-TYPE
    SYNTAX      TruthValue
    MAX-ACCESS  read-write
    STATUS      current
    DESCRIPTION
        "Defines whether port is enabled."
    ::= { vtssPtpConfigClocksPortDsEntry 3 }

vtssPtpConfigClocksPortDsLogAnnounceInterval OBJECT-TYPE
    SYNTAX      VTSSInteger16
    MAX-ACCESS  read-write
    STATUS      current
    DESCRIPTION
        "Interval between announce message transmissions. Range -3 to 4."
    ::= { vtssPtpConfigClocksPortDsEntry 4 }

vtssPtpConfigClocksPortDsAnnounceReceiptTimeout OBJECT-TYPE
    SYNTAX      VTSSUnsigned8
    MAX-ACCESS  read-write
    STATUS      current
    DESCRIPTION
        "The timeout for receiving announce messages on the port. Range 1 to 10."
    ::= { vtssPtpConfigClocksPortDsEntry 5 }

vtssPtpConfigClocksPortDsLogSyncInterval OBJECT-TYPE
    SYNTAX      VTSSInteger16
    MAX-ACCESS  read-write
    STATUS      current
    DESCRIPTION
        "The interval for issuing sync meesages in the master. Range -7 to 4."
    ::= { vtssPtpConfigClocksPortDsEntry 6 }

vtssPtpConfigClocksPortDsDelayMechanism OBJECT-TYPE
    SYNTAX      VTSSptpDelayMechanism
    MAX-ACCESS  read-write
    STATUS      current
    DESCRIPTION
        "The delay mechanism used for the port. Valid options : e2e, p2p,
         commonP2P, disabled."
    ::= { vtssPtpConfigClocksPortDsEntry 7 }

vtssPtpConfigClocksPortDsLogMinPdelayReqInterval OBJECT-TYPE
    SYNTAX      VTSSInteger16
    MAX-ACCESS  read-write
    STATUS      current
    DESCRIPTION
        "The value of logMinPdelayReqInterval. Range -7 to 5."
    ::= { vtssPtpConfigClocksPortDsEntry 8 }

vtssPtpConfigClocksPortDsDelayAsymmetry OBJECT-TYPE
    SYNTAX      VTSSInteger64
    MAX-ACCESS  read-write
    STATUS      current
    DESCRIPTION
        "The value for the communication path asymmetry. Range -10000 to 10000."
    ::= { vtssPtpConfigClocksPortDsEntry 9 }

vtssPtpConfigClocksPortDsIngressLatency OBJECT-TYPE
    SYNTAX      VTSSInteger64
    MAX-ACCESS  read-write
    STATUS      current
    DESCRIPTION
        "Ingress delay for port. Range -10000 to 10000."
    ::= { vtssPtpConfigClocksPortDsEntry 10 }

vtssPtpConfigClocksPortDsEgressLatency OBJECT-TYPE
    SYNTAX      VTSSInteger64
    MAX-ACCESS  read-write
    STATUS      current
    DESCRIPTION
        "Egress delay for port. Range -10000 to 10000."
    ::= { vtssPtpConfigClocksPortDsEntry 11 }

vtssPtpConfigClocksPortDsPortInternal OBJECT-TYPE
    SYNTAX      TruthValue
    MAX-ACCESS  read-write
    STATUS      current
    DESCRIPTION
        "Defines whether port is enabled as an internal interface."
    ::= { vtssPtpConfigClocksPortDsEntry 12 }

vtssPtpConfigClocksPortDsVersionNumber OBJECT-TYPE
    SYNTAX      VTSSUnsigned16
    MAX-ACCESS  read-write
    STATUS      current
    DESCRIPTION
        "The version of PTP being used by the port. Current version is 2."
    ::= { vtssPtpConfigClocksPortDsEntry 13 }

vtssPtpConfigClocksPortDsMcastAddr OBJECT-TYPE
    SYNTAX      VTSSptpDestAdrType
    MAX-ACCESS  read-write
    STATUS      current
    DESCRIPTION
        "The multicast address used. Valid options : default or linkLocal."
    ::= { vtssPtpConfigClocksPortDsEntry 14 }

vtssPtpConfigClocksPortDsMasterOnly OBJECT-TYPE
    SYNTAX      TruthValue
    MAX-ACCESS  read-write
    STATUS      current
    DESCRIPTION
        "When true, the port cannot enter slave state."
    ::= { vtssPtpConfigClocksPortDsEntry 15 }

vtssPtpConfigClocksPortDsLocalPriority OBJECT-TYPE
    SYNTAX      VTSSUnsigned8
    MAX-ACCESS  read-write
    STATUS      current
    DESCRIPTION
        "The local priority value."
    ::= { vtssPtpConfigClocksPortDsEntry 16 }

vtssPtpConfigClocksPortDsNotMaster OBJECT-TYPE
    SYNTAX      TruthValue
    MAX-ACCESS  read-write
    STATUS      current
    DESCRIPTION
        "When true, the port will not enter Master state."
    ::= { vtssPtpConfigClocksPortDsEntry 17 }

vtssPtpConfigClocksPortDsAs2020 OBJECT-TYPE
    SYNTAX      TruthValue
    MAX-ACCESS  read-write
    STATUS      current
    DESCRIPTION
        "When true, the 802.1as version will be 2020."
    ::= { vtssPtpConfigClocksPortDsEntry 18 }

vtssPtpConfigClocksPortDsC8021asNeighborPropDelayThresh OBJECT-TYPE
    SYNTAX      VTSSInteger64
    MAX-ACCESS  read-write
    STATUS      current
    DESCRIPTION
        "max allowed meanLinkDelay. Range 0 to 4e9."
    ::= { vtssPtpConfigClocksPortDsEntry 19 }

vtssPtpConfigClocksPortDsC8021asSyncReceiptTimeout OBJECT-TYPE
    SYNTAX      VTSSUnsigned8
    MAX-ACCESS  read-write
    STATUS      current
    DESCRIPTION
        "Number of time-synchronization transmission intervals that a slave port
         waits without receiving synchronization information."
    ::= { vtssPtpConfigClocksPortDsEntry 20 }

vtssPtpConfigClocksPortDsC8021asAllowedLostResponses OBJECT-TYPE
    SYNTAX      VTSSUnsigned8
    MAX-ACCESS  read-write
    STATUS      current
    DESCRIPTION
        "Number of Pdelay_Req messages for which a valid response is not
         received, above which a port is considered to not be exchanging peer
         delay messages with its neighbor.
         
         Range 0 to 10."
    ::= { vtssPtpConfigClocksPortDsEntry 21 }

vtssPtpConfigClocksPortDsC8021asAllowedFaults OBJECT-TYPE
    SYNTAX      VTSSUnsigned8 (1..255)
    MAX-ACCESS  read-write
    STATUS      current
    DESCRIPTION
        "Number of allowed instances where the computed mean propagation delay
         exceeds the threshold meanLinkDelayThresh and/or instances where the
         computation of neighborRateRatio is invalid."
    ::= { vtssPtpConfigClocksPortDsEntry 22 }

vtssPtpConfigClocksPortDsC8021asUseMgtSettableLogAnnounceIntvl OBJECT-TYPE
    SYNTAX      TruthValue
    MAX-ACCESS  read-write
    STATUS      current
    DESCRIPTION
        "Flag to decide the value to be used for Announce interval. Range -3 to
         4."
    ::= { vtssPtpConfigClocksPortDsEntry 23 }

vtssPtpConfigClocksPortDsC8021asUseMgtSettableLogSyncIntvl OBJECT-TYPE
    SYNTAX      TruthValue
    MAX-ACCESS  read-write
    STATUS      current
    DESCRIPTION
        "Flag to decide the value to be used for sync packet interval. Range -7
         to 4."
    ::= { vtssPtpConfigClocksPortDsEntry 24 }

vtssPtpConfigClocksPortDsC8021asUseMgtSettableLogPdelayReqIntvl OBJECT-TYPE
    SYNTAX      TruthValue
    MAX-ACCESS  read-write
    STATUS      current
    DESCRIPTION
        "Flag to decide the value to be used for Peer delay request interval.
         Range -7 to 5."
    ::= { vtssPtpConfigClocksPortDsEntry 25 }

vtssPtpConfigClocksPortDsC8021asMgtSettableLogAnnounceIntvl OBJECT-TYPE
    SYNTAX      VTSSInteger8 (-3..4)
    MAX-ACCESS  read-write
    STATUS      current
    DESCRIPTION
        "If useMgmtAnnounce is set, port uses this value to decide the Announce
         packet interval , else default value is used. Range is -3 to 4."
    ::= { vtssPtpConfigClocksPortDsEntry 26 }

vtssPtpConfigClocksPortDsC8021asMgtSettableLogSyncIntvl OBJECT-TYPE
    SYNTAX      VTSSInteger8 (-7..4)
    MAX-ACCESS  read-write
    STATUS      current
    DESCRIPTION
        "If useMgmtSync is set, port uses this value to decide the sync packet
         interval , else default value is used. Range is -7 to 4 ."
    ::= { vtssPtpConfigClocksPortDsEntry 27 }

vtssPtpConfigClocksPortDsC8021asMgtSettableLogPdelayReqIntvl OBJECT-TYPE
    SYNTAX      VTSSInteger8 (-7..5)
    MAX-ACCESS  read-write
    STATUS      current
    DESCRIPTION
        "If useMgmtPdelay is set, port uses this value to decide the Peer delay
         request packet interval , else default value is used. Range is -7 to 5."
    ::= { vtssPtpConfigClocksPortDsEntry 28 }

vtssPtpConfigClocksPortDsC8021asUseMgtSettableLogGptpCapMsgIntvl OBJECT-TYPE
    SYNTAX      TruthValue
    MAX-ACCESS  read-write
    STATUS      current
    DESCRIPTION
        "Flag to set OPTION to configure gptp interval."
    ::= { vtssPtpConfigClocksPortDsEntry 29 }

vtssPtpConfigClocksPortDsC8021asMgtSettableLogGptpCapMsgIntvl OBJECT-TYPE
    SYNTAX      VTSSInteger8
    MAX-ACCESS  read-write
    STATUS      current
    DESCRIPTION
        "If UseMgtSettableLogGptpCapableMessageInterval is set, set gptp capable
         tlv interval. Range -7 to 4."
    ::= { vtssPtpConfigClocksPortDsEntry 30 }

vtssPtpConfigClocksPortDsC8021GptpCapableReceiptTimeout OBJECT-TYPE
    SYNTAX      VTSSUnsigned8 (1..255)
    MAX-ACCESS  read-write
    STATUS      current
    DESCRIPTION
        "Set gPtpCapableReceiptTimeout value per port."
    ::= { vtssPtpConfigClocksPortDsEntry 31 }

vtssPtpConfigClocksPortDsC8021InitialLogGptpCapableMessageIntvl OBJECT-TYPE
    SYNTAX      VTSSInteger8
    MAX-ACCESS  read-write
    STATUS      current
    DESCRIPTION
        "Set gptp interval per port."
    ::= { vtssPtpConfigClocksPortDsEntry 32 }

vtssPtpConfigClocksPortDsC8021asUseMgtSetCompNbrRateRatio OBJECT-TYPE
    SYNTAX      TruthValue
    MAX-ACCESS  read-write
    STATUS      current
    DESCRIPTION
        "This value determines the source of the value of
         computeNeighborRateRatio. 'True' indicates source as
         'mgtSettablecomputeNeighborRateRatio'. Otherwise, either initial value
         or value set by LinkDelayIntervalSetting state machine."
    ::= { vtssPtpConfigClocksPortDsEntry 33 }

vtssPtpConfigClocksPortDsC8021asMgtSetCompNbrRateRatio OBJECT-TYPE
    SYNTAX      TruthValue
    MAX-ACCESS  read-write
    STATUS      current
    DESCRIPTION
        "This value indicates the input through management interface whether to
         compute neighbor rate ratio or not."
    ::= { vtssPtpConfigClocksPortDsEntry 34 }

vtssPtpConfigClocksPortDsC8021asUseMgtSetCompMeanLinkDelay OBJECT-TYPE
    SYNTAX      TruthValue
    MAX-ACCESS  read-write
    STATUS      current
    DESCRIPTION
        "This value determines the source of the value of computeMeanLinkDelay.
         'True' indicates source as 'mgtSettableComputeMeanLinkDelay'.
         Otherwise, initial value or value set by LinkDelayInterval State
         machine is used."
    ::= { vtssPtpConfigClocksPortDsEntry 35 }

vtssPtpConfigClocksPortDsC8021asmgtSetCompMeanLinkDelay OBJECT-TYPE
    SYNTAX      TruthValue
    MAX-ACCESS  read-write
    STATUS      current
    DESCRIPTION
        "This value indicates the input through management interface whether to
         compute Mean Link delay or not."
    ::= { vtssPtpConfigClocksPortDsEntry 36 }

vtssPtpConfigClocksVirtualPortCfgTable OBJECT-TYPE
    SYNTAX      SEQUENCE OF VTSSPtpConfigClocksVirtualPortCfgEntry
    MAX-ACCESS  not-accessible
    STATUS      current
    DESCRIPTION
        "This is the configurable part of the PTP clocks virtual port
         parameters."
    ::= { vtssPtpConfigClocks 9 }

vtssPtpConfigClocksVirtualPortCfgEntry OBJECT-TYPE
    SYNTAX      VTSSPtpConfigClocksVirtualPortCfgEntry
    MAX-ACCESS  not-accessible
    STATUS      current
    DESCRIPTION
        "The clockId index must be a value must be a value from 0 up to the
         number of PTP clocks minus one."
    INDEX       { vtssPtpConfigClocksVirtualPortCfgClockId }
    ::= { vtssPtpConfigClocksVirtualPortCfgTable 1 }

VTSSPtpConfigClocksVirtualPortCfgEntry ::= SEQUENCE {
    vtssPtpConfigClocksVirtualPortCfgClockId                         Integer32,
    vtssPtpConfigClocksVirtualPortCfgEnable                          TruthValue,
    vtssPtpConfigClocksVirtualPortCfgInputPin                        VTSSUnsigned16,
    vtssPtpConfigClocksVirtualPortCfgClockQualityClockClass          VTSSUnsigned8,
    vtssPtpConfigClocksVirtualPortCfgClockQualityClockAccuracy       VTSSUnsigned8,
    vtssPtpConfigClocksVirtualPortCfgClockQualityOffsetScaledLogVar  VTSSUnsigned16,
    vtssPtpConfigClocksVirtualPortCfgPriority1                       VTSSUnsigned8,
    vtssPtpConfigClocksVirtualPortCfgPriority2                       VTSSUnsigned8,
    vtssPtpConfigClocksVirtualPortCfgLocalPriority                   VTSSUnsigned8,
    vtssPtpConfigClocksVirtualPortCfgVirtualPortMode                 VTSSptpVirtualPortmode,
    vtssPtpConfigClocksVirtualPortCfgOutputPin                       VTSSUnsigned16,
    vtssPtpConfigClocksVirtualPortCfgProto                           VTSSptpTodProtocol,
    vtssPtpConfigClocksVirtualPortCfgPortnum                         Unsigned32,
    vtssPtpConfigClocksVirtualPortCfgPpsDelay                        Unsigned32,
    vtssPtpConfigClocksVirtualPortCfgCurrentUtcOffset                VTSSInteger16,
    vtssPtpConfigClocksVirtualPortCfgCurrentUtcOffsetValid           TruthValue,
    vtssPtpConfigClocksVirtualPortCfgLeap59                          TruthValue,
    vtssPtpConfigClocksVirtualPortCfgLeap61                          TruthValue,
    vtssPtpConfigClocksVirtualPortCfgTimeTraceable                   TruthValue,
    vtssPtpConfigClocksVirtualPortCfgFrequencyTraceable              TruthValue,
    vtssPtpConfigClocksVirtualPortCfgPtpTimescale                    TruthValue,
    vtssPtpConfigClocksVirtualPortCfgTimeSource                      VTSSUnsigned8,
    vtssPtpConfigClocksVirtualPortCfgPendingLeap                     TruthValue,
    vtssPtpConfigClocksVirtualPortCfgLeapDate                        VTSSUnsigned16,
    vtssPtpConfigClocksVirtualPortCfgLeapType                        VTSSptpLeapSecondType,
    vtssPtpConfigClocksVirtualPortCfgAlarm                           VTSSUnsigned8,
    vtssPtpConfigClocksVirtualPortCfgClockIdentity                   OCTET STRING,
    vtssPtpConfigClocksVirtualPortCfgStepsRemoved                    VTSSUnsigned16
}

vtssPtpConfigClocksVirtualPortCfgClockId OBJECT-TYPE
    SYNTAX      Integer32 (0..32767)
    MAX-ACCESS  accessible-for-notify
    STATUS      current
    DESCRIPTION
        "-"
    ::= { vtssPtpConfigClocksVirtualPortCfgEntry 1 }

vtssPtpConfigClocksVirtualPortCfgEnable OBJECT-TYPE
    SYNTAX      TruthValue
    MAX-ACCESS  read-write
    STATUS      current
    DESCRIPTION
        "Determines whether the virtual port is enabled."
    ::= { vtssPtpConfigClocksVirtualPortCfgEntry 2 }

vtssPtpConfigClocksVirtualPortCfgInputPin OBJECT-TYPE
    SYNTAX      VTSSUnsigned16 (0..3)
    MAX-ACCESS  read-write
    STATUS      current
    DESCRIPTION
        "Input io pin to be used in pps-in mode ."
    ::= { vtssPtpConfigClocksVirtualPortCfgEntry 3 }

vtssPtpConfigClocksVirtualPortCfgClockQualityClockClass OBJECT-TYPE
    SYNTAX      VTSSUnsigned8
    MAX-ACCESS  read-write
    STATUS      current
    DESCRIPTION
        "This is the clock class field of the clock quality structure.
         
         IEEE-1588-2008 value representation : 6 (GM locked to 1pps output), 7
         (GM in holdover after 1pps output), 135 (Boundary clock in holdover),
         165 (Boundary clock out of holdover), 140 (GM out of holdover CAT 1),
         150 (GM out of holdover CAT 2), 160 (GM out of holdover CAT 3), 248
         (Default), 255 (Time slave clock)."
    ::= { vtssPtpConfigClocksVirtualPortCfgEntry 4 }

vtssPtpConfigClocksVirtualPortCfgClockQualityClockAccuracy OBJECT-TYPE
    SYNTAX      VTSSUnsigned8
    MAX-ACCESS  read-write
    STATUS      current
    DESCRIPTION
        "This is the clock accuracy field of the clock quality structure.
         
         Value representation : 32 (25 ns), 33 (100 ns), 34 (250 ns), 35 (1 us),
         36 (2.5 us)37 (10 us), 38 (25 us), 39 (100 us), 40 (250 ns), 41 (1 ms),
         42 (2.5 ms), 43 (10 ms)44 (25 ms), 45 (100 ms), 46 (250 ms), 47 (1 s),
         48 (10 s), 49 (> 10 s), 254 (unknown)."
    ::= { vtssPtpConfigClocksVirtualPortCfgEntry 5 }

vtssPtpConfigClocksVirtualPortCfgClockQualityOffsetScaledLogVar OBJECT-TYPE
    SYNTAX      VTSSUnsigned16
    MAX-ACCESS  read-write
    STATUS      current
    DESCRIPTION
        "This is the offsetScaledLogVariance field of the clock quality
         structure."
    ::= { vtssPtpConfigClocksVirtualPortCfgEntry 6 }

vtssPtpConfigClocksVirtualPortCfgPriority1 OBJECT-TYPE
    SYNTAX      VTSSUnsigned8
    MAX-ACCESS  read-write
    STATUS      current
    DESCRIPTION
        "The priority1 value."
    ::= { vtssPtpConfigClocksVirtualPortCfgEntry 7 }

vtssPtpConfigClocksVirtualPortCfgPriority2 OBJECT-TYPE
    SYNTAX      VTSSUnsigned8
    MAX-ACCESS  read-write
    STATUS      current
    DESCRIPTION
        "The priority2 value."
    ::= { vtssPtpConfigClocksVirtualPortCfgEntry 8 }

vtssPtpConfigClocksVirtualPortCfgLocalPriority OBJECT-TYPE
    SYNTAX      VTSSUnsigned8
    MAX-ACCESS  read-write
    STATUS      current
    DESCRIPTION
        "The local priority value."
    ::= { vtssPtpConfigClocksVirtualPortCfgEntry 9 }

vtssPtpConfigClocksVirtualPortCfgVirtualPortMode OBJECT-TYPE
    SYNTAX      VTSSptpVirtualPortmode
    MAX-ACCESS  read-write
    STATUS      current
    DESCRIPTION
        "Virtual port mode :
         disable/main-auto/sub/main-man/pps-in/pps-out/freq-out"
    ::= { vtssPtpConfigClocksVirtualPortCfgEntry 10 }

vtssPtpConfigClocksVirtualPortCfgOutputPin OBJECT-TYPE
    SYNTAX      VTSSUnsigned16 (0..3)
    MAX-ACCESS  read-write
    STATUS      current
    DESCRIPTION
        "Output io pin to be used in pps-out mode"
    ::= { vtssPtpConfigClocksVirtualPortCfgEntry 11 }

vtssPtpConfigClocksVirtualPortCfgProto OBJECT-TYPE
    SYNTAX      VTSSptpTodProtocol
    MAX-ACCESS  read-write
    STATUS      current
    DESCRIPTION
        "Protocol used to transfer time of day. polyt/zda/gga/rmc/pim/none"
    ::= { vtssPtpConfigClocksVirtualPortCfgEntry 12 }

vtssPtpConfigClocksVirtualPortCfgPortnum OBJECT-TYPE
    SYNTAX      Unsigned32
    MAX-ACCESS  read-write
    STATUS      current
    DESCRIPTION
        "Port number used to transfer tod with pim protocol."
    ::= { vtssPtpConfigClocksVirtualPortCfgEntry 13 }

vtssPtpConfigClocksVirtualPortCfgPpsDelay OBJECT-TYPE
    SYNTAX      Unsigned32
    MAX-ACCESS  read-write
    STATUS      current
    DESCRIPTION
        "PPS delay from source to receiver in sub mode approximated."
    ::= { vtssPtpConfigClocksVirtualPortCfgEntry 14 }

vtssPtpConfigClocksVirtualPortCfgCurrentUtcOffset OBJECT-TYPE
    SYNTAX      VTSSInteger16
    MAX-ACCESS  read-write
    STATUS      current
    DESCRIPTION
        "virtual port's UTC time offset. GNSS servers use UTC time. Range 0 to
         10000."
    ::= { vtssPtpConfigClocksVirtualPortCfgEntry 15 }

vtssPtpConfigClocksVirtualPortCfgCurrentUtcOffsetValid OBJECT-TYPE
    SYNTAX      TruthValue
    MAX-ACCESS  read-write
    STATUS      current
    DESCRIPTION
        "Indicates whether the current UTC time offset value is valid."
    ::= { vtssPtpConfigClocksVirtualPortCfgEntry 16 }

vtssPtpConfigClocksVirtualPortCfgLeap59 OBJECT-TYPE
    SYNTAX      TruthValue
    MAX-ACCESS  read-write
    STATUS      current
    DESCRIPTION
        "Indicates that the last minute of the day has only 59 seconds."
    ::= { vtssPtpConfigClocksVirtualPortCfgEntry 17 }

vtssPtpConfigClocksVirtualPortCfgLeap61 OBJECT-TYPE
    SYNTAX      TruthValue
    MAX-ACCESS  read-write
    STATUS      current
    DESCRIPTION
        "Indicates that the last minute of the day has 61 seconds."
    ::= { vtssPtpConfigClocksVirtualPortCfgEntry 18 }

vtssPtpConfigClocksVirtualPortCfgTimeTraceable OBJECT-TYPE
    SYNTAX      TruthValue
    MAX-ACCESS  read-write
    STATUS      current
    DESCRIPTION
        "Indicates that time is traceable to a primary reference."
    ::= { vtssPtpConfigClocksVirtualPortCfgEntry 19 }

vtssPtpConfigClocksVirtualPortCfgFrequencyTraceable OBJECT-TYPE
    SYNTAX      TruthValue
    MAX-ACCESS  read-write
    STATUS      current
    DESCRIPTION
        "Indicates that frequency is traceable to a primary reference."
    ::= { vtssPtpConfigClocksVirtualPortCfgEntry 20 }

vtssPtpConfigClocksVirtualPortCfgPtpTimescale OBJECT-TYPE
    SYNTAX      TruthValue
    MAX-ACCESS  read-write
    STATUS      current
    DESCRIPTION
        "Indicates whether timescale of the grandmaster clock is PTP."
    ::= { vtssPtpConfigClocksVirtualPortCfgEntry 21 }

vtssPtpConfigClocksVirtualPortCfgTimeSource OBJECT-TYPE
    SYNTAX      VTSSUnsigned8
    MAX-ACCESS  read-write
    STATUS      current
    DESCRIPTION
        "Source of time used by the grandmaster clock."
    ::= { vtssPtpConfigClocksVirtualPortCfgEntry 22 }

vtssPtpConfigClocksVirtualPortCfgPendingLeap OBJECT-TYPE
    SYNTAX      TruthValue
    MAX-ACCESS  read-write
    STATUS      current
    DESCRIPTION
        "Indicates whether a leap event is pending."
    ::= { vtssPtpConfigClocksVirtualPortCfgEntry 23 }

vtssPtpConfigClocksVirtualPortCfgLeapDate OBJECT-TYPE
    SYNTAX      VTSSUnsigned16
    MAX-ACCESS  read-write
    STATUS      current
    DESCRIPTION
        "Date of leap event represented as number of days after 1970/01/01"
    ::= { vtssPtpConfigClocksVirtualPortCfgEntry 24 }

vtssPtpConfigClocksVirtualPortCfgLeapType OBJECT-TYPE
    SYNTAX      VTSSptpLeapSecondType
    MAX-ACCESS  read-write
    STATUS      current
    DESCRIPTION
        "Type of leap event i.e. leap59 or leap61."
    ::= { vtssPtpConfigClocksVirtualPortCfgEntry 25 }

vtssPtpConfigClocksVirtualPortCfgAlarm OBJECT-TYPE
    SYNTAX      VTSSUnsigned8
    MAX-ACCESS  read-write
    STATUS      current
    DESCRIPTION
        "Generate alarm or not on virtual port master to indicate GPS status."
    ::= { vtssPtpConfigClocksVirtualPortCfgEntry 26 }

vtssPtpConfigClocksVirtualPortCfgClockIdentity OBJECT-TYPE
    SYNTAX      OCTET STRING (SIZE(8))
    MAX-ACCESS  read-write
    STATUS      current
    DESCRIPTION
        "This is the 8 byte clockIdentify used by virtual port."
    ::= { vtssPtpConfigClocksVirtualPortCfgEntry 27 }

vtssPtpConfigClocksVirtualPortCfgStepsRemoved OBJECT-TYPE
    SYNTAX      VTSSUnsigned16
    MAX-ACCESS  read-write
    STATUS      current
    DESCRIPTION
        "It is number of PTP clocks traversed from Grandmaster through virtual
         port to reach current clock."
    ::= { vtssPtpConfigClocksVirtualPortCfgEntry 28 }

vtssPtpConfigCmlds OBJECT IDENTIFIER
    ::= { vtssPtpConfig 3 }

vtssPtpConfigCmldsPortDsTable OBJECT-TYPE
    SYNTAX      SEQUENCE OF VTSSPtpConfigCmldsPortDsEntry
    MAX-ACCESS  not-accessible
    STATUS      current
    DESCRIPTION
        "This is the configurable part of the PTP clocks CMLDS PortDS."
    ::= { vtssPtpConfigCmlds 1 }

vtssPtpConfigCmldsPortDsEntry OBJECT-TYPE
    SYNTAX      VTSSPtpConfigCmldsPortDsEntry
    MAX-ACCESS  not-accessible
    STATUS      current
    DESCRIPTION
        "The port_id index must be a value from 0 up to the number of ports."
    INDEX       { vtssPtpConfigCmldsPortDsPortId }
    ::= { vtssPtpConfigCmldsPortDsTable 1 }

VTSSPtpConfigCmldsPortDsEntry ::= SEQUENCE {
    vtssPtpConfigCmldsPortDsPortId                              Unsigned32,
    vtssPtpConfigCmldsPortDsDelayAsymmetry                      VTSSInteger64,
    vtssPtpConfigCmldsPortDsInitialLogPdelayReqInterval         VTSSInteger8,
    vtssPtpConfigCmldsPortDsUseMgtSettableLogPdelayReqInterval  TruthValue,
    vtssPtpConfigCmldsPortDsMgtSettableLogPdelayReqInterval     VTSSInteger8,
    vtssPtpConfigCmldsPortDsInitialCompNbrRateRatio             TruthValue,
    vtssPtpConfigCmldsPortDsUseMgtSetCompNbrRateRatio           TruthValue,
    vtssPtpConfigCmldsPortDsMgtSetCompNbrRateRatio              TruthValue,
    vtssPtpConfigCmldsPortDsInitialCompMeanLinkDelay            TruthValue,
    vtssPtpConfigCmldsPortDsUseMgtSetCompMeanLinkDelay          TruthValue,
    vtssPtpConfigCmldsPortDsMgtSetCompMeanLinkDelay             TruthValue,
    vtssPtpConfigCmldsPortDsAllowedLostResponses                VTSSUnsigned8,
    vtssPtpConfigCmldsPortDsAllowedFaults                       VTSSUnsigned8,
    vtssPtpConfigCmldsPortDsMeanLinkDelayThresh                 VTSSInteger64
}

vtssPtpConfigCmldsPortDsPortId OBJECT-TYPE
    SYNTAX      Unsigned32 (0..255)
    MAX-ACCESS  accessible-for-notify
    STATUS      current
    DESCRIPTION
        "-"
    ::= { vtssPtpConfigCmldsPortDsEntry 1 }

vtssPtpConfigCmldsPortDsDelayAsymmetry OBJECT-TYPE
    SYNTAX      VTSSInteger64
    MAX-ACCESS  read-write
    STATUS      current
    DESCRIPTION
        "the asymmetry in the propagation delay on the link attached to this
         port relative to the grandmaster time base, as defined in 8.3. If
         propagation delay asymmetry is not modeled, then delayAsymmetry is
         zero."
    ::= { vtssPtpConfigCmldsPortDsEntry 2 }

vtssPtpConfigCmldsPortDsInitialLogPdelayReqInterval OBJECT-TYPE
    SYNTAX      VTSSInteger8
    MAX-ACCESS  read-write
    STATUS      current
    DESCRIPTION
        "the value is the logarithm to base 2 of the Pdelay_Req message
         transmission interval used when the Link Port is initialized, or a
         message interval request TLV is received with the linkDelayInterval
         field set to 126"
    ::= { vtssPtpConfigCmldsPortDsEntry 3 }

vtssPtpConfigCmldsPortDsUseMgtSettableLogPdelayReqInterval OBJECT-TYPE
    SYNTAX      TruthValue
    MAX-ACCESS  read-write
    STATUS      current
    DESCRIPTION
        "This value determines the source of the sync interval and mean time
         interval between successive Pdelay_Req messages. TRUE indicates source
         as mgtSettableLogPdelayReqInterval. FALSE indicates source as
         LinkDelayIntervalSetting state machine "
    ::= { vtssPtpConfigCmldsPortDsEntry 4 }

vtssPtpConfigCmldsPortDsMgtSettableLogPdelayReqInterval OBJECT-TYPE
    SYNTAX      VTSSInteger8
    MAX-ACCESS  read-write
    STATUS      current
    DESCRIPTION
        "This value is the logarithm to base 2 of the mean time interval between
         successive Pdelay_Req messages if useMgtSettableLogPdelayReqInterval is
         TRUE."
    ::= { vtssPtpConfigCmldsPortDsEntry 5 }

vtssPtpConfigCmldsPortDsInitialCompNbrRateRatio OBJECT-TYPE
    SYNTAX      TruthValue
    MAX-ACCESS  read-write
    STATUS      current
    DESCRIPTION
        "Initial value that indicates whether neighborRateRatio is to be
         computed by this port."
    ::= { vtssPtpConfigCmldsPortDsEntry 6 }

vtssPtpConfigCmldsPortDsUseMgtSetCompNbrRateRatio OBJECT-TYPE
    SYNTAX      TruthValue
    MAX-ACCESS  read-write
    STATUS      current
    DESCRIPTION
        "This value determines the source of the value of
         computeNeighborRateRatio. 'True' indicates source as
         'mgtSettablecomputeNeighborRateRatio'. 'false' indicates source as
         'LinkDelayIntervalSetting state machine'."
    ::= { vtssPtpConfigCmldsPortDsEntry 7 }

vtssPtpConfigCmldsPortDsMgtSetCompNbrRateRatio OBJECT-TYPE
    SYNTAX      TruthValue
    MAX-ACCESS  read-write
    STATUS      current
    DESCRIPTION
        "This value indicates the input through management interface whether to
         compute neighbor rate ratio or not."
    ::= { vtssPtpConfigCmldsPortDsEntry 8 }

vtssPtpConfigCmldsPortDsInitialCompMeanLinkDelay OBJECT-TYPE
    SYNTAX      TruthValue
    MAX-ACCESS  read-write
    STATUS      current
    DESCRIPTION
        "Initial value that indicates whether mean Link delay is computed by
         this port or not."
    ::= { vtssPtpConfigCmldsPortDsEntry 9 }

vtssPtpConfigCmldsPortDsUseMgtSetCompMeanLinkDelay OBJECT-TYPE
    SYNTAX      TruthValue
    MAX-ACCESS  read-write
    STATUS      current
    DESCRIPTION
        "This value determines the source of the value of computeMeanLinkDelay.
         'True' indicates source as 'mgtSettableComputeMeanLinkDelay'. 'false'
         indicates source as 'LinkDelayIntervalSetting state machine'."
    ::= { vtssPtpConfigCmldsPortDsEntry 10 }

vtssPtpConfigCmldsPortDsMgtSetCompMeanLinkDelay OBJECT-TYPE
    SYNTAX      TruthValue
    MAX-ACCESS  read-write
    STATUS      current
    DESCRIPTION
        "This value indicates the input through management interface whether to
         compute Mean Link Delay or not."
    ::= { vtssPtpConfigCmldsPortDsEntry 11 }

vtssPtpConfigCmldsPortDsAllowedLostResponses OBJECT-TYPE
    SYNTAX      VTSSUnsigned8 (0..10)
    MAX-ACCESS  read-write
    STATUS      current
    DESCRIPTION
        "It is the number of Pdelay_Req messages for which a valid response is
         not received, above which a Link Port is considered to not be
         exchanging peer delay messages with its neighbor."
    ::= { vtssPtpConfigCmldsPortDsEntry 12 }

vtssPtpConfigCmldsPortDsAllowedFaults OBJECT-TYPE
    SYNTAX      VTSSUnsigned8 (1..255)
    MAX-ACCESS  read-write
    STATUS      current
    DESCRIPTION
        "It is the number of faults, above which asCapableAcrossDomains is set
         to FALSE."
    ::= { vtssPtpConfigCmldsPortDsEntry 13 }

vtssPtpConfigCmldsPortDsMeanLinkDelayThresh OBJECT-TYPE
    SYNTAX      VTSSInteger64
    MAX-ACCESS  read-write
    STATUS      current
    DESCRIPTION
        "The propagation time threshold, above which a port is not considered
         capable of participating in the IEEE 802.1AS protocol."
    ::= { vtssPtpConfigCmldsPortDsEntry 14 }

vtssPtpStatus OBJECT IDENTIFIER
    ::= { vtssPtpMibObjects 3 }

vtssPtpStatusClocks OBJECT IDENTIFIER
    ::= { vtssPtpStatus 1 }

vtssPtpStatusClocksDefaultDsTable OBJECT-TYPE
    SYNTAX      SEQUENCE OF VTSSPtpStatusClocksDefaultDsEntry
    MAX-ACCESS  not-accessible
    STATUS      current
    DESCRIPTION
        "This is the dynamic (status) part of the PTP clocks DefaultDS."
    ::= { vtssPtpStatusClocks 1 }

vtssPtpStatusClocksDefaultDsEntry OBJECT-TYPE
    SYNTAX      VTSSPtpStatusClocksDefaultDsEntry
    MAX-ACCESS  not-accessible
    STATUS      current
    DESCRIPTION
        "The clockId index must be a value must be a value from 0 up to the
         number of PTP clocks minus one."
    INDEX       { vtssPtpStatusClocksDefaultDsClockId }
    ::= { vtssPtpStatusClocksDefaultDsTable 1 }

VTSSPtpStatusClocksDefaultDsEntry ::= SEQUENCE {
    vtssPtpStatusClocksDefaultDsClockId                         Integer32,
    vtssPtpStatusClocksDefaultDsClockIdentity                   OCTET STRING,
    vtssPtpStatusClocksDefaultDsClockQualityClockClass          VTSSUnsigned8,
    vtssPtpStatusClocksDefaultDsClockQualityClockAccuracy       VTSSUnsigned8,
    vtssPtpStatusClocksDefaultDsClockQualityOffsetScaledLogVar  VTSSUnsigned16,
    vtssPtpStatusClocksDefaultDsS8021asGmCapable                TruthValue,
    vtssPtpStatusClocksDefaultDsS8021asSdoId                    VTSSUnsigned16
}

vtssPtpStatusClocksDefaultDsClockId OBJECT-TYPE
    SYNTAX      Integer32 (0..32767)
    MAX-ACCESS  accessible-for-notify
    STATUS      current
    DESCRIPTION
        "-"
    ::= { vtssPtpStatusClocksDefaultDsEntry 1 }

vtssPtpStatusClocksDefaultDsClockIdentity OBJECT-TYPE
    SYNTAX      OCTET STRING (SIZE(8))
    MAX-ACCESS  read-only
    STATUS      current
    DESCRIPTION
        "This is the unique 8 byte clockIdentify field from the DefaultDS
         structure."
    ::= { vtssPtpStatusClocksDefaultDsEntry 2 }

vtssPtpStatusClocksDefaultDsClockQualityClockClass OBJECT-TYPE
    SYNTAX      VTSSUnsigned8
    MAX-ACCESS  read-only
    STATUS      current
    DESCRIPTION
        "This is the clock class field of the clock quality structure.
         
         IEEE-1588-2008 value representation : 6 (GM locked to 1pps output), 7
         (GM in holdover after 1pps output), 135 (Boundary clock in holdover),
         165 (Boundary clock out of holdover), 140 (GM out of holdover CAT 1),
         150 (GM out of holdover CAT 2), 160 (GM out of holdover CAT 3), 248
         (Default), 255 (Time slave clock)."
    ::= { vtssPtpStatusClocksDefaultDsEntry 3 }

vtssPtpStatusClocksDefaultDsClockQualityClockAccuracy OBJECT-TYPE
    SYNTAX      VTSSUnsigned8
    MAX-ACCESS  read-only
    STATUS      current
    DESCRIPTION
        "This is the clock accuracy field of the clock quality structure.
         
         Value representation : 32 (25 ns), 33 (100 ns), 34 (250 ns), 35 (1 us),
         36 (2.5 us) 37 (10 us), 38 (25 us), 39 (100 us), 40 (250 ns), 41 (1
         ms), 42 (2.5 ms), 43 (10 ms)44 (25 ms), 45 (100 ms), 46 (250 ms), 47 (1
         s), 48 (10 s), 49 (> 10 s), 254 (unknown)."
    ::= { vtssPtpStatusClocksDefaultDsEntry 4 }

vtssPtpStatusClocksDefaultDsClockQualityOffsetScaledLogVar OBJECT-TYPE
    SYNTAX      VTSSUnsigned16
    MAX-ACCESS  read-only
    STATUS      current
    DESCRIPTION
        "This is the offsetScaledLogVariance field of the clock quality
         structure."
    ::= { vtssPtpStatusClocksDefaultDsEntry 5 }

vtssPtpStatusClocksDefaultDsS8021asGmCapable OBJECT-TYPE
    SYNTAX      TruthValue
    MAX-ACCESS  read-only
    STATUS      current
    DESCRIPTION
        "Defines IEEE 802.1AS specific default_DS status parameters, TRUE if the
         time-aware system is capable of being a Grandmaster."
    ::= { vtssPtpStatusClocksDefaultDsEntry 6 }

vtssPtpStatusClocksDefaultDsS8021asSdoId OBJECT-TYPE
    SYNTAX      VTSSUnsigned16
    MAX-ACCESS  read-only
    STATUS      current
    DESCRIPTION
        "Defines IEEE 802.1AS specific default_DS status parameters, part of ptp
         domain identifier."
    ::= { vtssPtpStatusClocksDefaultDsEntry 7 }

vtssPtpStatusClocksCurrentDsTable OBJECT-TYPE
    SYNTAX      SEQUENCE OF VTSSPtpStatusClocksCurrentDsEntry
    MAX-ACCESS  not-accessible
    STATUS      current
    DESCRIPTION
        "This is the dynamic (status) part of the PTP clocks CurrentDS."
    ::= { vtssPtpStatusClocks 2 }

vtssPtpStatusClocksCurrentDsEntry OBJECT-TYPE
    SYNTAX      VTSSPtpStatusClocksCurrentDsEntry
    MAX-ACCESS  not-accessible
    STATUS      current
    DESCRIPTION
        "The clockId index must be a value must be a value from 0 up to the
         number of PTP clocks minus one."
    INDEX       { vtssPtpStatusClocksCurrentDsClockId }
    ::= { vtssPtpStatusClocksCurrentDsTable 1 }

VTSSPtpStatusClocksCurrentDsEntry ::= SEQUENCE {
    vtssPtpStatusClocksCurrentDsClockId                               Integer32,
    vtssPtpStatusClocksCurrentDsStepsRemoved                          VTSSUnsigned16,
    vtssPtpStatusClocksCurrentDsOffsetFromMaster                      VTSSInteger64,
    vtssPtpStatusClocksCurrentDsMeanPathDelay                         VTSSInteger64,
    vtssPtpStatusClocksCurrentDsCur8021asLastGMPhaseChangeLow         VTSSUnsigned64,
    vtssPtpStatusClocksCurrentDsCur8021asLastGMPhaseChangeHigh        Integer32,
    vtssPtpStatusClocksCurrentDsCur8021asLastGMFreqChange             VTSSInteger32e-9,
    vtssPtpStatusClocksCurrentDsCur8021asGmTimeBaseIndicator          VTSSUnsigned16,
    vtssPtpStatusClocksCurrentDsCur8021asGmChangeCount                Unsigned32,
    vtssPtpStatusClocksCurrentDsCur8021asTimeOfLastGMChangeEvt        Unsigned32,
    vtssPtpStatusClocksCurrentDsCur8021asTimeOfLastGMPhaseChangeEvt   Unsigned32,
    vtssPtpStatusClocksCurrentDsCur8021asTimeOfLastGMFreqChangeEvent  Unsigned32
}

vtssPtpStatusClocksCurrentDsClockId OBJECT-TYPE
    SYNTAX      Integer32 (0..32767)
    MAX-ACCESS  accessible-for-notify
    STATUS      current
    DESCRIPTION
        "-"
    ::= { vtssPtpStatusClocksCurrentDsEntry 1 }

vtssPtpStatusClocksCurrentDsStepsRemoved OBJECT-TYPE
    SYNTAX      VTSSUnsigned16
    MAX-ACCESS  read-only
    STATUS      current
    DESCRIPTION
        "The number of PTP clocks traversed from the grandmaster to the local
         PTP clock."
    ::= { vtssPtpStatusClocksCurrentDsEntry 2 }

vtssPtpStatusClocksCurrentDsOffsetFromMaster OBJECT-TYPE
    SYNTAX      VTSSInteger64
    MAX-ACCESS  read-only
    STATUS      current
    DESCRIPTION
        "The time difference in ns from the grandmaster to the local PTP clock."
    ::= { vtssPtpStatusClocksCurrentDsEntry 3 }

vtssPtpStatusClocksCurrentDsMeanPathDelay OBJECT-TYPE
    SYNTAX      VTSSInteger64
    MAX-ACCESS  read-only
    STATUS      current
    DESCRIPTION
        "The mean path delay from the master to the local slave."
    ::= { vtssPtpStatusClocksCurrentDsEntry 4 }

vtssPtpStatusClocksCurrentDsCur8021asLastGMPhaseChangeLow OBJECT-TYPE
    SYNTAX      VTSSUnsigned64
    MAX-ACCESS  read-only
    STATUS      current
    DESCRIPTION
        "The system time when the most recent change in grandmaster phase
         occurred due to a change of either the grandmaster or grandmaster time
         base 64 ls bits."
    ::= { vtssPtpStatusClocksCurrentDsEntry 5 }

vtssPtpStatusClocksCurrentDsCur8021asLastGMPhaseChangeHigh OBJECT-TYPE
    SYNTAX      Integer32
    MAX-ACCESS  read-only
    STATUS      current
    DESCRIPTION
        "The system time when the most recent change in grandmaster phase
         occurred due to a change of either the grandmaster or grandmaster time
         base in 32 ms bits"
    ::= { vtssPtpStatusClocksCurrentDsEntry 6 }

vtssPtpStatusClocksCurrentDsCur8021asLastGMFreqChange OBJECT-TYPE
    SYNTAX      VTSSInteger32e-9
    MAX-ACCESS  read-only
    STATUS      current
    DESCRIPTION
        "TRUE if the time-aware system is capable of being a Grandmaster."
    ::= { vtssPtpStatusClocksCurrentDsEntry 7 }

vtssPtpStatusClocksCurrentDsCur8021asGmTimeBaseIndicator OBJECT-TYPE
    SYNTAX      VTSSUnsigned16
    MAX-ACCESS  read-only
    STATUS      current
    DESCRIPTION
        "TimeBaseIndicator of the current grandmaster."
    ::= { vtssPtpStatusClocksCurrentDsEntry 8 }

vtssPtpStatusClocksCurrentDsCur8021asGmChangeCount OBJECT-TYPE
    SYNTAX      Unsigned32
    MAX-ACCESS  read-only
    STATUS      current
    DESCRIPTION
        "The number of times the grandmaster has changed in a gPTP domain."
    ::= { vtssPtpStatusClocksCurrentDsEntry 9 }

vtssPtpStatusClocksCurrentDsCur8021asTimeOfLastGMChangeEvt OBJECT-TYPE
    SYNTAX      Unsigned32
    MAX-ACCESS  read-only
    STATUS      current
    DESCRIPTION
        "The system time when the most recent grandmaster change occurred."
    ::= { vtssPtpStatusClocksCurrentDsEntry 10 }

vtssPtpStatusClocksCurrentDsCur8021asTimeOfLastGMPhaseChangeEvt OBJECT-TYPE
    SYNTAX      Unsigned32
    MAX-ACCESS  read-only
    STATUS      current
    DESCRIPTION
        "The system time when the most recent change in grandmaster phase
         occurred due to a change of either the grandmaster or grandmaster time
         base."
    ::= { vtssPtpStatusClocksCurrentDsEntry 11 }

vtssPtpStatusClocksCurrentDsCur8021asTimeOfLastGMFreqChangeEvent OBJECT-TYPE
    SYNTAX      Unsigned32
    MAX-ACCESS  read-only
    STATUS      current
    DESCRIPTION
        "The system time when the most recent change in grandmaster frequency
         occurred due to a change of either the grandmaster or grandmaster time
         base."
    ::= { vtssPtpStatusClocksCurrentDsEntry 12 }

vtssPtpStatusClocksParentDsTable OBJECT-TYPE
    SYNTAX      SEQUENCE OF VTSSPtpStatusClocksParentDsEntry
    MAX-ACCESS  not-accessible
    STATUS      current
    DESCRIPTION
        "This is the dynamic (status) part of the PTP clocks ParentDS."
    ::= { vtssPtpStatusClocks 3 }

vtssPtpStatusClocksParentDsEntry OBJECT-TYPE
    SYNTAX      VTSSPtpStatusClocksParentDsEntry
    MAX-ACCESS  not-accessible
    STATUS      current
    DESCRIPTION
        "The clockId index must be a value must be a value from 0 up to the
         number of PTP clocks minus one."
    INDEX       { vtssPtpStatusClocksParentDsClockId }
    ::= { vtssPtpStatusClocksParentDsTable 1 }

VTSSPtpStatusClocksParentDsEntry ::= SEQUENCE {
    vtssPtpStatusClocksParentDsClockId                             Integer32,
    vtssPtpStatusClocksParentDsParentPortIdentityClockIdentity     OCTET STRING,
    vtssPtpStatusClocksParentDsParentPortIdentityPortNumber        VTSSUnsigned16,
    vtssPtpStatusClocksParentDsParentStats                         TruthValue,
    vtssPtpStatusClocksParentDsObservedParentOffsetScaledLogVar    VTSSUnsigned16,
    vtssPtpStatusClocksParentDsObservedParentClockPhaseChangeRate  Integer32,
    vtssPtpStatusClocksParentDsGrmstrIdentity                      OCTET STRING,
    vtssPtpStatusClocksParentDsGrmstrClkQualClockClass             VTSSUnsigned8,
    vtssPtpStatusClocksParentDsGmstrClkQualClockAccuracy           VTSSUnsigned8,
    vtssPtpStatusClocksParentDsGmstrClkQualOffsetScaledLogVar      VTSSUnsigned16,
    vtssPtpStatusClocksParentDsGmstrPriority1                      VTSSUnsigned8,
    vtssPtpStatusClocksParentDsGmstrPriority2                      VTSSUnsigned8,
    vtssPtpStatusClocksParentDsPar8021asCumulativeRateRatio        Integer32
}

vtssPtpStatusClocksParentDsClockId OBJECT-TYPE
    SYNTAX      Integer32 (0..32767)
    MAX-ACCESS  accessible-for-notify
    STATUS      current
    DESCRIPTION
        "-"
    ::= { vtssPtpStatusClocksParentDsEntry 1 }

vtssPtpStatusClocksParentDsParentPortIdentityClockIdentity OBJECT-TYPE
    SYNTAX      OCTET STRING (SIZE(8))
    MAX-ACCESS  read-only
    STATUS      current
    DESCRIPTION
        "This is the 8 byte unique clock identity of the parent port."
    ::= { vtssPtpStatusClocksParentDsEntry 2 }

vtssPtpStatusClocksParentDsParentPortIdentityPortNumber OBJECT-TYPE
    SYNTAX      VTSSUnsigned16
    MAX-ACCESS  read-only
    STATUS      current
    DESCRIPTION
        "This is the port number on the parent associated with the parent clock."
    ::= { vtssPtpStatusClocksParentDsEntry 3 }

vtssPtpStatusClocksParentDsParentStats OBJECT-TYPE
    SYNTAX      TruthValue
    MAX-ACCESS  read-only
    STATUS      current
    DESCRIPTION
        "Parents stats (always false)."
    ::= { vtssPtpStatusClocksParentDsEntry 4 }

vtssPtpStatusClocksParentDsObservedParentOffsetScaledLogVar OBJECT-TYPE
    SYNTAX      VTSSUnsigned16
    MAX-ACCESS  read-only
    STATUS      current
    DESCRIPTION
        "This field is optional and is not computed (as signaled by parentStats
         being false)."
    ::= { vtssPtpStatusClocksParentDsEntry 5 }

vtssPtpStatusClocksParentDsObservedParentClockPhaseChangeRate OBJECT-TYPE
    SYNTAX      Integer32
    MAX-ACCESS  read-only
    STATUS      current
    DESCRIPTION
        "This field is optional and is not computed (as signaled by parentStats
         being false)."
    ::= { vtssPtpStatusClocksParentDsEntry 6 }

vtssPtpStatusClocksParentDsGrmstrIdentity OBJECT-TYPE
    SYNTAX      OCTET STRING (SIZE(8))
    MAX-ACCESS  read-only
    STATUS      current
    DESCRIPTION
        "This is the 8 byte unique clock identity of the grand master clock."
    ::= { vtssPtpStatusClocksParentDsEntry 7 }

vtssPtpStatusClocksParentDsGrmstrClkQualClockClass OBJECT-TYPE
    SYNTAX      VTSSUnsigned8
    MAX-ACCESS  read-only
    STATUS      current
    DESCRIPTION
        "This is the clock class of the clock quality structure of the grand
         master clock.
         
         IEEE-1588-2008 value representation : 6 (GM locked to 1pps output), 7
         (GM in holdover after 1pps output), 135 (Boundary clock in holdover),
         165 (Boundary clock out of holdover), 140 (GM out of holdover CAT 1),
         150 (GM out of holdover CAT 2), 160 (GM out of holdover CAT 3), 248
         (Default), 255 (Time slave clock)."
    ::= { vtssPtpStatusClocksParentDsEntry 8 }

vtssPtpStatusClocksParentDsGmstrClkQualClockAccuracy OBJECT-TYPE
    SYNTAX      VTSSUnsigned8
    MAX-ACCESS  read-only
    STATUS      current
    DESCRIPTION
        "This is the clock accuracy of the clock quality structure of the grand
         master clock.
         
         Value representation : 32 (25 ns), 33 (100 ns), 34 (250 ns), 35 (1 us),
         36 (2.5 us) 37 (10 us), 38 (25 us), 39 (100 us), 40 (250 ns), 41 (1
         ms), 42 (2.5 ms), 43 (10 ms) 44 (25 ms), 45 (100 ms), 46 (250 ms), 47
         (1 s), 48 (10 s), 49 (> 10 s), 254 (unknown)."
    ::= { vtssPtpStatusClocksParentDsEntry 9 }

vtssPtpStatusClocksParentDsGmstrClkQualOffsetScaledLogVar OBJECT-TYPE
    SYNTAX      VTSSUnsigned16
    MAX-ACCESS  read-only
    STATUS      current
    DESCRIPTION
        "This is the offsetScaledLogVariance field of the clock quality
         structure of the grand master clock."
    ::= { vtssPtpStatusClocksParentDsEntry 10 }

vtssPtpStatusClocksParentDsGmstrPriority1 OBJECT-TYPE
    SYNTAX      VTSSUnsigned8
    MAX-ACCESS  read-only
    STATUS      current
    DESCRIPTION
        "Grandmaster Priority1 value."
    ::= { vtssPtpStatusClocksParentDsEntry 11 }

vtssPtpStatusClocksParentDsGmstrPriority2 OBJECT-TYPE
    SYNTAX      VTSSUnsigned8
    MAX-ACCESS  read-only
    STATUS      current
    DESCRIPTION
        "Grandmaster Priority2 value."
    ::= { vtssPtpStatusClocksParentDsEntry 12 }

vtssPtpStatusClocksParentDsPar8021asCumulativeRateRatio OBJECT-TYPE
    SYNTAX      Integer32
    MAX-ACCESS  read-only
    STATUS      current
    DESCRIPTION
        "The ratio of the frequency og the grandmaster to the frequencu of the
         Local CLock entity, expressed as fractional frequency offset * 2**41 ."
    ::= { vtssPtpStatusClocksParentDsEntry 13 }

vtssPtpStatusClocksTimePropertiesDsTable OBJECT-TYPE
    SYNTAX      SEQUENCE OF VTSSPtpStatusClocksTimePropertiesDsEntry
    MAX-ACCESS  not-accessible
    STATUS      current
    DESCRIPTION
        "This is the dynamic (status) part of the PTP clocks TimePropertiesDS."
    ::= { vtssPtpStatusClocks 4 }

vtssPtpStatusClocksTimePropertiesDsEntry OBJECT-TYPE
    SYNTAX      VTSSPtpStatusClocksTimePropertiesDsEntry
    MAX-ACCESS  not-accessible
    STATUS      current
    DESCRIPTION
        "The clockId index must be a value must be a value from 0 up to the
         number of PTP clocks minus one."
    INDEX       { vtssPtpStatusClocksTimePropertiesDsClockId }
    ::= { vtssPtpStatusClocksTimePropertiesDsTable 1 }

VTSSPtpStatusClocksTimePropertiesDsEntry ::= SEQUENCE {
    vtssPtpStatusClocksTimePropertiesDsClockId                Integer32,
    vtssPtpStatusClocksTimePropertiesDsCurrentUtcOffset       VTSSInteger16,
    vtssPtpStatusClocksTimePropertiesDsCurrentUtcOffsetValid  TruthValue,
    vtssPtpStatusClocksTimePropertiesDsLeap59                 TruthValue,
    vtssPtpStatusClocksTimePropertiesDsLeap61                 TruthValue,
    vtssPtpStatusClocksTimePropertiesDsTimeTraceable          TruthValue,
    vtssPtpStatusClocksTimePropertiesDsFrequencyTraceable     TruthValue,
    vtssPtpStatusClocksTimePropertiesDsPtpTimescale           TruthValue,
    vtssPtpStatusClocksTimePropertiesDsTimeSource             VTSSUnsigned8,
    vtssPtpStatusClocksTimePropertiesDsPendingLeap            TruthValue,
    vtssPtpStatusClocksTimePropertiesDsLeapDate               VTSSUnsigned16,
    vtssPtpStatusClocksTimePropertiesDsLeapType               VTSSptpLeapSecondType
}

vtssPtpStatusClocksTimePropertiesDsClockId OBJECT-TYPE
    SYNTAX      Integer32 (0..32767)
    MAX-ACCESS  accessible-for-notify
    STATUS      current
    DESCRIPTION
        "-"
    ::= { vtssPtpStatusClocksTimePropertiesDsEntry 1 }

vtssPtpStatusClocksTimePropertiesDsCurrentUtcOffset OBJECT-TYPE
    SYNTAX      VTSSInteger16
    MAX-ACCESS  read-only
    STATUS      current
    DESCRIPTION
        "The current UTC time offset. Range 0 to 10000."
    ::= { vtssPtpStatusClocksTimePropertiesDsEntry 2 }

vtssPtpStatusClocksTimePropertiesDsCurrentUtcOffsetValid OBJECT-TYPE
    SYNTAX      TruthValue
    MAX-ACCESS  read-only
    STATUS      current
    DESCRIPTION
        "Indicates whether the current UTC time offset value is valid."
    ::= { vtssPtpStatusClocksTimePropertiesDsEntry 3 }

vtssPtpStatusClocksTimePropertiesDsLeap59 OBJECT-TYPE
    SYNTAX      TruthValue
    MAX-ACCESS  read-only
    STATUS      current
    DESCRIPTION
        "Indicates that the last minute of the day has only 59 seconds."
    ::= { vtssPtpStatusClocksTimePropertiesDsEntry 4 }

vtssPtpStatusClocksTimePropertiesDsLeap61 OBJECT-TYPE
    SYNTAX      TruthValue
    MAX-ACCESS  read-only
    STATUS      current
    DESCRIPTION
        "Indicates that the last minute of the day has 61 seconds."
    ::= { vtssPtpStatusClocksTimePropertiesDsEntry 5 }

vtssPtpStatusClocksTimePropertiesDsTimeTraceable OBJECT-TYPE
    SYNTAX      TruthValue
    MAX-ACCESS  read-only
    STATUS      current
    DESCRIPTION
        "Indicates that time is traceable to a primary reference."
    ::= { vtssPtpStatusClocksTimePropertiesDsEntry 6 }

vtssPtpStatusClocksTimePropertiesDsFrequencyTraceable OBJECT-TYPE
    SYNTAX      TruthValue
    MAX-ACCESS  read-only
    STATUS      current
    DESCRIPTION
        "Indicates that frequency is traceable to a primary reference."
    ::= { vtssPtpStatusClocksTimePropertiesDsEntry 7 }

vtssPtpStatusClocksTimePropertiesDsPtpTimescale OBJECT-TYPE
    SYNTAX      TruthValue
    MAX-ACCESS  read-only
    STATUS      current
    DESCRIPTION
        "Indicates whether timescale of the grandmaster clock is PTP."
    ::= { vtssPtpStatusClocksTimePropertiesDsEntry 8 }

vtssPtpStatusClocksTimePropertiesDsTimeSource OBJECT-TYPE
    SYNTAX      VTSSUnsigned8
    MAX-ACCESS  read-only
    STATUS      current
    DESCRIPTION
        "Source of time used by the grandmaster clock.
         
         Value representation : 16 (Atomic clock), 32 (GPS), 48 (Terrestrial
         radio), 64 (PTP), 80 (NTP), 96 (Hand set), 144 (Other), 160 (Internal
         oscillator)."
    ::= { vtssPtpStatusClocksTimePropertiesDsEntry 9 }

vtssPtpStatusClocksTimePropertiesDsPendingLeap OBJECT-TYPE
    SYNTAX      TruthValue
    MAX-ACCESS  read-only
    STATUS      current
    DESCRIPTION
        "Indicates whether a leap event is pending."
    ::= { vtssPtpStatusClocksTimePropertiesDsEntry 10 }

vtssPtpStatusClocksTimePropertiesDsLeapDate OBJECT-TYPE
    SYNTAX      VTSSUnsigned16
    MAX-ACCESS  read-only
    STATUS      current
    DESCRIPTION
        "Date of leap event represented as number of days after 1970/01/01"
    ::= { vtssPtpStatusClocksTimePropertiesDsEntry 11 }

vtssPtpStatusClocksTimePropertiesDsLeapType OBJECT-TYPE
    SYNTAX      VTSSptpLeapSecondType
    MAX-ACCESS  read-only
    STATUS      current
    DESCRIPTION
        "Type of leap event i.e. leap59 or leap61."
    ::= { vtssPtpStatusClocksTimePropertiesDsEntry 12 }

vtssPtpStatusClocksSlaveDsTable OBJECT-TYPE
    SYNTAX      SEQUENCE OF VTSSPtpStatusClocksSlaveDsEntry
    MAX-ACCESS  not-accessible
    STATUS      current
    DESCRIPTION
        "This is the dynamic (status) part of the PTP clocks SlaveDS."
    ::= { vtssPtpStatusClocks 5 }

vtssPtpStatusClocksSlaveDsEntry OBJECT-TYPE
    SYNTAX      VTSSPtpStatusClocksSlaveDsEntry
    MAX-ACCESS  not-accessible
    STATUS      current
    DESCRIPTION
        "The clockId index must be a value must be a value from 0 up to the
         number of PTP clocks minus one."
    INDEX       { vtssPtpStatusClocksSlaveDsClockId }
    ::= { vtssPtpStatusClocksSlaveDsTable 1 }

VTSSPtpStatusClocksSlaveDsEntry ::= SEQUENCE {
    vtssPtpStatusClocksSlaveDsClockId         Integer32,
    vtssPtpStatusClocksSlaveDsSlavePort       VTSSUnsigned16,
    vtssPtpStatusClocksSlaveDsSlaveState      VTSSptpSlaveClockState,
    vtssPtpStatusClocksSlaveDsHoldoverStable  TruthValue,
    vtssPtpStatusClocksSlaveDsHoldoverAdj     VTSSInteger64
}

vtssPtpStatusClocksSlaveDsClockId OBJECT-TYPE
    SYNTAX      Integer32 (0..32767)
    MAX-ACCESS  accessible-for-notify
    STATUS      current
    DESCRIPTION
        "-"
    ::= { vtssPtpStatusClocksSlaveDsEntry 1 }

vtssPtpStatusClocksSlaveDsSlavePort OBJECT-TYPE
    SYNTAX      VTSSUnsigned16
    MAX-ACCESS  read-only
    STATUS      current
    DESCRIPTION
        "0 => no slave port, 1..n => selected slave port."
    ::= { vtssPtpStatusClocksSlaveDsEntry 2 }

vtssPtpStatusClocksSlaveDsSlaveState OBJECT-TYPE
    SYNTAX      VTSSptpSlaveClockState
    MAX-ACCESS  read-only
    STATUS      current
    DESCRIPTION
        "The slaves state. Valid options : freerun, freqLocking, freqLocked,
         phaseLocking, phaseLocked, holdover, invalid."
    ::= { vtssPtpStatusClocksSlaveDsEntry 3 }

vtssPtpStatusClocksSlaveDsHoldoverStable OBJECT-TYPE
    SYNTAX      TruthValue
    MAX-ACCESS  read-only
    STATUS      current
    DESCRIPTION
        "True if the stabilization period has expired."
    ::= { vtssPtpStatusClocksSlaveDsEntry 4 }

vtssPtpStatusClocksSlaveDsHoldoverAdj OBJECT-TYPE
    SYNTAX      VTSSInteger64
    MAX-ACCESS  read-only
    STATUS      current
    DESCRIPTION
        "The calculated holdover offset (ppb*10)."
    ::= { vtssPtpStatusClocksSlaveDsEntry 5 }

vtssPtpStatusClocksUnicastMasterTable OBJECT-TYPE
    SYNTAX      SEQUENCE OF VTSSPtpStatusClocksUnicastMasterEntry
    MAX-ACCESS  not-accessible
    STATUS      current
    DESCRIPTION
        "This is the dynamic (status) part of the PTP clocks unicast master
         table."
    ::= { vtssPtpStatusClocks 6 }

vtssPtpStatusClocksUnicastMasterEntry OBJECT-TYPE
    SYNTAX      VTSSPtpStatusClocksUnicastMasterEntry
    MAX-ACCESS  not-accessible
    STATUS      current
    DESCRIPTION
        "The clockId index must be a value must be a value from 0 up to the
         number of PTP clocks minus one."
    INDEX       { vtssPtpStatusClocksUnicastMasterClockId,
                  vtssPtpStatusClocksUnicastMasterSlaveIp }
    ::= { vtssPtpStatusClocksUnicastMasterTable 1 }

VTSSPtpStatusClocksUnicastMasterEntry ::= SEQUENCE {
    vtssPtpStatusClocksUnicastMasterClockId          Integer32,
    vtssPtpStatusClocksUnicastMasterSlaveIp          IpAddress,
    vtssPtpStatusClocksUnicastMasterSlaveMac         MacAddress,
    vtssPtpStatusClocksUnicastMasterPort             VTSSUnsigned16,
    vtssPtpStatusClocksUnicastMasterAnnLogMsgPeriod  VTSSInteger16,
    vtssPtpStatusClocksUnicastMasterAnn              TruthValue,
    vtssPtpStatusClocksUnicastMasterLogMsgPeriod     VTSSInteger16,
    vtssPtpStatusClocksUnicastMasterSync             TruthValue
}

vtssPtpStatusClocksUnicastMasterClockId OBJECT-TYPE
    SYNTAX      Integer32 (0..32767)
    MAX-ACCESS  accessible-for-notify
    STATUS      current
    DESCRIPTION
        "-"
    ::= { vtssPtpStatusClocksUnicastMasterEntry 1 }

vtssPtpStatusClocksUnicastMasterSlaveIp OBJECT-TYPE
    SYNTAX      IpAddress
    MAX-ACCESS  accessible-for-notify
    STATUS      current
    DESCRIPTION
        "-"
    ::= { vtssPtpStatusClocksUnicastMasterEntry 2 }

vtssPtpStatusClocksUnicastMasterSlaveMac OBJECT-TYPE
    SYNTAX      MacAddress
    MAX-ACCESS  read-only
    STATUS      current
    DESCRIPTION
        "MAC address of the slave."
    ::= { vtssPtpStatusClocksUnicastMasterEntry 3 }

vtssPtpStatusClocksUnicastMasterPort OBJECT-TYPE
    SYNTAX      VTSSUnsigned16
    MAX-ACCESS  read-only
    STATUS      current
    DESCRIPTION
        "Port on the master that slave is connected to."
    ::= { vtssPtpStatusClocksUnicastMasterEntry 4 }

vtssPtpStatusClocksUnicastMasterAnnLogMsgPeriod OBJECT-TYPE
    SYNTAX      VTSSInteger16
    MAX-ACCESS  read-only
    STATUS      current
    DESCRIPTION
        "The granted Announce interval. Range -3 to 4."
    ::= { vtssPtpStatusClocksUnicastMasterEntry 5 }

vtssPtpStatusClocksUnicastMasterAnn OBJECT-TYPE
    SYNTAX      TruthValue
    MAX-ACCESS  read-only
    STATUS      current
    DESCRIPTION
        "True if sending announce messages."
    ::= { vtssPtpStatusClocksUnicastMasterEntry 6 }

vtssPtpStatusClocksUnicastMasterLogMsgPeriod OBJECT-TYPE
    SYNTAX      VTSSInteger16
    MAX-ACCESS  read-only
    STATUS      current
    DESCRIPTION
        "The granted sync interval. Range -7 to 4."
    ::= { vtssPtpStatusClocksUnicastMasterEntry 7 }

vtssPtpStatusClocksUnicastMasterSync OBJECT-TYPE
    SYNTAX      TruthValue
    MAX-ACCESS  read-only
    STATUS      current
    DESCRIPTION
        "True if sending sync messages."
    ::= { vtssPtpStatusClocksUnicastMasterEntry 8 }

vtssPtpStatusClocksUnicastSlaveTable OBJECT-TYPE
    SYNTAX      SEQUENCE OF VTSSPtpStatusClocksUnicastSlaveEntry
    MAX-ACCESS  not-accessible
    STATUS      current
    DESCRIPTION
        "This is the dynamic (status) part of the PTP clocks unicast slave
         table."
    ::= { vtssPtpStatusClocks 7 }

vtssPtpStatusClocksUnicastSlaveEntry OBJECT-TYPE
    SYNTAX      VTSSPtpStatusClocksUnicastSlaveEntry
    MAX-ACCESS  not-accessible
    STATUS      current
    DESCRIPTION
        "The clockId index must be a value must be a value from 0 up to the
         number of PTP clocks minus one."
    INDEX       { vtssPtpStatusClocksUnicastSlaveClockId,
                  vtssPtpStatusClocksUnicastSlaveMasterId }
    ::= { vtssPtpStatusClocksUnicastSlaveTable 1 }

VTSSPtpStatusClocksUnicastSlaveEntry ::= SEQUENCE {
    vtssPtpStatusClocksUnicastSlaveClockId                          Integer32,
    vtssPtpStatusClocksUnicastSlaveMasterId                         Integer32,
    vtssPtpStatusClocksUnicastSlaveMasterIp                         IpAddress,
    vtssPtpStatusClocksUnicastSlaveMasterMac                        MacAddress,
    vtssPtpStatusClocksUnicastSlaveSourcePortIdentityClockIdentity  OCTET STRING,
    vtssPtpStatusClocksUnicastSlaveSourcePortIdentityPortNumber     VTSSUnsigned16,
    vtssPtpStatusClocksUnicastSlavePort                             VTSSUnsigned16,
    vtssPtpStatusClocksUnicastSlaveLogMsgPeriod                     VTSSInteger16,
    vtssPtpStatusClocksUnicastSlaveCommState                        VTSSptpUcCommState,
    vtssPtpStatusClocksUnicastSlaveConfMasterIp                     IpAddress
}

vtssPtpStatusClocksUnicastSlaveClockId OBJECT-TYPE
    SYNTAX      Integer32 (0..32767)
    MAX-ACCESS  accessible-for-notify
    STATUS      current
    DESCRIPTION
        "-"
    ::= { vtssPtpStatusClocksUnicastSlaveEntry 1 }

vtssPtpStatusClocksUnicastSlaveMasterId OBJECT-TYPE
    SYNTAX      Integer32 (0..32767)
    MAX-ACCESS  accessible-for-notify
    STATUS      current
    DESCRIPTION
        "-"
    ::= { vtssPtpStatusClocksUnicastSlaveEntry 2 }

vtssPtpStatusClocksUnicastSlaveMasterIp OBJECT-TYPE
    SYNTAX      IpAddress
    MAX-ACCESS  read-only
    STATUS      current
    DESCRIPTION
        "This is the IP address of the master."
    ::= { vtssPtpStatusClocksUnicastSlaveEntry 3 }

vtssPtpStatusClocksUnicastSlaveMasterMac OBJECT-TYPE
    SYNTAX      MacAddress
    MAX-ACCESS  read-only
    STATUS      current
    DESCRIPTION
        "This is the MAC address of the master."
    ::= { vtssPtpStatusClocksUnicastSlaveEntry 4 }

vtssPtpStatusClocksUnicastSlaveSourcePortIdentityClockIdentity OBJECT-TYPE
    SYNTAX      OCTET STRING (SIZE(8))
    MAX-ACCESS  read-only
    STATUS      current
    DESCRIPTION
        "This is the 8 byte unique clock identity of the source port."
    ::= { vtssPtpStatusClocksUnicastSlaveEntry 5 }

vtssPtpStatusClocksUnicastSlaveSourcePortIdentityPortNumber OBJECT-TYPE
    SYNTAX      VTSSUnsigned16
    MAX-ACCESS  read-only
    STATUS      current
    DESCRIPTION
        "This is port number of the port used on the source."
    ::= { vtssPtpStatusClocksUnicastSlaveEntry 6 }

vtssPtpStatusClocksUnicastSlavePort OBJECT-TYPE
    SYNTAX      VTSSUnsigned16
    MAX-ACCESS  read-only
    STATUS      current
    DESCRIPTION
        "The port (on the slave) connected to the master."
    ::= { vtssPtpStatusClocksUnicastSlaveEntry 7 }

vtssPtpStatusClocksUnicastSlaveLogMsgPeriod OBJECT-TYPE
    SYNTAX      VTSSInteger16
    MAX-ACCESS  read-only
    STATUS      current
    DESCRIPTION
        "The granted sync interval."
    ::= { vtssPtpStatusClocksUnicastSlaveEntry 8 }

vtssPtpStatusClocksUnicastSlaveCommState OBJECT-TYPE
    SYNTAX      VTSSptpUcCommState
    MAX-ACCESS  read-only
    STATUS      current
    DESCRIPTION
        "Communication state."
    ::= { vtssPtpStatusClocksUnicastSlaveEntry 9 }

vtssPtpStatusClocksUnicastSlaveConfMasterIp OBJECT-TYPE
    SYNTAX      IpAddress
    MAX-ACCESS  read-only
    STATUS      current
    DESCRIPTION
        "Copy of the destination ip address."
    ::= { vtssPtpStatusClocksUnicastSlaveEntry 10 }

vtssPtpStatusClocksPortsDsTable OBJECT-TYPE
    SYNTAX      SEQUENCE OF VTSSPtpStatusClocksPortsDsEntry
    MAX-ACCESS  not-accessible
    STATUS      current
    DESCRIPTION
        "This is the dynamic (status) part of the PTP clocks PortDS."
    ::= { vtssPtpStatusClocks 8 }

vtssPtpStatusClocksPortsDsEntry OBJECT-TYPE
    SYNTAX      VTSSPtpStatusClocksPortsDsEntry
    MAX-ACCESS  not-accessible
    STATUS      current
    DESCRIPTION
        "The clockId index must be a value must be a value from 0 up to the
         number of PTP clocks minus one."
    INDEX       { vtssPtpStatusClocksPortsDsClockId,
                  vtssPtpStatusClocksPortsDsPortId }
    ::= { vtssPtpStatusClocksPortsDsTable 1 }

VTSSPtpStatusClocksPortsDsEntry ::= SEQUENCE {
    vtssPtpStatusClocksPortsDsClockId                              Integer32,
    vtssPtpStatusClocksPortsDsPortId                               VTSSInterfaceIndex,
    vtssPtpStatusClocksPortsDsPortState                            VTSSptpClockPortState,
    vtssPtpStatusClocksPortsDsLogMinDelayReqInterval               VTSSInteger16,
    vtssPtpStatusClocksPortsDsPeerMeanPathDelay                    VTSSInteger64,
    vtssPtpStatusClocksPortsDsPeerDelayOk                          TruthValue,
    vtssPtpStatusClocksPortsDsS8021asPortRole                      VTSSptp8021asPortRole,
    vtssPtpStatusClocksPortsDsS8021asIsMeasuringDelay              TruthValue,
    vtssPtpStatusClocksPortsDsS8021asAsCapable                     TruthValue,
    vtssPtpStatusClocksPortsDsS8021asNeighborRateRatio             Integer32,
    vtssPtpStatusClocksPortsDsS8021asCurrentLogAnnounceInterval    VTSSInteger8,
    vtssPtpStatusClocksPortsDsS8021asCurrentLogSyncInterval        VTSSInteger8,
    vtssPtpStatusClocksPortsDsS8021asSyncReceiptTimeInterval       VTSSInteger64,
    vtssPtpStatusClocksPortsDsS8021asCurrentLogPDelayReqInterval   VTSSInteger8,
    vtssPtpStatusClocksPortsDsS8021asAcceptableMasterTableEnabled  TruthValue,
    vtssPtpStatusClocksPortsDsS8021asVersionNumber                 VTSSUnsigned8,
    vtssPtpStatusClocksPortsDsS8021asCurrentCompNbrRateRatio       TruthValue,
    vtssPtpStatusClocksPortsDsS8021asCurrentCompMeanLinkDelay      TruthValue
}

vtssPtpStatusClocksPortsDsClockId OBJECT-TYPE
    SYNTAX      Integer32 (0..32767)
    MAX-ACCESS  accessible-for-notify
    STATUS      current
    DESCRIPTION
        "-"
    ::= { vtssPtpStatusClocksPortsDsEntry 1 }

vtssPtpStatusClocksPortsDsPortId OBJECT-TYPE
    SYNTAX      VTSSInterfaceIndex
    MAX-ACCESS  accessible-for-notify
    STATUS      current
    DESCRIPTION
        "-"
    ::= { vtssPtpStatusClocksPortsDsEntry 2 }

vtssPtpStatusClocksPortsDsPortState OBJECT-TYPE
    SYNTAX      VTSSptpClockPortState
    MAX-ACCESS  read-only
    STATUS      current
    DESCRIPTION
        "The state of the port. Valid options : initializing, faulty, disabled,
         listening, preMaster, master, passive, uncalibrated, slave,
         p2pTransparent, e2eTransparent and frontend."
    ::= { vtssPtpStatusClocksPortsDsEntry 3 }

vtssPtpStatusClocksPortsDsLogMinDelayReqInterval OBJECT-TYPE
    SYNTAX      VTSSInteger16
    MAX-ACCESS  read-only
    STATUS      current
    DESCRIPTION
        "The delay request interval announced by the master. Range -7 to 5."
    ::= { vtssPtpStatusClocksPortsDsEntry 4 }

vtssPtpStatusClocksPortsDsPeerMeanPathDelay OBJECT-TYPE
    SYNTAX      VTSSInteger64
    MAX-ACCESS  read-only
    STATUS      current
    DESCRIPTION
        "The path delay measured in ns by the port in P2P mode."
    ::= { vtssPtpStatusClocksPortsDsEntry 5 }

vtssPtpStatusClocksPortsDsPeerDelayOk OBJECT-TYPE
    SYNTAX      TruthValue
    MAX-ACCESS  read-only
    STATUS      current
    DESCRIPTION
        "False if portmode is P2P and peer delay has not been measured."
    ::= { vtssPtpStatusClocksPortsDsEntry 6 }

vtssPtpStatusClocksPortsDsS8021asPortRole OBJECT-TYPE
    SYNTAX      VTSSptp8021asPortRole
    MAX-ACCESS  read-only
    STATUS      current
    DESCRIPTION
        "Port role of this port. Valid options : disabledPort, masterPort,
         passivePort and slavePort."
    ::= { vtssPtpStatusClocksPortsDsEntry 8 }

vtssPtpStatusClocksPortsDsS8021asIsMeasuringDelay OBJECT-TYPE
    SYNTAX      TruthValue
    MAX-ACCESS  read-only
    STATUS      current
    DESCRIPTION
        "TRUE if the port is measuring link propagation delay."
    ::= { vtssPtpStatusClocksPortsDsEntry 9 }

vtssPtpStatusClocksPortsDsS8021asAsCapable OBJECT-TYPE
    SYNTAX      TruthValue
    MAX-ACCESS  read-only
    STATUS      current
    DESCRIPTION
        "TRUE if the time-aware system at the other end of the link is 802.1AS
         capable."
    ::= { vtssPtpStatusClocksPortsDsEntry 10 }

vtssPtpStatusClocksPortsDsS8021asNeighborRateRatio OBJECT-TYPE
    SYNTAX      Integer32
    MAX-ACCESS  read-only
    STATUS      current
    DESCRIPTION
        "Calculated neighbor rate ratio expressed as the fractional frequency
         offset multiplied by 2**41."
    ::= { vtssPtpStatusClocksPortsDsEntry 11 }

vtssPtpStatusClocksPortsDsS8021asCurrentLogAnnounceInterval OBJECT-TYPE
    SYNTAX      VTSSInteger8
    MAX-ACCESS  read-only
    STATUS      current
    DESCRIPTION
        "log2 of the current announce interval."
    ::= { vtssPtpStatusClocksPortsDsEntry 12 }

vtssPtpStatusClocksPortsDsS8021asCurrentLogSyncInterval OBJECT-TYPE
    SYNTAX      VTSSInteger8
    MAX-ACCESS  read-only
    STATUS      current
    DESCRIPTION
        "log2 of the current sync interval."
    ::= { vtssPtpStatusClocksPortsDsEntry 13 }

vtssPtpStatusClocksPortsDsS8021asSyncReceiptTimeInterval OBJECT-TYPE
    SYNTAX      VTSSInteger64
    MAX-ACCESS  read-only
    STATUS      current
    DESCRIPTION
        "Time interval after which sync receipt timeout occurs if
         time-synchronization information has not been received during the
         interval."
    ::= { vtssPtpStatusClocksPortsDsEntry 14 }

vtssPtpStatusClocksPortsDsS8021asCurrentLogPDelayReqInterval OBJECT-TYPE
    SYNTAX      VTSSInteger8
    MAX-ACCESS  read-only
    STATUS      current
    DESCRIPTION
        "log2 of the current Pdelay_Req interval."
    ::= { vtssPtpStatusClocksPortsDsEntry 15 }

vtssPtpStatusClocksPortsDsS8021asAcceptableMasterTableEnabled OBJECT-TYPE
    SYNTAX      TruthValue
    MAX-ACCESS  read-only
    STATUS      current
    DESCRIPTION
        "Always FALSE."
    ::= { vtssPtpStatusClocksPortsDsEntry 16 }

vtssPtpStatusClocksPortsDsS8021asVersionNumber OBJECT-TYPE
    SYNTAX      VTSSUnsigned8
    MAX-ACCESS  read-only
    STATUS      current
    DESCRIPTION
        "IEEE 1588 PTP version number (always 2)."
    ::= { vtssPtpStatusClocksPortsDsEntry 17 }

vtssPtpStatusClocksPortsDsS8021asCurrentCompNbrRateRatio OBJECT-TYPE
    SYNTAX      TruthValue
    MAX-ACCESS  read-only
    STATUS      current
    DESCRIPTION
        "current value of computeNeighborRateRatio."
    ::= { vtssPtpStatusClocksPortsDsEntry 18 }

vtssPtpStatusClocksPortsDsS8021asCurrentCompMeanLinkDelay OBJECT-TYPE
    SYNTAX      TruthValue
    MAX-ACCESS  read-only
    STATUS      current
    DESCRIPTION
        "current value of computeMeanLinkDelay."
    ::= { vtssPtpStatusClocksPortsDsEntry 19 }

vtssPtpStatusCmlds OBJECT IDENTIFIER
    ::= { vtssPtpStatus 2 }

vtssPtpStatusCmldsPortDsTable OBJECT-TYPE
    SYNTAX      SEQUENCE OF VTSSPtpStatusCmldsPortDsEntry
    MAX-ACCESS  not-accessible
    STATUS      current
    DESCRIPTION
        "This is the dynamic part of the PTP clocks CMLDS PortDS."
    ::= { vtssPtpStatusCmlds 1 }

vtssPtpStatusCmldsPortDsEntry OBJECT-TYPE
    SYNTAX      VTSSPtpStatusCmldsPortDsEntry
    MAX-ACCESS  not-accessible
    STATUS      current
    DESCRIPTION
        "The port_id index must be a value from 0 up to the number of ports."
    INDEX       { vtssPtpStatusCmldsPortDsPortIdentityPortNumber }
    ::= { vtssPtpStatusCmldsPortDsTable 1 }

VTSSPtpStatusCmldsPortDsEntry ::= SEQUENCE {
    vtssPtpStatusCmldsPortDsPortIdentityPortNumber       Unsigned32,
    vtssPtpStatusCmldsPortDsPortIdentityClockIdentity    OCTET STRING,
    vtssPtpStatusCmldsPortDsCmldsLinkPortEnabled         TruthValue,
    vtssPtpStatusCmldsPortDsIsMeasuringDelay             TruthValue,
    vtssPtpStatusCmldsPortDsAsCapableAcrossDomains       TruthValue,
    vtssPtpStatusCmldsPortDsMeanLinkDelay                VTSSInteger64,
    vtssPtpStatusCmldsPortDsNeighborRateRatio            Integer32,
    vtssPtpStatusCmldsPortDsCurrentLogPDelayReqInterval  VTSSInteger8,
    vtssPtpStatusCmldsPortDsCurrentCompNbrRateRatio      TruthValue,
    vtssPtpStatusCmldsPortDsCurrentCompMeanLinkDelay     TruthValue,
    vtssPtpStatusCmldsPortDsVersionNumber                VTSSUnsigned8,
    vtssPtpStatusCmldsPortDsMinorVersionNumber           VTSSUnsigned8
}

vtssPtpStatusCmldsPortDsPortIdentityPortNumber OBJECT-TYPE
    SYNTAX      Unsigned32 (0..255)
    MAX-ACCESS  accessible-for-notify
    STATUS      current
    DESCRIPTION
        "This is the port number on which CMLDS can be enabled."
    ::= { vtssPtpStatusCmldsPortDsEntry 1 }

vtssPtpStatusCmldsPortDsPortIdentityClockIdentity OBJECT-TYPE
    SYNTAX      OCTET STRING (SIZE(8))
    MAX-ACCESS  read-only
    STATUS      current
    DESCRIPTION
        "This is the 8 byte unique clock identity of the parent port."
    ::= { vtssPtpStatusCmldsPortDsEntry 2 }

vtssPtpStatusCmldsPortDsCmldsLinkPortEnabled OBJECT-TYPE
    SYNTAX      TruthValue
    MAX-ACCESS  read-only
    STATUS      current
    DESCRIPTION
        "This value is true if CMLDS is used on this port by atleast one PTP
         clock."
    ::= { vtssPtpStatusCmldsPortDsEntry 3 }

vtssPtpStatusCmldsPortDsIsMeasuringDelay OBJECT-TYPE
    SYNTAX      TruthValue
    MAX-ACCESS  read-only
    STATUS      current
    DESCRIPTION
        "true if the CMLDS service is measuring link propagation delay on this
         port."
    ::= { vtssPtpStatusCmldsPortDsEntry 4 }

vtssPtpStatusCmldsPortDsAsCapableAcrossDomains OBJECT-TYPE
    SYNTAX      TruthValue
    MAX-ACCESS  read-only
    STATUS      current
    DESCRIPTION
        "true if CMLDS service reaches asCapable state when the conditions for
         neighbor rate ratio and link delay are met."
    ::= { vtssPtpStatusCmldsPortDsEntry 5 }

vtssPtpStatusCmldsPortDsMeanLinkDelay OBJECT-TYPE
    SYNTAX      VTSSInteger64
    MAX-ACCESS  read-only
    STATUS      current
    DESCRIPTION
        "the measured mean propagation delay on the link attached to this port"
    ::= { vtssPtpStatusCmldsPortDsEntry 6 }

vtssPtpStatusCmldsPortDsNeighborRateRatio OBJECT-TYPE
    SYNTAX      Integer32
    MAX-ACCESS  read-only
    STATUS      current
    DESCRIPTION
        "Calculated neighbor rate ratio expressed as the fractional frequency
         offset multiplied by 2**41."
    ::= { vtssPtpStatusCmldsPortDsEntry 7 }

vtssPtpStatusCmldsPortDsCurrentLogPDelayReqInterval OBJECT-TYPE
    SYNTAX      VTSSInteger8
    MAX-ACCESS  read-only
    STATUS      current
    DESCRIPTION
        "the value is the logarithm to the base 2 of the current Pdelay_Req
         message transmission interval."
    ::= { vtssPtpStatusCmldsPortDsEntry 8 }

vtssPtpStatusCmldsPortDsCurrentCompNbrRateRatio OBJECT-TYPE
    SYNTAX      TruthValue
    MAX-ACCESS  read-only
    STATUS      current
    DESCRIPTION
        "true if Neighbor rate ratio is being computed."
    ::= { vtssPtpStatusCmldsPortDsEntry 9 }

vtssPtpStatusCmldsPortDsCurrentCompMeanLinkDelay OBJECT-TYPE
    SYNTAX      TruthValue
    MAX-ACCESS  read-only
    STATUS      current
    DESCRIPTION
        "true if MeanLinkDelay is being measured by CMLDS service currently."
    ::= { vtssPtpStatusCmldsPortDsEntry 10 }

vtssPtpStatusCmldsPortDsVersionNumber OBJECT-TYPE
    SYNTAX      VTSSUnsigned8
    MAX-ACCESS  read-only
    STATUS      current
    DESCRIPTION
        "Version number of IEEE 1588 PTP used in the PTP 802.1as profile."
    ::= { vtssPtpStatusCmldsPortDsEntry 11 }

vtssPtpStatusCmldsPortDsMinorVersionNumber OBJECT-TYPE
    SYNTAX      VTSSUnsigned8
    MAX-ACCESS  read-only
    STATUS      current
    DESCRIPTION
        "Minor version number set to 1 for transmitted messages of 802.1as
         profile."
    ::= { vtssPtpStatusCmldsPortDsEntry 12 }

vtssPtpStatusCmldsDefaultDs OBJECT IDENTIFIER
    ::= { vtssPtpStatusCmlds 2 }

vtssPtpStatusCmldsDefaultDsClockIdentity OBJECT-TYPE
    SYNTAX      OCTET STRING (SIZE(8))
    MAX-ACCESS  read-only
    STATUS      current
    DESCRIPTION
        "Identity of the PTP clock associated with common link delay service."
    ::= { vtssPtpStatusCmldsDefaultDs 1 }

vtssPtpStatusCmldsDefaultDsNumberLinkPorts OBJECT-TYPE
    SYNTAX      VTSSUnsigned16
    MAX-ACCESS  read-only
    STATUS      current
    DESCRIPTION
        "number of Link Ports of the time-aware system on which the Common Mean
         Link Delay Service can be enabled."
    ::= { vtssPtpStatusCmldsDefaultDs 2 }

vtssPtpStatusCmldsDefaultDsSdoId OBJECT-TYPE
    SYNTAX      VTSSUnsigned16
    MAX-ACCESS  read-only
    STATUS      current
    DESCRIPTION
        "sdoID for Common Mean Link Delay Service."
    ::= { vtssPtpStatusCmldsDefaultDs 3 }

vtssPtpControl OBJECT IDENTIFIER
    ::= { vtssPtpMibObjects 4 }

vtssPtpControlClocksTable OBJECT-TYPE
    SYNTAX      SEQUENCE OF VTSSPtpControlClocksEntry
    MAX-ACCESS  not-accessible
    STATUS      current
    DESCRIPTION
        "This is the PTP clocks control structure."
    ::= { vtssPtpControl 1 }

vtssPtpControlClocksEntry OBJECT-TYPE
    SYNTAX      VTSSPtpControlClocksEntry
    MAX-ACCESS  not-accessible
    STATUS      current
    DESCRIPTION
        "The clockId index must be a value must be a value from 0 up to the
         number of PTP clocks minus one."
    INDEX       { vtssPtpControlClocksClockId }
    ::= { vtssPtpControlClocksTable 1 }

VTSSPtpControlClocksEntry ::= SEQUENCE {
    vtssPtpControlClocksClockId            Integer32,
    vtssPtpControlClocksSyncToSystemClock  VTSSUnsigned8
}

vtssPtpControlClocksClockId OBJECT-TYPE
    SYNTAX      Integer32 (0..32767)
    MAX-ACCESS  accessible-for-notify
    STATUS      current
    DESCRIPTION
        "-"
    ::= { vtssPtpControlClocksEntry 1 }

vtssPtpControlClocksSyncToSystemClock OBJECT-TYPE
    SYNTAX      VTSSUnsigned8
    MAX-ACCESS  read-write
    STATUS      current
    DESCRIPTION
        "-"
    ::= { vtssPtpControlClocksEntry 2 }

vtssPtpStatistics OBJECT IDENTIFIER
    ::= { vtssPtpMibObjects 5 }

vtssPtpStatisticsClocks OBJECT IDENTIFIER
    ::= { vtssPtpStatistics 1 }

vtssPtpStatisticsClocksPortsDsTable OBJECT-TYPE
    SYNTAX      SEQUENCE OF VTSSPtpStatisticsClocksPortsDsEntry
    MAX-ACCESS  not-accessible
    STATUS      current
    DESCRIPTION
        "This is the dynamic (status) part of the PTP port parameter statistics."
    ::= { vtssPtpStatisticsClocks 1 }

vtssPtpStatisticsClocksPortsDsEntry OBJECT-TYPE
    SYNTAX      VTSSPtpStatisticsClocksPortsDsEntry
    MAX-ACCESS  not-accessible
    STATUS      current
    DESCRIPTION
        "The clockId index must be a value must be a value from 0 up to the
         number of PTP clocks minus one."
    INDEX       { vtssPtpStatisticsClocksPortsDsClockId,
                  vtssPtpStatisticsClocksPortsDsPortId }
    ::= { vtssPtpStatisticsClocksPortsDsTable 1 }

VTSSPtpStatisticsClocksPortsDsEntry ::= SEQUENCE {
    vtssPtpStatisticsClocksPortsDsClockId                        Integer32,
    vtssPtpStatisticsClocksPortsDsPortId                         VTSSInterfaceIndex,
    vtssPtpStatisticsClocksPortsDsRxSyncCount                    Unsigned32,
    vtssPtpStatisticsClocksPortsDsRxFollowUpCount                Unsigned32,
    vtssPtpStatisticsClocksPortsDsRxPdelayRequestCount           Unsigned32,
    vtssPtpStatisticsClocksPortsDsRxPdelayResponseCount          Unsigned32,
    vtssPtpStatisticsClocksPortsDsRxPdelayResponseFollowUpCount  Unsigned32,
    vtssPtpStatisticsClocksPortsDsRxAnnounceCount                Unsigned32,
    vtssPtpStatisticsClocksPortsDsRxPTPPacketDiscardCount        Unsigned32,
    vtssPtpStatisticsClocksPortsDsSyncReceiptTimeoutCount        Unsigned32,
    vtssPtpStatisticsClocksPortsDsAnnounceReceiptTimeoutCount    Unsigned32,
    vtssPtpStatisticsClocksPortsDsPdelayAllowedLostResExcCount   Unsigned32,
    vtssPtpStatisticsClocksPortsDsTxSyncCount                    Unsigned32,
    vtssPtpStatisticsClocksPortsDsTxFollowUpCount                Unsigned32,
    vtssPtpStatisticsClocksPortsDsTxPdelayRequestCount           Unsigned32,
    vtssPtpStatisticsClocksPortsDsTxPdelayResponseCount          Unsigned32,
    vtssPtpStatisticsClocksPortsDsTxPdelayResponseFollowUpCount  Unsigned32,
    vtssPtpStatisticsClocksPortsDsTxAnnounceCount                Unsigned32
}

vtssPtpStatisticsClocksPortsDsClockId OBJECT-TYPE
    SYNTAX      Integer32 (0..32767)
    MAX-ACCESS  accessible-for-notify
    STATUS      current
    DESCRIPTION
        "-"
    ::= { vtssPtpStatisticsClocksPortsDsEntry 1 }

vtssPtpStatisticsClocksPortsDsPortId OBJECT-TYPE
    SYNTAX      VTSSInterfaceIndex
    MAX-ACCESS  accessible-for-notify
    STATUS      current
    DESCRIPTION
        "-"
    ::= { vtssPtpStatisticsClocksPortsDsEntry 2 }

vtssPtpStatisticsClocksPortsDsRxSyncCount OBJECT-TYPE
    SYNTAX      Unsigned32
    MAX-ACCESS  read-only
    STATUS      current
    DESCRIPTION
        "Increments every time synchronization is received."
    ::= { vtssPtpStatisticsClocksPortsDsEntry 3 }

vtssPtpStatisticsClocksPortsDsRxFollowUpCount OBJECT-TYPE
    SYNTAX      Unsigned32
    MAX-ACCESS  read-only
    STATUS      current
    DESCRIPTION
        "Increments every time a Follow_Up is received."
    ::= { vtssPtpStatisticsClocksPortsDsEntry 4 }

vtssPtpStatisticsClocksPortsDsRxPdelayRequestCount OBJECT-TYPE
    SYNTAX      Unsigned32
    MAX-ACCESS  read-only
    STATUS      current
    DESCRIPTION
        "Increments every time a Pdelay_Req is received."
    ::= { vtssPtpStatisticsClocksPortsDsEntry 5 }

vtssPtpStatisticsClocksPortsDsRxPdelayResponseCount OBJECT-TYPE
    SYNTAX      Unsigned32
    MAX-ACCESS  read-only
    STATUS      current
    DESCRIPTION
        "Increments every time a Pdelay_Resp is received."
    ::= { vtssPtpStatisticsClocksPortsDsEntry 6 }

vtssPtpStatisticsClocksPortsDsRxPdelayResponseFollowUpCount OBJECT-TYPE
    SYNTAX      Unsigned32
    MAX-ACCESS  read-only
    STATUS      current
    DESCRIPTION
        "Increments every time a Pdelay_Resp_Follow_Up is received."
    ::= { vtssPtpStatisticsClocksPortsDsEntry 7 }

vtssPtpStatisticsClocksPortsDsRxAnnounceCount OBJECT-TYPE
    SYNTAX      Unsigned32
    MAX-ACCESS  read-only
    STATUS      current
    DESCRIPTION
        "Increments every time a Announce message is received."
    ::= { vtssPtpStatisticsClocksPortsDsEntry 8 }

vtssPtpStatisticsClocksPortsDsRxPTPPacketDiscardCount OBJECT-TYPE
    SYNTAX      Unsigned32
    MAX-ACCESS  read-only
    STATUS      current
    DESCRIPTION
        "Increments every time a PTP message is discarded due to the conditions
         described in IEEE 802.1AS clause 14.7.8."
    ::= { vtssPtpStatisticsClocksPortsDsEntry 9 }

vtssPtpStatisticsClocksPortsDsSyncReceiptTimeoutCount OBJECT-TYPE
    SYNTAX      Unsigned32
    MAX-ACCESS  read-only
    STATUS      current
    DESCRIPTION
        "Increments every time sync receipt timeout occurs."
    ::= { vtssPtpStatisticsClocksPortsDsEntry 10 }

vtssPtpStatisticsClocksPortsDsAnnounceReceiptTimeoutCount OBJECT-TYPE
    SYNTAX      Unsigned32
    MAX-ACCESS  read-only
    STATUS      current
    DESCRIPTION
        "Increments every time announce receipt timeout occurs."
    ::= { vtssPtpStatisticsClocksPortsDsEntry 11 }

vtssPtpStatisticsClocksPortsDsPdelayAllowedLostResExcCount OBJECT-TYPE
    SYNTAX      Unsigned32
    MAX-ACCESS  read-only
    STATUS      current
    DESCRIPTION
        "Increments every time the value of the variable lostResponses exceeds
         the value of the variable allowedLostResponses."
    ::= { vtssPtpStatisticsClocksPortsDsEntry 12 }

vtssPtpStatisticsClocksPortsDsTxSyncCount OBJECT-TYPE
    SYNTAX      Unsigned32
    MAX-ACCESS  read-only
    STATUS      current
    DESCRIPTION
        "Increments every time synchronization information is transmitted."
    ::= { vtssPtpStatisticsClocksPortsDsEntry 13 }

vtssPtpStatisticsClocksPortsDsTxFollowUpCount OBJECT-TYPE
    SYNTAX      Unsigned32
    MAX-ACCESS  read-only
    STATUS      current
    DESCRIPTION
        "Increments every time a Follow_Up message is transmitted."
    ::= { vtssPtpStatisticsClocksPortsDsEntry 14 }

vtssPtpStatisticsClocksPortsDsTxPdelayRequestCount OBJECT-TYPE
    SYNTAX      Unsigned32
    MAX-ACCESS  read-only
    STATUS      current
    DESCRIPTION
        "Increments every time a Pdelay_Req message is transmitted."
    ::= { vtssPtpStatisticsClocksPortsDsEntry 15 }

vtssPtpStatisticsClocksPortsDsTxPdelayResponseCount OBJECT-TYPE
    SYNTAX      Unsigned32
    MAX-ACCESS  read-only
    STATUS      current
    DESCRIPTION
        "Increments every time a Pdelay_Resp message is transmitted."
    ::= { vtssPtpStatisticsClocksPortsDsEntry 16 }

vtssPtpStatisticsClocksPortsDsTxPdelayResponseFollowUpCount OBJECT-TYPE
    SYNTAX      Unsigned32
    MAX-ACCESS  read-only
    STATUS      current
    DESCRIPTION
        "Increments every time a Pdelay_Resp_Follow_Up message is transmitted."
    ::= { vtssPtpStatisticsClocksPortsDsEntry 17 }

vtssPtpStatisticsClocksPortsDsTxAnnounceCount OBJECT-TYPE
    SYNTAX      Unsigned32
    MAX-ACCESS  read-only
    STATUS      current
    DESCRIPTION
        "Increments every time an Announce message is transmitted."
    ::= { vtssPtpStatisticsClocksPortsDsEntry 18 }

vtssPtpStatisticsCmlds OBJECT IDENTIFIER
    ::= { vtssPtpStatistics 2 }

vtssPtpStatisticsCmldsPortDsTable OBJECT-TYPE
    SYNTAX      SEQUENCE OF VTSSPtpStatisticsCmldsPortDsEntry
    MAX-ACCESS  not-accessible
    STATUS      current
    DESCRIPTION
        "This is the statistics part of Common Mean Link Delay Service Port."
    ::= { vtssPtpStatisticsCmlds 1 }

vtssPtpStatisticsCmldsPortDsEntry OBJECT-TYPE
    SYNTAX      VTSSPtpStatisticsCmldsPortDsEntry
    MAX-ACCESS  not-accessible
    STATUS      current
    DESCRIPTION
        "The port_id index must be a value from 0 up to the number of ports."
    INDEX       {                   vtssPtpStatisticsCmldsPortDsPortIdentityPortNumber }
    ::= { vtssPtpStatisticsCmldsPortDsTable 1 }

VTSSPtpStatisticsCmldsPortDsEntry ::= SEQUENCE {
    vtssPtpStatisticsCmldsPortDsPortIdentityPortNumber         Unsigned32,
    vtssPtpStatisticsCmldsPortDsRxPdelayRequestCount           Unsigned32,
    vtssPtpStatisticsCmldsPortDsRxPdelayResponseCount          Unsigned32,
    vtssPtpStatisticsCmldsPortDsRxPdelayResponseFollowUpCount  Unsigned32,
    vtssPtpStatisticsCmldsPortDsRxPTPPacketDiscardCount        Unsigned32,
    vtssPtpStatisticsCmldsPortDsPdelayAllowedLostResExcCount   Unsigned32,
    vtssPtpStatisticsCmldsPortDsTxPdelayRequestCount           Unsigned32,
    vtssPtpStatisticsCmldsPortDsTxPdelayResponseCount          Unsigned32,
    vtssPtpStatisticsCmldsPortDsTxPdelayResponseFollowUpCount  Unsigned32
}

vtssPtpStatisticsCmldsPortDsPortIdentityPortNumber OBJECT-TYPE
    SYNTAX      Unsigned32 (0..255)
    MAX-ACCESS  accessible-for-notify
    STATUS      current
    DESCRIPTION
        "This is the port number of the Common Mean Link Delay Service enabled
         port."
    ::= { vtssPtpStatisticsCmldsPortDsEntry 1 }

vtssPtpStatisticsCmldsPortDsRxPdelayRequestCount OBJECT-TYPE
    SYNTAX      Unsigned32
    MAX-ACCESS  read-only
    STATUS      current
    DESCRIPTION
        "Increments every time a Pdelay_Req is received."
    ::= { vtssPtpStatisticsCmldsPortDsEntry 2 }

vtssPtpStatisticsCmldsPortDsRxPdelayResponseCount OBJECT-TYPE
    SYNTAX      Unsigned32
    MAX-ACCESS  read-only
    STATUS      current
    DESCRIPTION
        "Increments every time a Pdelay_Response is received."
    ::= { vtssPtpStatisticsCmldsPortDsEntry 3 }

vtssPtpStatisticsCmldsPortDsRxPdelayResponseFollowUpCount OBJECT-TYPE
    SYNTAX      Unsigned32
    MAX-ACCESS  read-only
    STATUS      current
    DESCRIPTION
        "Increments every time a PdelayResponseFollowup is received."
    ::= { vtssPtpStatisticsCmldsPortDsEntry 4 }

vtssPtpStatisticsCmldsPortDsRxPTPPacketDiscardCount OBJECT-TYPE
    SYNTAX      Unsigned32
    MAX-ACCESS  read-only
    STATUS      current
    DESCRIPTION
        "Increments every time a PTP message of Common Mean Link Delay Service
         is discarded."
    ::= { vtssPtpStatisticsCmldsPortDsEntry 5 }

vtssPtpStatisticsCmldsPortDsPdelayAllowedLostResExcCount OBJECT-TYPE
    SYNTAX      Unsigned32
    MAX-ACCESS  read-only
    STATUS      current
    DESCRIPTION
        "Increments every time the value of the variable lostResponses exceeds
         the value of the variable allowedLostResponses."
    ::= { vtssPtpStatisticsCmldsPortDsEntry 6 }

vtssPtpStatisticsCmldsPortDsTxPdelayRequestCount OBJECT-TYPE
    SYNTAX      Unsigned32
    MAX-ACCESS  read-only
    STATUS      current
    DESCRIPTION
        "Increments every time a Pdelay_Req message is transmitted."
    ::= { vtssPtpStatisticsCmldsPortDsEntry 7 }

vtssPtpStatisticsCmldsPortDsTxPdelayResponseCount OBJECT-TYPE
    SYNTAX      Unsigned32
    MAX-ACCESS  read-only
    STATUS      current
    DESCRIPTION
        "Increments every time a Pdelay_Resp message is transmitted."
    ::= { vtssPtpStatisticsCmldsPortDsEntry 8 }

vtssPtpStatisticsCmldsPortDsTxPdelayResponseFollowUpCount OBJECT-TYPE
    SYNTAX      Unsigned32
    MAX-ACCESS  read-only
    STATUS      current
    DESCRIPTION
        "Increments every time a Pdelay_Resp_Follow_Up message is transmitted."
    ::= { vtssPtpStatisticsCmldsPortDsEntry 9 }

vtssPtpMibConformance OBJECT IDENTIFIER
    ::= { vtssPtpMib 2 }

vtssPtpMibCompliances OBJECT IDENTIFIER
    ::= { vtssPtpMibConformance 1 }

vtssPtpMibGroups OBJECT IDENTIFIER
    ::= { vtssPtpMibConformance 2 }

vtssPtpCapabilitiesGlobalsInfoGroup OBJECT-GROUP
    OBJECTS     { vtssPtpCapabilitiesGlobalsClockCount,
                  vtssPtpCapabilitiesGlobalsHasMsPdv,
                  vtssPtpCapabilitiesGlobalsHasHwClkDomains }
    STATUS      current
    DESCRIPTION
        "A collection of objects."
    ::= { vtssPtpMibGroups 1 }

vtssPtpConfigGlobalsExternalClockModeInfoGroup OBJECT-GROUP
    OBJECTS     { vtssPtpConfigGlobalsExternalClockModeOnePpsMode,
                  vtssPtpConfigGlobalsExternalClockModeExternalEnable,
                  vtssPtpConfigGlobalsExternalClockModeAdjustMethod,
                  vtssPtpConfigGlobalsExternalClockModeClockFrequency,
                  vtssPtpConfigGlobalsExternalClockModePpsDomain }
    STATUS      current
    DESCRIPTION
        "A collection of objects."
    ::= { vtssPtpMibGroups 2 }

vtssPtpConfigGlobalsSystemTimeSyncModeInfoGroup OBJECT-GROUP
    OBJECTS     { vtssPtpConfigGlobalsSystemTimeSyncModeMode }
    STATUS      current
    DESCRIPTION
        "A collection of objects."
    ::= { vtssPtpMibGroups 3 }

vtssPtpConfigClocksDefaultDsTableInfoGroup OBJECT-GROUP
    OBJECTS     { vtssPtpConfigClocksDefaultDsClockId,
                  vtssPtpConfigClocksDefaultDsDeviceType,
                  vtssPtpConfigClocksDefaultDsTwoStepFlag,
                  vtssPtpConfigClocksDefaultDsPriority1,
                  vtssPtpConfigClocksDefaultDsPriority2,
                  vtssPtpConfigClocksDefaultDsOneWay,
                  vtssPtpConfigClocksDefaultDsDomainNumber,
                  vtssPtpConfigClocksDefaultDsProtocol,
                  vtssPtpConfigClocksDefaultDsVid,
                  vtssPtpConfigClocksDefaultDsPcp,
                  vtssPtpConfigClocksDefaultDsMep,
                  vtssPtpConfigClocksDefaultDsClkDom,
                  vtssPtpConfigClocksDefaultDsDscp,
                  vtssPtpConfigClocksDefaultDsProfile,
                  vtssPtpConfigClocksDefaultDsLocalPriority,
                  vtssPtpConfigClocksDefaultDsFilterType,
                  vtssPtpConfigClocksDefaultDsPathTraceEnable,
                  vtssPtpConfigClocksDefaultDsAction }
    STATUS      current
    DESCRIPTION
        "A collection of objects."
    ::= { vtssPtpMibGroups 4 }

vtssPtpConfigClocksDefaultDsTableRowEditorInfoGroup OBJECT-GROUP
    OBJECTS     { vtssPtpConfigClocksDefaultDsTableRowEditorClockId,
                  vtssPtpConfigClocksDefaultDsTableRowEditorDeviceType,
                  vtssPtpConfigClocksDefaultDsTableRowEditorTwoStepFlag,
                  vtssPtpConfigClocksDefaultDsTableRowEditorPriority1,
                  vtssPtpConfigClocksDefaultDsTableRowEditorPriority2,
                  vtssPtpConfigClocksDefaultDsTableRowEditorOneWay,
                  vtssPtpConfigClocksDefaultDsTableRowEditorDomainNumber,
                  vtssPtpConfigClocksDefaultDsTableRowEditorProtocol,
                  vtssPtpConfigClocksDefaultDsTableRowEditorVid,
                  vtssPtpConfigClocksDefaultDsTableRowEditorPcp,
                  vtssPtpConfigClocksDefaultDsTableRowEditorMep,
                  vtssPtpConfigClocksDefaultDsTableRowEditorClkDom,
                  vtssPtpConfigClocksDefaultDsTableRowEditorDscp,
                  vtssPtpConfigClocksDefaultDsTableRowEditorProfile,
                  vtssPtpConfigClocksDefaultDsTableRowEditorLocalPriority,
                  vtssPtpConfigClocksDefaultDsTableRowEditorFilterType,
                  vtssPtpConfigClocksDefaultDsTableRowEditorPathTraceEnable,
                  vtssPtpConfigClocksDefaultDsTableRowEditorAction }
    STATUS      current
    DESCRIPTION
        "A collection of objects."
    ::= { vtssPtpMibGroups 5 }

vtssPtpConfigClocksTimePropertiesDsTableInfoGroup OBJECT-GROUP
    OBJECTS     { vtssPtpConfigClocksTimePropertiesDsClockId,
                  vtssPtpConfigClocksTimePropertiesDsCurrentUtcOffset,
                  vtssPtpConfigClocksTimePropertiesDsCurrentUtcOffsetValid,
                  vtssPtpConfigClocksTimePropertiesDsLeap59,
                  vtssPtpConfigClocksTimePropertiesDsLeap61,
                  vtssPtpConfigClocksTimePropertiesDsTimeTraceable,
                  vtssPtpConfigClocksTimePropertiesDsFrequencyTraceable,
                  vtssPtpConfigClocksTimePropertiesDsPtpTimescale,
                  vtssPtpConfigClocksTimePropertiesDsTimeSource,
                  vtssPtpConfigClocksTimePropertiesDsPendingLeap,
                  vtssPtpConfigClocksTimePropertiesDsLeapDate,
                  vtssPtpConfigClocksTimePropertiesDsLeapType }
    STATUS      current
    DESCRIPTION
        "A collection of objects."
    ::= { vtssPtpMibGroups 6 }

vtssPtpConfigClocksFilterParametersTableInfoGroup OBJECT-GROUP
    OBJECTS     { vtssPtpConfigClocksFilterParametersClockId,
                  vtssPtpConfigClocksFilterParametersDelayFilter,
                  vtssPtpConfigClocksFilterParametersPeriod,
                  vtssPtpConfigClocksFilterParametersDist }
    STATUS      current
    DESCRIPTION
        "A collection of objects."
    ::= { vtssPtpMibGroups 7 }

vtssPtpConfigClocksServoParametersTableInfoGroup OBJECT-GROUP
    OBJECTS     { vtssPtpConfigClocksServoParametersClockId,
                  vtssPtpConfigClocksServoParametersDisplay,
                  vtssPtpConfigClocksServoParametersPEnable,
                  vtssPtpConfigClocksServoParametersIEnable,
                  vtssPtpConfigClocksServoParametersDEnable,
                  vtssPtpConfigClocksServoParametersPval,
                  vtssPtpConfigClocksServoParametersIval,
                  vtssPtpConfigClocksServoParametersDval,
                  vtssPtpConfigClocksServoParametersSrvOption,
                  vtssPtpConfigClocksServoParametersSynceThreshold,
                  vtssPtpConfigClocksServoParametersSynceAp,
                  vtssPtpConfigClocksServoParametersHoFilter,
                  vtssPtpConfigClocksServoParametersStableAdjThreshold,
                  vtssPtpConfigClocksServoParametersGain }
    STATUS      current
    DESCRIPTION
        "A collection of objects."
    ::= { vtssPtpMibGroups 8 }

vtssPtpConfigClocksSlaveConfigTableInfoGroup OBJECT-GROUP
    OBJECTS     { vtssPtpConfigClocksSlaveConfigClockId,
                  vtssPtpConfigClocksSlaveConfigStableOffset,
                  vtssPtpConfigClocksSlaveConfigOffsetOk,
                  vtssPtpConfigClocksSlaveConfigOffsetFail }
    STATUS      current
    DESCRIPTION
        "A collection of objects."
    ::= { vtssPtpMibGroups 9 }

vtssPtpConfigClocksUnicastSlaveConfigTableInfoGroup OBJECT-GROUP
    OBJECTS     { vtssPtpConfigClocksUnicastSlaveConfigClockId,
                  vtssPtpConfigClocksUnicastSlaveConfigMasterId,
                  vtssPtpConfigClocksUnicastSlaveConfigDuration,
                  vtssPtpConfigClocksUnicastSlaveConfigIpAddress }
    STATUS      current
    DESCRIPTION
        "A collection of objects."
    ::= { vtssPtpMibGroups 10 }

vtssPtpConfigClocksPortDsTableInfoGroup OBJECT-GROUP
    OBJECTS     { vtssPtpConfigClocksPortDsClockId,
                  vtssPtpConfigClocksPortDsPortId,
                  vtssPtpConfigClocksPortDsEnabled,
                  vtssPtpConfigClocksPortDsLogAnnounceInterval,
                  vtssPtpConfigClocksPortDsAnnounceReceiptTimeout,
                  vtssPtpConfigClocksPortDsLogSyncInterval,
                  vtssPtpConfigClocksPortDsDelayMechanism,
                  vtssPtpConfigClocksPortDsLogMinPdelayReqInterval,
                  vtssPtpConfigClocksPortDsDelayAsymmetry,
                  vtssPtpConfigClocksPortDsIngressLatency,
                  vtssPtpConfigClocksPortDsEgressLatency,
                  vtssPtpConfigClocksPortDsPortInternal,
                  vtssPtpConfigClocksPortDsVersionNumber,
                  vtssPtpConfigClocksPortDsMcastAddr,
                  vtssPtpConfigClocksPortDsMasterOnly,
                  vtssPtpConfigClocksPortDsLocalPriority,
                  vtssPtpConfigClocksPortDsNotMaster,
                  vtssPtpConfigClocksPortDsAs2020,
                  vtssPtpConfigClocksPortDsC8021asNeighborPropDelayThresh,
                  vtssPtpConfigClocksPortDsC8021asSyncReceiptTimeout,
                  vtssPtpConfigClocksPortDsC8021asAllowedLostResponses,
                  vtssPtpConfigClocksPortDsC8021asAllowedFaults,
                  vtssPtpConfigClocksPortDsC8021asUseMgtSettableLogAnnounceIntvl,
                  vtssPtpConfigClocksPortDsC8021asUseMgtSettableLogSyncIntvl,
                  vtssPtpConfigClocksPortDsC8021asUseMgtSettableLogPdelayReqIntvl,
                  vtssPtpConfigClocksPortDsC8021asMgtSettableLogAnnounceIntvl,
                  vtssPtpConfigClocksPortDsC8021asMgtSettableLogSyncIntvl,
                  vtssPtpConfigClocksPortDsC8021asMgtSettableLogPdelayReqIntvl,
                  vtssPtpConfigClocksPortDsC8021asUseMgtSettableLogGptpCapMsgIntvl,
                  vtssPtpConfigClocksPortDsC8021asMgtSettableLogGptpCapMsgIntvl,
                  vtssPtpConfigClocksPortDsC8021GptpCapableReceiptTimeout,
                  vtssPtpConfigClocksPortDsC8021InitialLogGptpCapableMessageIntvl,
                  vtssPtpConfigClocksPortDsC8021asUseMgtSetCompNbrRateRatio,
                  vtssPtpConfigClocksPortDsC8021asMgtSetCompNbrRateRatio,
                  vtssPtpConfigClocksPortDsC8021asUseMgtSetCompMeanLinkDelay,
                  vtssPtpConfigClocksPortDsC8021asmgtSetCompMeanLinkDelay }
    STATUS      current
    DESCRIPTION
        "A collection of objects."
    ::= { vtssPtpMibGroups 11 }

vtssPtpConfigClocksVirtualPortCfgTableInfoGroup OBJECT-GROUP
    OBJECTS     { vtssPtpConfigClocksVirtualPortCfgClockId,
                  vtssPtpConfigClocksVirtualPortCfgEnable,
                  vtssPtpConfigClocksVirtualPortCfgInputPin,
                  vtssPtpConfigClocksVirtualPortCfgClockQualityClockClass,
                  vtssPtpConfigClocksVirtualPortCfgClockQualityClockAccuracy,
                  vtssPtpConfigClocksVirtualPortCfgClockQualityOffsetScaledLogVar,
                  vtssPtpConfigClocksVirtualPortCfgPriority1,
                  vtssPtpConfigClocksVirtualPortCfgPriority2,
                  vtssPtpConfigClocksVirtualPortCfgLocalPriority,
                  vtssPtpConfigClocksVirtualPortCfgVirtualPortMode,
                  vtssPtpConfigClocksVirtualPortCfgOutputPin,
                  vtssPtpConfigClocksVirtualPortCfgProto,
                  vtssPtpConfigClocksVirtualPortCfgPortnum,
                  vtssPtpConfigClocksVirtualPortCfgPpsDelay,
                  vtssPtpConfigClocksVirtualPortCfgCurrentUtcOffset,
                  vtssPtpConfigClocksVirtualPortCfgCurrentUtcOffsetValid,
                  vtssPtpConfigClocksVirtualPortCfgLeap59,
                  vtssPtpConfigClocksVirtualPortCfgLeap61,
                  vtssPtpConfigClocksVirtualPortCfgTimeTraceable,
                  vtssPtpConfigClocksVirtualPortCfgFrequencyTraceable,
                  vtssPtpConfigClocksVirtualPortCfgPtpTimescale,
                  vtssPtpConfigClocksVirtualPortCfgTimeSource,
                  vtssPtpConfigClocksVirtualPortCfgPendingLeap,
                  vtssPtpConfigClocksVirtualPortCfgLeapDate,
                  vtssPtpConfigClocksVirtualPortCfgLeapType,
                  vtssPtpConfigClocksVirtualPortCfgAlarm,
                  vtssPtpConfigClocksVirtualPortCfgClockIdentity,
                  vtssPtpConfigClocksVirtualPortCfgStepsRemoved }
    STATUS      current
    DESCRIPTION
        "A collection of objects."
    ::= { vtssPtpMibGroups 12 }

vtssPtpConfigCmldsPortDsTableInfoGroup OBJECT-GROUP
    OBJECTS     { vtssPtpConfigCmldsPortDsPortId,
                  vtssPtpConfigCmldsPortDsDelayAsymmetry,
                  vtssPtpConfigCmldsPortDsInitialLogPdelayReqInterval,
                  vtssPtpConfigCmldsPortDsUseMgtSettableLogPdelayReqInterval,
                  vtssPtpConfigCmldsPortDsMgtSettableLogPdelayReqInterval,
                  vtssPtpConfigCmldsPortDsInitialCompNbrRateRatio,
                  vtssPtpConfigCmldsPortDsUseMgtSetCompNbrRateRatio,
                  vtssPtpConfigCmldsPortDsMgtSetCompNbrRateRatio,
                  vtssPtpConfigCmldsPortDsInitialCompMeanLinkDelay,
                  vtssPtpConfigCmldsPortDsUseMgtSetCompMeanLinkDelay,
                  vtssPtpConfigCmldsPortDsMgtSetCompMeanLinkDelay,
                  vtssPtpConfigCmldsPortDsAllowedLostResponses,
                  vtssPtpConfigCmldsPortDsAllowedFaults,
                  vtssPtpConfigCmldsPortDsMeanLinkDelayThresh }
    STATUS      current
    DESCRIPTION
        "A collection of objects."
    ::= { vtssPtpMibGroups 13 }

vtssPtpStatusClocksDefaultDsTableInfoGroup OBJECT-GROUP
    OBJECTS     { vtssPtpStatusClocksDefaultDsClockId,
                  vtssPtpStatusClocksDefaultDsClockIdentity,
                  vtssPtpStatusClocksDefaultDsClockQualityClockClass,
                  vtssPtpStatusClocksDefaultDsClockQualityClockAccuracy,
                  vtssPtpStatusClocksDefaultDsClockQualityOffsetScaledLogVar,
                  vtssPtpStatusClocksDefaultDsS8021asGmCapable,
                  vtssPtpStatusClocksDefaultDsS8021asSdoId }
    STATUS      current
    DESCRIPTION
        "A collection of objects."
    ::= { vtssPtpMibGroups 14 }

vtssPtpStatusClocksCurrentDsTableInfoGroup OBJECT-GROUP
    OBJECTS     { vtssPtpStatusClocksCurrentDsClockId,
                  vtssPtpStatusClocksCurrentDsStepsRemoved,
                  vtssPtpStatusClocksCurrentDsOffsetFromMaster,
                  vtssPtpStatusClocksCurrentDsMeanPathDelay,
                  vtssPtpStatusClocksCurrentDsCur8021asLastGMPhaseChangeLow,
                  vtssPtpStatusClocksCurrentDsCur8021asLastGMPhaseChangeHigh,
                  vtssPtpStatusClocksCurrentDsCur8021asLastGMFreqChange,
                  vtssPtpStatusClocksCurrentDsCur8021asGmTimeBaseIndicator,
                  vtssPtpStatusClocksCurrentDsCur8021asGmChangeCount,
                  vtssPtpStatusClocksCurrentDsCur8021asTimeOfLastGMChangeEvt,
                  vtssPtpStatusClocksCurrentDsCur8021asTimeOfLastGMPhaseChangeEvt,
                  vtssPtpStatusClocksCurrentDsCur8021asTimeOfLastGMFreqChangeEvent }
    STATUS      current
    DESCRIPTION
        "A collection of objects."
    ::= { vtssPtpMibGroups 15 }

vtssPtpStatusClocksParentDsTableInfoGroup OBJECT-GROUP
    OBJECTS     { vtssPtpStatusClocksParentDsClockId,
                  vtssPtpStatusClocksParentDsParentPortIdentityClockIdentity,
                  vtssPtpStatusClocksParentDsParentPortIdentityPortNumber,
                  vtssPtpStatusClocksParentDsParentStats,
                  vtssPtpStatusClocksParentDsObservedParentOffsetScaledLogVar,
                  vtssPtpStatusClocksParentDsObservedParentClockPhaseChangeRate,
                  vtssPtpStatusClocksParentDsGrmstrIdentity,
                  vtssPtpStatusClocksParentDsGrmstrClkQualClockClass,
                  vtssPtpStatusClocksParentDsGmstrClkQualClockAccuracy,
                  vtssPtpStatusClocksParentDsGmstrClkQualOffsetScaledLogVar,
                  vtssPtpStatusClocksParentDsGmstrPriority1,
                  vtssPtpStatusClocksParentDsGmstrPriority2,
                  vtssPtpStatusClocksParentDsPar8021asCumulativeRateRatio }
    STATUS      current
    DESCRIPTION
        "A collection of objects."
    ::= { vtssPtpMibGroups 16 }

vtssPtpStatusClocksTimePropertiesDsTableInfoGroup OBJECT-GROUP
    OBJECTS     { vtssPtpStatusClocksTimePropertiesDsClockId,
                  vtssPtpStatusClocksTimePropertiesDsCurrentUtcOffset,
                  vtssPtpStatusClocksTimePropertiesDsCurrentUtcOffsetValid,
                  vtssPtpStatusClocksTimePropertiesDsLeap59,
                  vtssPtpStatusClocksTimePropertiesDsLeap61,
                  vtssPtpStatusClocksTimePropertiesDsTimeTraceable,
                  vtssPtpStatusClocksTimePropertiesDsFrequencyTraceable,
                  vtssPtpStatusClocksTimePropertiesDsPtpTimescale,
                  vtssPtpStatusClocksTimePropertiesDsTimeSource,
                  vtssPtpStatusClocksTimePropertiesDsPendingLeap,
                  vtssPtpStatusClocksTimePropertiesDsLeapDate,
                  vtssPtpStatusClocksTimePropertiesDsLeapType }
    STATUS      current
    DESCRIPTION
        "A collection of objects."
    ::= { vtssPtpMibGroups 17 }

vtssPtpStatusClocksSlaveDsTableInfoGroup OBJECT-GROUP
    OBJECTS     { vtssPtpStatusClocksSlaveDsClockId,
                  vtssPtpStatusClocksSlaveDsSlavePort,
                  vtssPtpStatusClocksSlaveDsSlaveState,
                  vtssPtpStatusClocksSlaveDsHoldoverStable,
                  vtssPtpStatusClocksSlaveDsHoldoverAdj }
    STATUS      current
    DESCRIPTION
        "A collection of objects."
    ::= { vtssPtpMibGroups 18 }

vtssPtpStatusClocksUnicastMasterTableInfoGroup OBJECT-GROUP
    OBJECTS     { vtssPtpStatusClocksUnicastMasterClockId,
                  vtssPtpStatusClocksUnicastMasterSlaveIp,
                  vtssPtpStatusClocksUnicastMasterSlaveMac,
                  vtssPtpStatusClocksUnicastMasterPort,
                  vtssPtpStatusClocksUnicastMasterAnnLogMsgPeriod,
                  vtssPtpStatusClocksUnicastMasterAnn,
                  vtssPtpStatusClocksUnicastMasterLogMsgPeriod,
                  vtssPtpStatusClocksUnicastMasterSync }
    STATUS      current
    DESCRIPTION
        "A collection of objects."
    ::= { vtssPtpMibGroups 19 }

vtssPtpStatusClocksUnicastSlaveTableInfoGroup OBJECT-GROUP
    OBJECTS     { vtssPtpStatusClocksUnicastSlaveClockId,
                  vtssPtpStatusClocksUnicastSlaveMasterId,
                  vtssPtpStatusClocksUnicastSlaveMasterIp,
                  vtssPtpStatusClocksUnicastSlaveMasterMac,
                  vtssPtpStatusClocksUnicastSlaveSourcePortIdentityClockIdentity,
                  vtssPtpStatusClocksUnicastSlaveSourcePortIdentityPortNumber,
                  vtssPtpStatusClocksUnicastSlavePort,
                  vtssPtpStatusClocksUnicastSlaveLogMsgPeriod,
                  vtssPtpStatusClocksUnicastSlaveCommState,
                  vtssPtpStatusClocksUnicastSlaveConfMasterIp }
    STATUS      current
    DESCRIPTION
        "A collection of objects."
    ::= { vtssPtpMibGroups 20 }

vtssPtpStatusClocksPortsDsTableInfoGroup OBJECT-GROUP
    OBJECTS     { vtssPtpStatusClocksPortsDsClockId,
                  vtssPtpStatusClocksPortsDsPortId,
                  vtssPtpStatusClocksPortsDsPortState,
                  vtssPtpStatusClocksPortsDsLogMinDelayReqInterval,
                  vtssPtpStatusClocksPortsDsPeerMeanPathDelay,
                  vtssPtpStatusClocksPortsDsPeerDelayOk,
                  vtssPtpStatusClocksPortsDsS8021asPortRole,
                  vtssPtpStatusClocksPortsDsS8021asIsMeasuringDelay,
                  vtssPtpStatusClocksPortsDsS8021asAsCapable,
                  vtssPtpStatusClocksPortsDsS8021asNeighborRateRatio,
                  vtssPtpStatusClocksPortsDsS8021asCurrentLogAnnounceInterval,
                  vtssPtpStatusClocksPortsDsS8021asCurrentLogSyncInterval,
                  vtssPtpStatusClocksPortsDsS8021asSyncReceiptTimeInterval,
                  vtssPtpStatusClocksPortsDsS8021asCurrentLogPDelayReqInterval,
                  vtssPtpStatusClocksPortsDsS8021asAcceptableMasterTableEnabled,
                  vtssPtpStatusClocksPortsDsS8021asVersionNumber,
                  vtssPtpStatusClocksPortsDsS8021asCurrentCompNbrRateRatio,
                  vtssPtpStatusClocksPortsDsS8021asCurrentCompMeanLinkDelay }
    STATUS      current
    DESCRIPTION
        "A collection of objects."
    ::= { vtssPtpMibGroups 21 }

vtssPtpStatusCmldsPortDsTableInfoGroup OBJECT-GROUP
    OBJECTS     { vtssPtpStatusCmldsPortDsPortIdentityPortNumber,
                  vtssPtpStatusCmldsPortDsPortIdentityClockIdentity,
                  vtssPtpStatusCmldsPortDsCmldsLinkPortEnabled,
                  vtssPtpStatusCmldsPortDsIsMeasuringDelay,
                  vtssPtpStatusCmldsPortDsAsCapableAcrossDomains,
                  vtssPtpStatusCmldsPortDsMeanLinkDelay,
                  vtssPtpStatusCmldsPortDsNeighborRateRatio,
                  vtssPtpStatusCmldsPortDsCurrentLogPDelayReqInterval,
                  vtssPtpStatusCmldsPortDsCurrentCompNbrRateRatio,
                  vtssPtpStatusCmldsPortDsCurrentCompMeanLinkDelay,
                  vtssPtpStatusCmldsPortDsVersionNumber,
                  vtssPtpStatusCmldsPortDsMinorVersionNumber }
    STATUS      current
    DESCRIPTION
        "A collection of objects."
    ::= { vtssPtpMibGroups 22 }

vtssPtpStatusCmldsDefaultDsTableInfoGroup OBJECT-GROUP
    OBJECTS     { vtssPtpStatusCmldsDefaultDsClockIdentity,
                  vtssPtpStatusCmldsDefaultDsNumberLinkPorts,
                  vtssPtpStatusCmldsDefaultDsSdoId }
    STATUS      current
    DESCRIPTION
        "A collection of objects."
    ::= { vtssPtpMibGroups 23 }

vtssPtpControlClocksTableInfoGroup OBJECT-GROUP
    OBJECTS     { vtssPtpControlClocksClockId,
                  vtssPtpControlClocksSyncToSystemClock }
    STATUS      current
    DESCRIPTION
        "A collection of objects."
    ::= { vtssPtpMibGroups 24 }

vtssPtpStatisticsClocksPortsDsTableInfoGroup OBJECT-GROUP
    OBJECTS     { vtssPtpStatisticsClocksPortsDsClockId,
                  vtssPtpStatisticsClocksPortsDsPortId,
                  vtssPtpStatisticsClocksPortsDsRxSyncCount,
                  vtssPtpStatisticsClocksPortsDsRxFollowUpCount,
                  vtssPtpStatisticsClocksPortsDsRxPdelayRequestCount,
                  vtssPtpStatisticsClocksPortsDsRxPdelayResponseCount,
                  vtssPtpStatisticsClocksPortsDsRxPdelayResponseFollowUpCount,
                  vtssPtpStatisticsClocksPortsDsRxAnnounceCount,
                  vtssPtpStatisticsClocksPortsDsRxPTPPacketDiscardCount,
                  vtssPtpStatisticsClocksPortsDsSyncReceiptTimeoutCount,
                  vtssPtpStatisticsClocksPortsDsAnnounceReceiptTimeoutCount,
                  vtssPtpStatisticsClocksPortsDsPdelayAllowedLostResExcCount,
                  vtssPtpStatisticsClocksPortsDsTxSyncCount,
                  vtssPtpStatisticsClocksPortsDsTxFollowUpCount,
                  vtssPtpStatisticsClocksPortsDsTxPdelayRequestCount,
                  vtssPtpStatisticsClocksPortsDsTxPdelayResponseCount,
                  vtssPtpStatisticsClocksPortsDsTxPdelayResponseFollowUpCount,
                  vtssPtpStatisticsClocksPortsDsTxAnnounceCount }
    STATUS      current
    DESCRIPTION
        "A collection of objects."
    ::= { vtssPtpMibGroups 25 }

vtssPtpStatisticsCmldsPortDsTableInfoGroup OBJECT-GROUP
    OBJECTS     {                   vtssPtpStatisticsCmldsPortDsPortIdentityPortNumber,
                  vtssPtpStatisticsCmldsPortDsRxPdelayRequestCount,
                  vtssPtpStatisticsCmldsPortDsRxPdelayResponseCount,
                  vtssPtpStatisticsCmldsPortDsRxPdelayResponseFollowUpCount,
                  vtssPtpStatisticsCmldsPortDsRxPTPPacketDiscardCount,
                  vtssPtpStatisticsCmldsPortDsPdelayAllowedLostResExcCount,
                  vtssPtpStatisticsCmldsPortDsTxPdelayRequestCount,
                  vtssPtpStatisticsCmldsPortDsTxPdelayResponseCount,
                  vtssPtpStatisticsCmldsPortDsTxPdelayResponseFollowUpCount }
    STATUS      current
    DESCRIPTION
        "A collection of objects."
    ::= { vtssPtpMibGroups 26 }

vtssPtpMibCompliance MODULE-COMPLIANCE
    STATUS      current
    DESCRIPTION
        "The compliance statement for the implementation."

    MODULE      -- this module

    MANDATORY-GROUPS { vtssPtpCapabilitiesGlobalsInfoGroup,
                       vtssPtpConfigGlobalsExternalClockModeInfoGroup,
                       vtssPtpConfigGlobalsSystemTimeSyncModeInfoGroup,
                       vtssPtpConfigClocksDefaultDsTableInfoGroup,
                       vtssPtpConfigClocksDefaultDsTableRowEditorInfoGroup,
                       vtssPtpConfigClocksTimePropertiesDsTableInfoGroup,
                       vtssPtpConfigClocksFilterParametersTableInfoGroup,
                       vtssPtpConfigClocksServoParametersTableInfoGroup,
                       vtssPtpConfigClocksSlaveConfigTableInfoGroup,
                       vtssPtpConfigClocksUnicastSlaveConfigTableInfoGroup,
                       vtssPtpConfigClocksPortDsTableInfoGroup,
                       vtssPtpConfigClocksVirtualPortCfgTableInfoGroup,
                       vtssPtpConfigCmldsPortDsTableInfoGroup,
                       vtssPtpStatusClocksDefaultDsTableInfoGroup,
                       vtssPtpStatusClocksCurrentDsTableInfoGroup,
                       vtssPtpStatusClocksParentDsTableInfoGroup,
                       vtssPtpStatusClocksTimePropertiesDsTableInfoGroup,
                       vtssPtpStatusClocksSlaveDsTableInfoGroup,
                       vtssPtpStatusClocksUnicastMasterTableInfoGroup,
                       vtssPtpStatusClocksUnicastSlaveTableInfoGroup,
                       vtssPtpStatusClocksPortsDsTableInfoGroup,
                       vtssPtpStatusCmldsPortDsTableInfoGroup,
                       vtssPtpStatusCmldsDefaultDsTableInfoGroup,
                       vtssPtpControlClocksTableInfoGroup,
                       vtssPtpStatisticsClocksPortsDsTableInfoGroup,
                       vtssPtpStatisticsCmldsPortDsTableInfoGroup }

    ::= { vtssPtpMibCompliances 1 }

END
