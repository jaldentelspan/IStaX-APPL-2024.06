-- *****************************************************************
-- VTSS-SMI:  Microsemi ENT structure
-- ****************************************************************

VTSS-SMI DEFINITIONS ::= BEGIN

IMPORTS
    MODULE-IDENTITY,
    OBJECT-IDENTITY,
    enterprises
        FROM SNMPv2-SMI;


vtss MODULE-IDENTITY
    LAST-UPDATED    "201309240000Z"
    ORGANIZATION    "Microsemi Corporation"
    CONTACT-INFO
            "Microsemi Corporation"
    DESCRIPTION
        "The Structure of Management Information for the
        Vitesse enterprise."
    REVISION        "201309240000Z"
    DESCRIPTION
        "Initial version of this MIB module."
    ::= { enterprises 6603 }


vtssSwitchMgmt OBJECT-IDENTITY
    STATUS          current
    DESCRIPTION
        "switchMgmt is the root OBJECT IDENTIFIER from
         which object id values are assigned."
    ::= { vtss 1 }



END
