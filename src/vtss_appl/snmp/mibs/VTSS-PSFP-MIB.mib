-- *****************************************************************
-- PSFP-MIB:  Microsemi ENT private MIB
-- ****************************************************************

VTSS-PSFP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Integer32 FROM SNMPv2-SMI
    Unsigned32 FROM SNMPv2-SMI
    TruthValue FROM SNMPv2-TC
    VTSSDisplayString FROM VTSS-TC
    VTSSRowEditorState FROM VTSS-TC
    VTSSTextualTimestamp FROM VTSS-TC
    VTSSUnsigned64 FROM VTSS-TC
    VTSSUnsigned8 FROM VTSS-TC
    ;

vtssPsfpMib MODULE-IDENTITY
    LAST-UPDATED "202402010000Z"
    ORGANIZATION
        "Microsemi Corporation"
    CONTACT-INFO
        "Application support: http://www.microchip.com/support"
    DESCRIPTION
        "Private MIB for Per-Stream Filtering and Policing, PSFP."
    REVISION    "202402010000Z"
    DESCRIPTION
        "Initial version"
    ::= { vtssSwitchMgmt 155 }


VTSSpsfpFlowMeterColorMode ::= TEXTUAL-CONVENTION
    STATUS      current
    DESCRIPTION
        "This enumeration defines the color awareness."
    SYNTAX      INTEGER { colorBlind(0), colorAware(1) }

VTSSpsfpGateState ::= TEXTUAL-CONVENTION
    STATUS      current
    DESCRIPTION
        "This enumeration defines the available PSFP Gate states."
    SYNTAX      INTEGER { closed(0), open(1) }

VTSSpsfpTimeUnit ::= TEXTUAL-CONVENTION
    STATUS      current
    DESCRIPTION
        "This enumeration defines the available PSFP time units."
    SYNTAX      INTEGER { ns(0), us(1), ms(2) }

vtssPsfpMibObjects OBJECT IDENTIFIER
    ::= { vtssPsfpMib 1 }

vtssPsfpCapabilities OBJECT IDENTIFIER
    ::= { vtssPsfpMibObjects 1 }

vtssPsfpCapabilitiesFilterInstanceCntMax OBJECT-TYPE
    SYNTAX      Unsigned32
    MAX-ACCESS  read-only
    STATUS      current
    DESCRIPTION
        "The FilterInstanceCntMax parameter defines the maximum number of stream
         filter instances that are supported by this Bridge component. These are
         numbered [0; max]."
    ::= { vtssPsfpCapabilities 1 }

vtssPsfpCapabilitiesGateInstanceCntMax OBJECT-TYPE
    SYNTAX      Unsigned32
    MAX-ACCESS  read-only
    STATUS      current
    DESCRIPTION
        "The GateInstanceCntMax parameter defines the maximum number of stream
         gate instances that are supported by this Bridge component. These are
         numbered [0; max[."
    ::= { vtssPsfpCapabilities 2 }

vtssPsfpCapabilitiesFlowMeterInstanceCntMax OBJECT-TYPE
    SYNTAX      Unsigned32
    MAX-ACCESS  read-only
    STATUS      current
    DESCRIPTION
        "The FlowMeterInstanceCntMax parameter defines the maximum number of
         flow meter instances that are supported by this Bridge component."
    ::= { vtssPsfpCapabilities 3 }

vtssPsfpCapabilitiesGateControlListLengthMax OBJECT-TYPE
    SYNTAX      Unsigned32
    MAX-ACCESS  read-only
    STATUS      current
    DESCRIPTION
        "The GclListSizeMax parameter defines the The maximum value supported by
         this Bridge component of the AdminControlListLength and
         OperControlListLength parameters."
    ::= { vtssPsfpCapabilities 4 }

vtssPsfpCapabilitiesStreamIdMax OBJECT-TYPE
    SYNTAX      Unsigned32
    MAX-ACCESS  read-only
    STATUS      current
    DESCRIPTION
        "Maximum value of a Stream ID."
    ::= { vtssPsfpCapabilities 5 }

vtssPsfpCapabilitiesStreamCollectionIdMax OBJECT-TYPE
    SYNTAX      Unsigned32
    MAX-ACCESS  read-only
    STATUS      current
    DESCRIPTION
        "Maximum value of a Stream Collection ID."
    ::= { vtssPsfpCapabilities 6 }

vtssPsfpCapabilitiesPsfpSupported OBJECT-TYPE
    SYNTAX      TruthValue
    MAX-ACCESS  read-only
    STATUS      current
    DESCRIPTION
        "Indicates whether PSFP is supported or not on this platform."
    ::= { vtssPsfpCapabilities 7 }

vtssPsfpConfig OBJECT IDENTIFIER
    ::= { vtssPsfpMibObjects 2 }

vtssPsfpConfigFlowMeterTable OBJECT-TYPE
    SYNTAX      SEQUENCE OF VTSSPsfpConfigFlowMeterEntry
    MAX-ACCESS  not-accessible
    STATUS      current
    DESCRIPTION
        "This table holds the configuration of PSFP flow meters"
    ::= { vtssPsfpConfig 1 }

vtssPsfpConfigFlowMeterEntry OBJECT-TYPE
    SYNTAX      VTSSPsfpConfigFlowMeterEntry
    MAX-ACCESS  not-accessible
    STATUS      current
    DESCRIPTION
        "Each index points to a given flow meter ID"
    INDEX       { vtssPsfpConfigFlowMeterFlowMeterId }
    ::= { vtssPsfpConfigFlowMeterTable 1 }

VTSSPsfpConfigFlowMeterEntry ::= SEQUENCE {
    vtssPsfpConfigFlowMeterFlowMeterId             Unsigned32,
    vtssPsfpConfigFlowMeterCIR                     Unsigned32,
    vtssPsfpConfigFlowMeterCBS                     Unsigned32,
    vtssPsfpConfigFlowMeterEIR                     Unsigned32,
    vtssPsfpConfigFlowMeterEBS                     Unsigned32,
    vtssPsfpConfigFlowMeterCF                      VTSSUnsigned8,
    vtssPsfpConfigFlowMeterCM                      VTSSpsfpFlowMeterColorMode,
    vtssPsfpConfigFlowMeterDropOnYellow            TruthValue,
    vtssPsfpConfigFlowMeterMarkAllFramesRedEnable  TruthValue,
    vtssPsfpConfigFlowMeterAction                  VTSSRowEditorState
}

vtssPsfpConfigFlowMeterFlowMeterId OBJECT-TYPE
    SYNTAX      Unsigned32
    MAX-ACCESS  accessible-for-notify
    STATUS      current
    DESCRIPTION
        "The ID of the Flow Meter instance"
    ::= { vtssPsfpConfigFlowMeterEntry 1 }

vtssPsfpConfigFlowMeterCIR OBJECT-TYPE
    SYNTAX      Unsigned32
    MAX-ACCESS  read-write
    STATUS      current
    DESCRIPTION
        "The CIR parameter contains an integer value that represents the CIR
         value for the flow meter, in kbit/s."
    ::= { vtssPsfpConfigFlowMeterEntry 2 }

vtssPsfpConfigFlowMeterCBS OBJECT-TYPE
    SYNTAX      Unsigned32
    MAX-ACCESS  read-write
    STATUS      current
    DESCRIPTION
        "The CBS parameter contains an integer value that represents the CBS
         value for the flow meter, in octets."
    ::= { vtssPsfpConfigFlowMeterEntry 3 }

vtssPsfpConfigFlowMeterEIR OBJECT-TYPE
    SYNTAX      Unsigned32
    MAX-ACCESS  read-write
    STATUS      current
    DESCRIPTION
        "The EIR parameter contains an integer value that represents the EIR
         value for the flow meter, in kbit/s."
    ::= { vtssPsfpConfigFlowMeterEntry 4 }

vtssPsfpConfigFlowMeterEBS OBJECT-TYPE
    SYNTAX      Unsigned32
    MAX-ACCESS  read-write
    STATUS      current
    DESCRIPTION
        "The EBS parameter contains an integer value that represents the EBS
         value for the flow meter, in octets."
    ::= { vtssPsfpConfigFlowMeterEntry 5 }

vtssPsfpConfigFlowMeterCF OBJECT-TYPE
    SYNTAX      VTSSUnsigned8
    MAX-ACCESS  read-write
    STATUS      current
    DESCRIPTION
        "The CF parameter contains an integer value that represents the CF value
         for the flow meter, as an integer value 0 or 1."
    ::= { vtssPsfpConfigFlowMeterEntry 6 }

vtssPsfpConfigFlowMeterCM OBJECT-TYPE
    SYNTAX      VTSSpsfpFlowMeterColorMode
    MAX-ACCESS  read-write
    STATUS      current
    DESCRIPTION
        "The CM parameter contains an integer value that represents the CM value
         for the flow meter, as an enumerated value indicating colorBlind or
         colorAware."
    ::= { vtssPsfpConfigFlowMeterEntry 7 }

vtssPsfpConfigFlowMeterDropOnYellow OBJECT-TYPE
    SYNTAX      TruthValue
    MAX-ACCESS  read-write
    STATUS      current
    DESCRIPTION
        "The DropOnYellow parameter contains a boolean value that indicates
         whether yellow frames are dropped (TRUE) or have DEI set to TRUE
         (FALSE)"
    ::= { vtssPsfpConfigFlowMeterEntry 8 }

vtssPsfpConfigFlowMeterMarkAllFramesRedEnable OBJECT-TYPE
    SYNTAX      TruthValue
    MAX-ACCESS  read-write
    STATUS      current
    DESCRIPTION
        "The MarkAllFramesRedEnable parameter contains a boolean value that
         indicates whether the MarkAllFramesRed function is enabled (TRUE) or
         disabled (FALSE)."
    ::= { vtssPsfpConfigFlowMeterEntry 9 }

vtssPsfpConfigFlowMeterAction OBJECT-TYPE
    SYNTAX      VTSSRowEditorState
    MAX-ACCESS  read-write
    STATUS      current
    DESCRIPTION
        "Action"
    ::= { vtssPsfpConfigFlowMeterEntry 100 }

vtssPsfpConfigFlowMeterRowEditor OBJECT IDENTIFIER
    ::= { vtssPsfpConfig 2 }

vtssPsfpConfigFlowMeterRowEditorFlowMeterId OBJECT-TYPE
    SYNTAX      Unsigned32
    MAX-ACCESS  read-write
    STATUS      current
    DESCRIPTION
        "The ID of the Flow Meter instance"
    ::= { vtssPsfpConfigFlowMeterRowEditor 1 }

vtssPsfpConfigFlowMeterRowEditorCIR OBJECT-TYPE
    SYNTAX      Unsigned32
    MAX-ACCESS  read-write
    STATUS      current
    DESCRIPTION
        "The CIR parameter contains an integer value that represents the CIR
         value for the flow meter, in kbit/s."
    ::= { vtssPsfpConfigFlowMeterRowEditor 2 }

vtssPsfpConfigFlowMeterRowEditorCBS OBJECT-TYPE
    SYNTAX      Unsigned32
    MAX-ACCESS  read-write
    STATUS      current
    DESCRIPTION
        "The CBS parameter contains an integer value that represents the CBS
         value for the flow meter, in octets."
    ::= { vtssPsfpConfigFlowMeterRowEditor 3 }

vtssPsfpConfigFlowMeterRowEditorEIR OBJECT-TYPE
    SYNTAX      Unsigned32
    MAX-ACCESS  read-write
    STATUS      current
    DESCRIPTION
        "The EIR parameter contains an integer value that represents the EIR
         value for the flow meter, in kbit/s."
    ::= { vtssPsfpConfigFlowMeterRowEditor 4 }

vtssPsfpConfigFlowMeterRowEditorEBS OBJECT-TYPE
    SYNTAX      Unsigned32
    MAX-ACCESS  read-write
    STATUS      current
    DESCRIPTION
        "The EBS parameter contains an integer value that represents the EBS
         value for the flow meter, in octets."
    ::= { vtssPsfpConfigFlowMeterRowEditor 5 }

vtssPsfpConfigFlowMeterRowEditorCF OBJECT-TYPE
    SYNTAX      VTSSUnsigned8
    MAX-ACCESS  read-write
    STATUS      current
    DESCRIPTION
        "The CF parameter contains an integer value that represents the CF value
         for the flow meter, as an integer value 0 or 1."
    ::= { vtssPsfpConfigFlowMeterRowEditor 6 }

vtssPsfpConfigFlowMeterRowEditorCM OBJECT-TYPE
    SYNTAX      VTSSpsfpFlowMeterColorMode
    MAX-ACCESS  read-write
    STATUS      current
    DESCRIPTION
        "The CM parameter contains an integer value that represents the CM value
         for the flow meter, as an enumerated value indicating colorBlind or
         colorAware."
    ::= { vtssPsfpConfigFlowMeterRowEditor 7 }

vtssPsfpConfigFlowMeterRowEditorDropOnYellow OBJECT-TYPE
    SYNTAX      TruthValue
    MAX-ACCESS  read-write
    STATUS      current
    DESCRIPTION
        "The DropOnYellow parameter contains a boolean value that indicates
         whether yellow frames are dropped (TRUE) or have DEI set to TRUE
         (FALSE)"
    ::= { vtssPsfpConfigFlowMeterRowEditor 8 }

vtssPsfpConfigFlowMeterRowEditorMarkAllFramesRedEnable OBJECT-TYPE
    SYNTAX      TruthValue
    MAX-ACCESS  read-write
    STATUS      current
    DESCRIPTION
        "The MarkAllFramesRedEnable parameter contains a boolean value that
         indicates whether the MarkAllFramesRed function is enabled (TRUE) or
         disabled (FALSE)."
    ::= { vtssPsfpConfigFlowMeterRowEditor 9 }

vtssPsfpConfigFlowMeterRowEditorAction OBJECT-TYPE
    SYNTAX      VTSSRowEditorState
    MAX-ACCESS  read-write
    STATUS      current
    DESCRIPTION
        "Action"
    ::= { vtssPsfpConfigFlowMeterRowEditor 100 }

vtssPsfpConfigGateTable OBJECT-TYPE
    SYNTAX      SEQUENCE OF VTSSPsfpConfigGateEntry
    MAX-ACCESS  not-accessible
    STATUS      current
    DESCRIPTION
        "Stream Gate configuration table"
    ::= { vtssPsfpConfig 3 }

vtssPsfpConfigGateEntry OBJECT-TYPE
    SYNTAX      VTSSPsfpConfigGateEntry
    MAX-ACCESS  not-accessible
    STATUS      current
    DESCRIPTION
        "Each index represents the configuration of one stream gate instance"
    INDEX       { vtssPsfpConfigGateGateId }
    ::= { vtssPsfpConfigGateTable 1 }

VTSSPsfpConfigGateEntry ::= SEQUENCE {
    vtssPsfpConfigGateGateId                              Unsigned32,
    vtssPsfpConfigGateAdminGateState                      VTSSpsfpGateState,
    vtssPsfpConfigGateAdminCycleTimeNumerator             Unsigned32,
    vtssPsfpConfigGateAdminCycleTimeUnit                  VTSSpsfpTimeUnit,
    vtssPsfpConfigGateAdminCycleTimeExtensionNumerator    Unsigned32,
    vtssPsfpConfigGateAdminCycleTimeExtensionUnit         VTSSpsfpTimeUnit,
    vtssPsfpConfigGateAdminBaseTimeTxt                    VTSSTextualTimestamp,
    vtssPsfpConfigGateAdminBaseTimeIso8601                VTSSDisplayString,
    vtssPsfpConfigGateAdminIpv                            Integer32,
    vtssPsfpConfigGateAdminCloseGateInvalidRxEnable       TruthValue,
    vtssPsfpConfigGateAdminCloseGateOctetsExceededEnable  TruthValue,
    vtssPsfpConfigGateAdminGclLength                      Unsigned32,
    vtssPsfpConfigGateAdminGce0GateState                  VTSSpsfpGateState,
    vtssPsfpConfigGateAdminGce0Ipv                        Integer32,
    vtssPsfpConfigGateAdminGce0TimeIntervalNumerator      Unsigned32,
    vtssPsfpConfigGateAdminGce0TimeIntervalUnit           VTSSpsfpTimeUnit,
    vtssPsfpConfigGateAdminGce0IntervalOctetMax           Unsigned32,
    vtssPsfpConfigGateAdminGce1GateState                  VTSSpsfpGateState,
    vtssPsfpConfigGateAdminGce1Ipv                        Integer32,
    vtssPsfpConfigGateAdminGce1TimeIntervalNumerator      Unsigned32,
    vtssPsfpConfigGateAdminGce1TimeIntervalUnit           VTSSpsfpTimeUnit,
    vtssPsfpConfigGateAdminGce1IntervalOctetMax           Unsigned32,
    vtssPsfpConfigGateAdminGce2GateState                  VTSSpsfpGateState,
    vtssPsfpConfigGateAdminGce2Ipv                        Integer32,
    vtssPsfpConfigGateAdminGce2TimeIntervalNumerator      Unsigned32,
    vtssPsfpConfigGateAdminGce2TimeIntervalUnit           VTSSpsfpTimeUnit,
    vtssPsfpConfigGateAdminGce2IntervalOctetMax           Unsigned32,
    vtssPsfpConfigGateAdminGce3GateState                  VTSSpsfpGateState,
    vtssPsfpConfigGateAdminGce3Ipv                        Integer32,
    vtssPsfpConfigGateAdminGce3TimeIntervalNumerator      Unsigned32,
    vtssPsfpConfigGateAdminGce3TimeIntervalUnit           VTSSpsfpTimeUnit,
    vtssPsfpConfigGateAdminGce3IntervalOctetMax           Unsigned32,
    vtssPsfpConfigGateAdminConfigChange                   TruthValue,
    vtssPsfpConfigGateAdminGateEnabled                    TruthValue,
    vtssPsfpConfigGateAction                              VTSSRowEditorState
}

vtssPsfpConfigGateGateId OBJECT-TYPE
    SYNTAX      Unsigned32
    MAX-ACCESS  accessible-for-notify
    STATUS      current
    DESCRIPTION
        "The ID of the Stream Gate instance"
    ::= { vtssPsfpConfigGateEntry 1 }

vtssPsfpConfigGateAdminGateState OBJECT-TYPE
    SYNTAX      VTSSpsfpGateState
    MAX-ACCESS  read-write
    STATUS      current
    DESCRIPTION
        "The administrative value of the GateState parameter for the stream
         gate. The open value indicates that the gate is open, the closed value
         indicates that the gate is closed."
    ::= { vtssPsfpConfigGateEntry 2 }

vtssPsfpConfigGateAdminCycleTimeNumerator OBJECT-TYPE
    SYNTAX      Unsigned32
    MAX-ACCESS  read-write
    STATUS      current
    DESCRIPTION
        "The numerator of the administrative value of the AdminCycleTime
         parameter measured in units of AdminCycleTimeUnit."
    ::= { vtssPsfpConfigGateEntry 3 }

vtssPsfpConfigGateAdminCycleTimeUnit OBJECT-TYPE
    SYNTAX      VTSSpsfpTimeUnit
    MAX-ACCESS  read-write
    STATUS      current
    DESCRIPTION
        "The denominator (units) of the administrative value of the
         AdminCycleTime parameter. Numerator in AdminCycleTimeNumerator."
    ::= { vtssPsfpConfigGateEntry 4 }

vtssPsfpConfigGateAdminCycleTimeExtensionNumerator OBJECT-TYPE
    SYNTAX      Unsigned32
    MAX-ACCESS  read-write
    STATUS      current
    DESCRIPTION
        "The numerator of the administrative value of the
         AdminCycleTimeExtension parameter measured in units of
         AdminCycleTimeExtensionUnit."
    ::= { vtssPsfpConfigGateEntry 5 }

vtssPsfpConfigGateAdminCycleTimeExtensionUnit OBJECT-TYPE
    SYNTAX      VTSSpsfpTimeUnit
    MAX-ACCESS  read-write
    STATUS      current
    DESCRIPTION
        "The denominator (units) of the administrative value of the
         AdminCycleTimeExtension parameter. Numerator in
         AdminCycleTimeExtensionNumerator."
    ::= { vtssPsfpConfigGateEntry 6 }

vtssPsfpConfigGateAdminBaseTimeTxt OBJECT-TYPE
    SYNTAX      VTSSTextualTimestamp
    MAX-ACCESS  read-write
    STATUS      current
    DESCRIPTION
        "The administrative value of the BaseTime parameter for the gate. The
         value is represented in the format sssssssssssssss[.sssssssss]"
    ::= { vtssPsfpConfigGateEntry 7 }

vtssPsfpConfigGateAdminBaseTimeIso8601 OBJECT-TYPE
    SYNTAX      VTSSDisplayString (SIZE(0..24))
    MAX-ACCESS  read-write
    STATUS      current
    DESCRIPTION
        "The administrative value of the BaseTime parameter for the gate, in ISO
         8601 format (YYYY-MM-DDTHH:mm:ss.SSSZ). This is only readable, not
         writable."
    ::= { vtssPsfpConfigGateEntry 8 }

vtssPsfpConfigGateAdminIpv OBJECT-TYPE
    SYNTAX      Integer32
    MAX-ACCESS  read-write
    STATUS      current
    DESCRIPTION
        "The administrative value of the IPV parameter for the gate. Set to -1
         in order not to map to a particular egress queue."
    ::= { vtssPsfpConfigGateEntry 9 }

vtssPsfpConfigGateAdminCloseGateInvalidRxEnable OBJECT-TYPE
    SYNTAX      TruthValue
    MAX-ACCESS  read-write
    STATUS      current
    DESCRIPTION
        "The CloseGateInvalidRxEnable object contains a boolean value that
         indicates whether the PSFPGateClosedInvalidRx function is enabled
         (TRUE) or disabled (FALSE)."
    ::= { vtssPsfpConfigGateEntry 10 }

vtssPsfpConfigGateAdminCloseGateOctetsExceededEnable OBJECT-TYPE
    SYNTAX      TruthValue
    MAX-ACCESS  read-write
    STATUS      current
    DESCRIPTION
        "The CloseGateOctetsExceededEnable object contains a boolean value that
         indicates whether the PSFPGateClosedOctetsExceeded function is enabled
         (TRUE) or disabled (FALSE)."
    ::= { vtssPsfpConfigGateEntry 11 }

vtssPsfpConfigGateAdminGclLength OBJECT-TYPE
    SYNTAX      Unsigned32
    MAX-ACCESS  read-write
    STATUS      current
    DESCRIPTION
        "The length of the GCL list."
    ::= { vtssPsfpConfigGateEntry 12 }

vtssPsfpConfigGateAdminGce0GateState OBJECT-TYPE
    SYNTAX      VTSSpsfpGateState
    MAX-ACCESS  read-write
    STATUS      current
    DESCRIPTION
        "The Gate Control entry's gate state. Default is closed."
    ::= { vtssPsfpConfigGateEntry 23 }

vtssPsfpConfigGateAdminGce0Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateEntry 24 }

vtssPsfpConfigGateAdminGce0TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateEntry 25 }

vtssPsfpConfigGateAdminGce0TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateEntry 26 }

vtssPsfpConfigGateAdminGce0IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateEntry 27 }

vtssPsfpConfigGateAdminGce1GateState OBJECT-TYPE
    SYNTAX      VTSSpsfpGateState
    MAX-ACCESS  read-write
    STATUS      current
    DESCRIPTION
        "The Gate Control entry's gate state. Default is closed."
    ::= { vtssPsfpConfigGateEntry 33 }

vtssPsfpConfigGateAdminGce1Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateEntry 34 }

vtssPsfpConfigGateAdminGce1TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateEntry 35 }

vtssPsfpConfigGateAdminGce1TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateEntry 36 }

vtssPsfpConfigGateAdminGce1IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateEntry 37 }

vtssPsfpConfigGateAdminGce2GateState OBJECT-TYPE
    SYNTAX      VTSSpsfpGateState
    MAX-ACCESS  read-write
    STATUS      current
    DESCRIPTION
        "The Gate Control entry's gate state. Default is closed."
    ::= { vtssPsfpConfigGateEntry 43 }

vtssPsfpConfigGateAdminGce2Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateEntry 44 }

vtssPsfpConfigGateAdminGce2TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateEntry 45 }

vtssPsfpConfigGateAdminGce2TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateEntry 46 }

vtssPsfpConfigGateAdminGce2IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateEntry 47 }

vtssPsfpConfigGateAdminGce3GateState OBJECT-TYPE
    SYNTAX      VTSSpsfpGateState
    MAX-ACCESS  read-write
    STATUS      current
    DESCRIPTION
        "The Gate Control entry's gate state. Default is closed."
    ::= { vtssPsfpConfigGateEntry 53 }

vtssPsfpConfigGateAdminGce3Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateEntry 54 }

vtssPsfpConfigGateAdminGce3TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateEntry 55 }

vtssPsfpConfigGateAdminGce3TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateEntry 56 }

vtssPsfpConfigGateAdminGce3IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateEntry 57 }

vtssPsfpConfigGateAdminConfigChange OBJECT-TYPE
    SYNTAX      TruthValue
    MAX-ACCESS  read-write
    STATUS      current
    DESCRIPTION
        "The ConfigChange parameter signals the start of a configuration change
         for the gate when it is set to TRUE. This should only be done when the
         various administrative parameters are all set to appropriate values."
    ::= { vtssPsfpConfigGateEntry 63 }

vtssPsfpConfigGateAdminGateEnabled OBJECT-TYPE
    SYNTAX      TruthValue
    MAX-ACCESS  read-write
    STATUS      current
    DESCRIPTION
        "The GateEnabled parameter determines whether the stream gate is active
         (true) or inactive (false)."
    ::= { vtssPsfpConfigGateEntry 64 }

vtssPsfpConfigGateAction OBJECT-TYPE
    SYNTAX      VTSSRowEditorState
    MAX-ACCESS  read-write
    STATUS      current
    DESCRIPTION
        "Action"
    ::= { vtssPsfpConfigGateEntry 200 }

vtssPsfpConfigGateRowEditor OBJECT IDENTIFIER
    ::= { vtssPsfpConfig 4 }

vtssPsfpConfigGateRowEditorGateId OBJECT-TYPE
    SYNTAX      Unsigned32
    MAX-ACCESS  read-write
    STATUS      current
    DESCRIPTION
        "The ID of the Stream Gate instance"
    ::= { vtssPsfpConfigGateRowEditor 1 }

vtssPsfpConfigGateRowEditorAdminGateState OBJECT-TYPE
    SYNTAX      VTSSpsfpGateState
    MAX-ACCESS  read-write
    STATUS      current
    DESCRIPTION
        "The administrative value of the GateState parameter for the stream
         gate. The open value indicates that the gate is open, the closed value
         indicates that the gate is closed."
    ::= { vtssPsfpConfigGateRowEditor 2 }

vtssPsfpConfigGateRowEditorAdminCycleTimeNumerator OBJECT-TYPE
    SYNTAX      Unsigned32
    MAX-ACCESS  read-write
    STATUS      current
    DESCRIPTION
        "The numerator of the administrative value of the AdminCycleTime
         parameter measured in units of AdminCycleTimeUnit."
    ::= { vtssPsfpConfigGateRowEditor 3 }

vtssPsfpConfigGateRowEditorAdminCycleTimeUnit OBJECT-TYPE
    SYNTAX      VTSSpsfpTimeUnit
    MAX-ACCESS  read-write
    STATUS      current
    DESCRIPTION
        "The denominator (units) of the administrative value of the
         AdminCycleTime parameter. Numerator in AdminCycleTimeNumerator."
    ::= { vtssPsfpConfigGateRowEditor 4 }

vtssPsfpConfigGateRowEditorAdminCycleTimeExtensionNumerator OBJECT-TYPE
    SYNTAX      Unsigned32
    MAX-ACCESS  read-write
    STATUS      current
    DESCRIPTION
        "The numerator of the administrative value of the
         AdminCycleTimeExtension parameter measured in units of
         AdminCycleTimeExtensionUnit."
    ::= { vtssPsfpConfigGateRowEditor 5 }

vtssPsfpConfigGateRowEditorAdminCycleTimeExtensionUnit OBJECT-TYPE
    SYNTAX      VTSSpsfpTimeUnit
    MAX-ACCESS  read-write
    STATUS      current
    DESCRIPTION
        "The denominator (units) of the administrative value of the
         AdminCycleTimeExtension parameter. Numerator in
         AdminCycleTimeExtensionNumerator."
    ::= { vtssPsfpConfigGateRowEditor 6 }

vtssPsfpConfigGateRowEditorAdminBaseTimeTxt OBJECT-TYPE
    SYNTAX      VTSSTextualTimestamp
    MAX-ACCESS  read-write
    STATUS      current
    DESCRIPTION
        "The administrative value of the BaseTime parameter for the gate. The
         value is represented in the format sssssssssssssss[.sssssssss]"
    ::= { vtssPsfpConfigGateRowEditor 7 }

vtssPsfpConfigGateRowEditorAdminBaseTimeIso8601 OBJECT-TYPE
    SYNTAX      VTSSDisplayString (SIZE(0..24))
    MAX-ACCESS  read-write
    STATUS      current
    DESCRIPTION
        "The administrative value of the BaseTime parameter for the gate, in ISO
         8601 format (YYYY-MM-DDTHH:mm:ss.SSSZ). This is only readable, not
         writable."
    ::= { vtssPsfpConfigGateRowEditor 8 }

vtssPsfpConfigGateRowEditorAdminIpv OBJECT-TYPE
    SYNTAX      Integer32
    MAX-ACCESS  read-write
    STATUS      current
    DESCRIPTION
        "The administrative value of the IPV parameter for the gate. Set to -1
         in order not to map to a particular egress queue."
    ::= { vtssPsfpConfigGateRowEditor 9 }

vtssPsfpConfigGateRowEditorAdminCloseGateInvalidRxEnable OBJECT-TYPE
    SYNTAX      TruthValue
    MAX-ACCESS  read-write
    STATUS      current
    DESCRIPTION
        "The CloseGateInvalidRxEnable object contains a boolean value that
         indicates whether the PSFPGateClosedInvalidRx function is enabled
         (TRUE) or disabled (FALSE)."
    ::= { vtssPsfpConfigGateRowEditor 10 }

vtssPsfpConfigGateRowEditorAdminCloseGateOctetsExceededEnable OBJECT-TYPE
    SYNTAX      TruthValue
    MAX-ACCESS  read-write
    STATUS      current
    DESCRIPTION
        "The CloseGateOctetsExceededEnable object contains a boolean value that
         indicates whether the PSFPGateClosedOctetsExceeded function is enabled
         (TRUE) or disabled (FALSE)."
    ::= { vtssPsfpConfigGateRowEditor 11 }

vtssPsfpConfigGateRowEditorAdminGclLength OBJECT-TYPE
    SYNTAX      Unsigned32
    MAX-ACCESS  read-write
    STATUS      current
    DESCRIPTION
        "The length of the GCL list."
    ::= { vtssPsfpConfigGateRowEditor 12 }

vtssPsfpConfigGateRowEditorAdminGce0GateState OBJECT-TYPE
    SYNTAX      VTSSpsfpGateState
    MAX-ACCESS  read-write
    STATUS      current
    DESCRIPTION
        "The Gate Control entry's gate state. Default is closed."
    ::= { vtssPsfpConfigGateRowEditor 23 }

vtssPsfpConfigGateRowEditorAdminGce0Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateRowEditor 24 }

vtssPsfpConfigGateRowEditorAdminGce0TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateRowEditor 25 }

vtssPsfpConfigGateRowEditorAdminGce0TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateRowEditor 26 }

vtssPsfpConfigGateRowEditorAdminGce0IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateRowEditor 27 }

vtssPsfpConfigGateRowEditorAdminGce1GateState OBJECT-TYPE
    SYNTAX      VTSSpsfpGateState
    MAX-ACCESS  read-write
    STATUS      current
    DESCRIPTION
        "The Gate Control entry's gate state. Default is closed."
    ::= { vtssPsfpConfigGateRowEditor 33 }

vtssPsfpConfigGateRowEditorAdminGce1Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateRowEditor 34 }

vtssPsfpConfigGateRowEditorAdminGce1TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateRowEditor 35 }

vtssPsfpConfigGateRowEditorAdminGce1TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateRowEditor 36 }

vtssPsfpConfigGateRowEditorAdminGce1IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateRowEditor 37 }

vtssPsfpConfigGateRowEditorAdminGce2GateState OBJECT-TYPE
    SYNTAX      VTSSpsfpGateState
    MAX-ACCESS  read-write
    STATUS      current
    DESCRIPTION
        "The Gate Control entry's gate state. Default is closed."
    ::= { vtssPsfpConfigGateRowEditor 43 }

vtssPsfpConfigGateRowEditorAdminGce2Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateRowEditor 44 }

vtssPsfpConfigGateRowEditorAdminGce2TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateRowEditor 45 }

vtssPsfpConfigGateRowEditorAdminGce2TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateRowEditor 46 }

vtssPsfpConfigGateRowEditorAdminGce2IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateRowEditor 47 }

vtssPsfpConfigGateRowEditorAdminGce3GateState OBJECT-TYPE
    SYNTAX      VTSSpsfpGateState
    MAX-ACCESS  read-write
    STATUS      current
    DESCRIPTION
        "The Gate Control entry's gate state. Default is closed."
    ::= { vtssPsfpConfigGateRowEditor 53 }

vtssPsfpConfigGateRowEditorAdminGce3Ipv OBJECT-TYPE
    SYNTAX      Integer32
    MAX-ACCESS  read-write
    STATUS      current
    DESCRIPTION
        "The internal priority value of the gate entry used to map frames to a
         particular egress queue. Set to -1 in order to map frames to their
         default egress queue."
    ::= { vtssPsfpConfigGateRowEditor 54 }

vtssPsfpConfigGateRowEditorAdminGce3TimeIntervalNumerator OBJECT-TYPE
    SYNTAX      Unsigned32
    MAX-ACCESS  read-write
    STATUS      current
    DESCRIPTION
        "The numerator of the gate entry's time interval parameter measured in
         units of this gate entry's TimeIntervalUnit."
    ::= { vtssPsfpConfigGateRowEditor 55 }

vtssPsfpConfigGateRowEditorAdminGce3TimeIntervalUnit OBJECT-TYPE
    SYNTAX      VTSSpsfpTimeUnit
    MAX-ACCESS  read-write
    STATUS      current
    DESCRIPTION
        "The denominator (units) of the gate entry's time interval parameter.
         Numerator in this gate entry's TimeIntervalNumerator."
    ::= { vtssPsfpConfigGateRowEditor 56 }

vtssPsfpConfigGateRowEditorAdminGce3IntervalOctetMax OBJECT-TYPE
    SYNTAX      Unsigned32
    MAX-ACCESS  read-write
    STATUS      current
    DESCRIPTION
        "Frames larger than this value are discarded by the Gate Control entry.
         Set to 0 to disable this check and let any frame size pass through."
    ::= { vtssPsfpConfigGateRowEditor 57 }

vtssPsfpConfigGateRowEditorAdminConfigChange OBJECT-TYPE
    SYNTAX      TruthValue
    MAX-ACCESS  read-write
    STATUS      current
    DESCRIPTION
        "The ConfigChange parameter signals the start of a configuration change
         for the gate when it is set to TRUE. This should only be done when the
         various administrative parameters are all set to appropriate values."
    ::= { vtssPsfpConfigGateRowEditor 63 }

vtssPsfpConfigGateRowEditorAdminGateEnabled OBJECT-TYPE
    SYNTAX      TruthValue
    MAX-ACCESS  read-write
    STATUS      current
    DESCRIPTION
        "The GateEnabled parameter determines whether the stream gate is active
         (true) or inactive (false)."
    ::= { vtssPsfpConfigGateRowEditor 64 }

vtssPsfpConfigGateRowEditorAction OBJECT-TYPE
    SYNTAX      VTSSRowEditorState
    MAX-ACCESS  read-write
    STATUS      current
    DESCRIPTION
        "Action"
    ::= { vtssPsfpConfigGateRowEditor 200 }

vtssPsfpConfigFilterTable OBJECT-TYPE
    SYNTAX      SEQUENCE OF VTSSPsfpConfigFilterEntry
    MAX-ACCESS  not-accessible
    STATUS      current
    DESCRIPTION
        "This table holds the configuration of PSFP stream filters"
    ::= { vtssPsfpConfig 5 }

vtssPsfpConfigFilterEntry OBJECT-TYPE
    SYNTAX      VTSSPsfpConfigFilterEntry
    MAX-ACCESS  not-accessible
    STATUS      current
    DESCRIPTION
        "Each index points to a given filter ID"
    INDEX       { vtssPsfpConfigFilterFilterId }
    ::= { vtssPsfpConfigFilterTable 1 }

VTSSPsfpConfigFilterEntry ::= SEQUENCE {
    vtssPsfpConfigFilterFilterId                       Unsigned32,
    vtssPsfpConfigFilterStreamId                       Unsigned32,
    vtssPsfpConfigFilterStreamCollectionId             Unsigned32,
    vtssPsfpConfigFilterFlowMeterId                    Unsigned32,
    vtssPsfpConfigFilterGateId                         Unsigned32,
    vtssPsfpConfigFilterMaxSDUSize                     Unsigned32,
    vtssPsfpConfigFilterBlockDueToOversizeFrameEnable  TruthValue,
    vtssPsfpConfigFilterAction                         VTSSRowEditorState
}

vtssPsfpConfigFilterFilterId OBJECT-TYPE
    SYNTAX      Unsigned32
    MAX-ACCESS  accessible-for-notify
    STATUS      current
    DESCRIPTION
        "The ID of the Stream Filter instance"
    ::= { vtssPsfpConfigFilterEntry 1 }

vtssPsfpConfigFilterStreamId OBJECT-TYPE
    SYNTAX      Unsigned32
    MAX-ACCESS  read-write
    STATUS      current
    DESCRIPTION
        "The StreamId parameter contains a stream identifier value. The filter
         is not attached to any stream if it is set to 0. For a filter to be
         operable, it must either be attached to a stream or to a stream
         collection."
    ::= { vtssPsfpConfigFilterEntry 2 }

vtssPsfpConfigFilterStreamCollectionId OBJECT-TYPE
    SYNTAX      Unsigned32
    MAX-ACCESS  read-write
    STATUS      current
    DESCRIPTION
        "The StreamCollectionId parameter contains a stream collection
         identifier value. The filter is not attached to any stream collection
         if it is set to 0. For a filter to be operable, it must either be
         attached to a stream or to a stream collection."
    ::= { vtssPsfpConfigFilterEntry 3 }

vtssPsfpConfigFilterFlowMeterId OBJECT-TYPE
    SYNTAX      Unsigned32
    MAX-ACCESS  read-write
    STATUS      current
    DESCRIPTION
        "The FlowMeterID parameter contains an index of an entry in the Flow
         Meter Table. If set to -1, no flow meters are used."
    ::= { vtssPsfpConfigFilterEntry 4 }

vtssPsfpConfigFilterGateId OBJECT-TYPE
    SYNTAX      Unsigned32
    MAX-ACCESS  read-write
    STATUS      current
    DESCRIPTION
        "The GateId parameter contains an index of an entry in the Stream Gate
         Table. If set to -1, no stream gates are used."
    ::= { vtssPsfpConfigFilterEntry 5 }

vtssPsfpConfigFilterMaxSDUSize OBJECT-TYPE
    SYNTAX      Unsigned32
    MAX-ACCESS  read-write
    STATUS      current
    DESCRIPTION
        "Maximum SDU size."
    ::= { vtssPsfpConfigFilterEntry 6 }

vtssPsfpConfigFilterBlockDueToOversizeFrameEnable OBJECT-TYPE
    SYNTAX      TruthValue
    MAX-ACCESS  read-write
    STATUS      current
    DESCRIPTION
        "If enabled and at least one frame has been discarded because it was
         longer than MaxSDUSize, all frames get discarded. This can be cleared
         with ClearBlockedDueToOversizeFrame."
    ::= { vtssPsfpConfigFilterEntry 7 }

vtssPsfpConfigFilterAction OBJECT-TYPE
    SYNTAX      VTSSRowEditorState
    MAX-ACCESS  read-write
    STATUS      current
    DESCRIPTION
        "Action"
    ::= { vtssPsfpConfigFilterEntry 100 }

vtssPsfpConfigFilterRowEditor OBJECT IDENTIFIER
    ::= { vtssPsfpConfig 6 }

vtssPsfpConfigFilterRowEditorFilterId OBJECT-TYPE
    SYNTAX      Unsigned32
    MAX-ACCESS  read-write
    STATUS      current
    DESCRIPTION
        "The ID of the Stream Filter instance"
    ::= { vtssPsfpConfigFilterRowEditor 1 }

vtssPsfpConfigFilterRowEditorStreamId OBJECT-TYPE
    SYNTAX      Unsigned32
    MAX-ACCESS  read-write
    STATUS      current
    DESCRIPTION
        "The StreamId parameter contains a stream identifier value. The filter
         is not attached to any stream if it is set to 0. For a filter to be
         operable, it must either be attached to a stream or to a stream
         collection."
    ::= { vtssPsfpConfigFilterRowEditor 2 }

vtssPsfpConfigFilterRowEditorStreamCollectionId OBJECT-TYPE
    SYNTAX      Unsigned32
    MAX-ACCESS  read-write
    STATUS      current
    DESCRIPTION
        "The StreamCollectionId parameter contains a stream collection
         identifier value. The filter is not attached to any stream collection
         if it is set to 0. For a filter to be operable, it must either be
         attached to a stream or to a stream collection."
    ::= { vtssPsfpConfigFilterRowEditor 3 }

vtssPsfpConfigFilterRowEditorFlowMeterId OBJECT-TYPE
    SYNTAX      Unsigned32
    MAX-ACCESS  read-write
    STATUS      current
    DESCRIPTION
        "The FlowMeterID parameter contains an index of an entry in the Flow
         Meter Table. If set to -1, no flow meters are used."
    ::= { vtssPsfpConfigFilterRowEditor 4 }

vtssPsfpConfigFilterRowEditorGateId OBJECT-TYPE
    SYNTAX      Unsigned32
    MAX-ACCESS  read-write
    STATUS      current
    DESCRIPTION
        "The GateId parameter contains an index of an entry in the Stream Gate
         Table. If set to -1, no stream gates are used."
    ::= { vtssPsfpConfigFilterRowEditor 5 }

vtssPsfpConfigFilterRowEditorMaxSDUSize OBJECT-TYPE
    SYNTAX      Unsigned32
    MAX-ACCESS  read-write
    STATUS      current
    DESCRIPTION
        "Maximum SDU size."
    ::= { vtssPsfpConfigFilterRowEditor 6 }

vtssPsfpConfigFilterRowEditorBlockDueToOversizeFrameEnable OBJECT-TYPE
    SYNTAX      TruthValue
    MAX-ACCESS  read-write
    STATUS      current
    DESCRIPTION
        "If enabled and at least one frame has been discarded because it was
         longer than MaxSDUSize, all frames get discarded. This can be cleared
         with ClearBlockedDueToOversizeFrame."
    ::= { vtssPsfpConfigFilterRowEditor 7 }

vtssPsfpConfigFilterRowEditorAction OBJECT-TYPE
    SYNTAX      VTSSRowEditorState
    MAX-ACCESS  read-write
    STATUS      current
    DESCRIPTION
        "Action"
    ::= { vtssPsfpConfigFilterRowEditor 100 }

vtssPsfpStatus OBJECT IDENTIFIER
    ::= { vtssPsfpMibObjects 3 }

vtssPsfpStatusFlowMeterTable OBJECT-TYPE
    SYNTAX      SEQUENCE OF VTSSPsfpStatusFlowMeterEntry
    MAX-ACCESS  not-accessible
    STATUS      current
    DESCRIPTION
        "PSFP Flow Meter status"
    ::= { vtssPsfpStatus 1 }

vtssPsfpStatusFlowMeterEntry OBJECT-TYPE
    SYNTAX      VTSSPsfpStatusFlowMeterEntry
    MAX-ACCESS  not-accessible
    STATUS      current
    DESCRIPTION
        "Each index points to a given flow meter ID"
    INDEX       { vtssPsfpStatusFlowMeterFlowMeterId }
    ::= { vtssPsfpStatusFlowMeterTable 1 }

VTSSPsfpStatusFlowMeterEntry ::= SEQUENCE {
    vtssPsfpStatusFlowMeterFlowMeterId       Unsigned32,
    vtssPsfpStatusFlowMeterMarkAllFramesRed  VTSSUnsigned8
}

vtssPsfpStatusFlowMeterFlowMeterId OBJECT-TYPE
    SYNTAX      Unsigned32
    MAX-ACCESS  accessible-for-notify
    STATUS      current
    DESCRIPTION
        "The ID of the Flow Meter instance"
    ::= { vtssPsfpStatusFlowMeterEntry 1 }

vtssPsfpStatusFlowMeterMarkAllFramesRed OBJECT-TYPE
    SYNTAX      VTSSUnsigned8
    MAX-ACCESS  read-only
    STATUS      current
    DESCRIPTION
        "The MarkAllFramesRed parameter contains a boolean value that indicates
         whether, if the MarkAllFramesRed function is enabled, all frames are to
         be discarded (TRUE) or not (FALSE)."
    ::= { vtssPsfpStatusFlowMeterEntry 2 }

vtssPsfpStatusGateTable OBJECT-TYPE
    SYNTAX      SEQUENCE OF VTSSPsfpStatusGateEntry
    MAX-ACCESS  not-accessible
    STATUS      current
    DESCRIPTION
        "PSFP Stream Gate status table"
    ::= { vtssPsfpStatus 2 }

vtssPsfpStatusGateEntry OBJECT-TYPE
    SYNTAX      VTSSPsfpStatusGateEntry
    MAX-ACCESS  not-accessible
    STATUS      current
    DESCRIPTION
        "Each index represents a stream gate instance"
    INDEX       { vtssPsfpStatusGateGateId }
    ::= { vtssPsfpStatusGateTable 1 }

VTSSPsfpStatusGateEntry ::= SEQUENCE {
    vtssPsfpStatusGateGateId                                 Unsigned32,
    vtssPsfpStatusGateOperConfValid                          TruthValue,
    vtssPsfpStatusGateOperConfGateState                      VTSSpsfpGateState,
    vtssPsfpStatusGateOperConfCycleTimeNumerator             Unsigned32,
    vtssPsfpStatusGateOperConfCycleTimeUnit                  VTSSpsfpTimeUnit,
    vtssPsfpStatusGateOperConfCycleTimeExtensionNumerator    Unsigned32,
    vtssPsfpStatusGateOperConfCycleTimeExtensionUnit         VTSSpsfpTimeUnit,
    vtssPsfpStatusGateOperConfBaseTimeTxt                    VTSSTextualTimestamp,
    vtssPsfpStatusGateOperConfBaseTimeIso8601                VTSSDisplayString,
    vtssPsfpStatusGateOperConfIpv                            Integer32,
    vtssPsfpStatusGateOperConfCloseGateInvalidRxEnable       TruthValue,
    vtssPsfpStatusGateOperConfCloseGateOctetsExceededEnable  TruthValue,
    vtssPsfpStatusGateOperConfGclLength                      Unsigned32,
    vtssPsfpStatusGateOperConfGce0GateState                  VTSSpsfpGateState,
    vtssPsfpStatusGateOperConfGce0Ipv                        Integer32,
    vtssPsfpStatusGateOperConfGce0TimeIntervalNumerator      Unsigned32,
    vtssPsfpStatusGateOperConfGce0TimeIntervalUnit           VTSSpsfpTimeUnit,
    vtssPsfpStatusGateOperConfGce0IntervalOctetMax           Unsigned32,
    vtssPsfpStatusGateOperConfGce1GateState                  VTSSpsfpGateState,
    vtssPsfpStatusGateOperConfGce1Ipv                        Integer32,
    vtssPsfpStatusGateOperConfGce1TimeIntervalNumerator      Unsigned32,
    vtssPsfpStatusGateOperConfGce1TimeIntervalUnit           VTSSpsfpTimeUnit,
    vtssPsfpStatusGateOperConfGce1IntervalOctetMax           Unsigned32,
    vtssPsfpStatusGateOperConfGce2GateState                  VTSSpsfpGateState,
    vtssPsfpStatusGateOperConfGce2Ipv                        Integer32,
    vtssPsfpStatusGateOperConfGce2TimeIntervalNumerator      Unsigned32,
    vtssPsfpStatusGateOperConfGce2TimeIntervalUnit           VTSSpsfpTimeUnit,
    vtssPsfpStatusGateOperConfGce2IntervalOctetMax           Unsigned32,
    vtssPsfpStatusGateOperConfGce3GateState                  VTSSpsfpGateState,
    vtssPsfpStatusGateOperConfGce3Ipv                        Integer32,
    vtssPsfpStatusGateOperConfGce3TimeIntervalNumerator      Unsigned32,
    vtssPsfpStatusGateOperConfGce3TimeIntervalUnit           VTSSpsfpTimeUnit,
    vtssPsfpStatusGateOperConfGce3IntervalOctetMax           Unsigned32,
    vtssPsfpStatusGateOperConfConfigChange                   TruthValue,
    vtssPsfpStatusGateOperConfGateEnabled                    TruthValue,
    vtssPsfpStatusGateConfigPending                          VTSSUnsigned8,
    vtssPsfpStatusGatePendConfGateState                      VTSSpsfpGateState,
    vtssPsfpStatusGatePendConfCycleTimeNumerator             Unsigned32,
    vtssPsfpStatusGatePendConfCycleTimeUnit                  VTSSpsfpTimeUnit,
    vtssPsfpStatusGatePendConfCycleTimeExtensionNumerator    Unsigned32,
    vtssPsfpStatusGatePendConfCycleTimeExtensionUnit         VTSSpsfpTimeUnit,
    vtssPsfpStatusGatePendConfBaseTimeTxt                    VTSSTextualTimestamp,
    vtssPsfpStatusGatePendConfBaseTimeIso8601                VTSSDisplayString,
    vtssPsfpStatusGatePendConfIpv                            Integer32,
    vtssPsfpStatusGatePendConfCloseGateInvalidRxEnable       TruthValue,
    vtssPsfpStatusGatePendConfCloseGateOctetsExceededEnable  TruthValue,
    vtssPsfpStatusGatePendConfGclLength                      Unsigned32,
    vtssPsfpStatusGatePendConfGce0GateState                  VTSSpsfpGateState,
    vtssPsfpStatusGatePendConfGce0Ipv                        Integer32,
    vtssPsfpStatusGatePendConfGce0TimeIntervalNumerator      Unsigned32,
    vtssPsfpStatusGatePendConfGce0TimeIntervalUnit           VTSSpsfpTimeUnit,
    vtssPsfpStatusGatePendConfGce0IntervalOctetMax           Unsigned32,
    vtssPsfpStatusGatePendConfGce1GateState                  VTSSpsfpGateState,
    vtssPsfpStatusGatePendConfGce1Ipv                        Integer32,
    vtssPsfpStatusGatePendConfGce1TimeIntervalNumerator      Unsigned32,
    vtssPsfpStatusGatePendConfGce1TimeIntervalUnit           VTSSpsfpTimeUnit,
    vtssPsfpStatusGatePendConfGce1IntervalOctetMax           Unsigned32,
    vtssPsfpStatusGatePendConfGce2GateState                  VTSSpsfpGateState,
    vtssPsfpStatusGatePendConfGce2Ipv                        Integer32,
    vtssPsfpStatusGatePendConfGce2TimeIntervalNumerator      Unsigned32,
    vtssPsfpStatusGatePendConfGce2TimeIntervalUnit           VTSSpsfpTimeUnit,
    vtssPsfpStatusGatePendConfGce2IntervalOctetMax           Unsigned32,
    vtssPsfpStatusGatePendConfGce3GateState                  VTSSpsfpGateState,
    vtssPsfpStatusGatePendConfGce3Ipv                        Integer32,
    vtssPsfpStatusGatePendConfGce3TimeIntervalNumerator      Unsigned32,
    vtssPsfpStatusGatePendConfGce3TimeIntervalUnit           VTSSpsfpTimeUnit,
    vtssPsfpStatusGatePendConfGce3IntervalOctetMax           Unsigned32,
    vtssPsfpStatusGatePendConfConfigChange                   TruthValue,
    vtssPsfpStatusGatePendConfGateEnabled                    TruthValue,
    vtssPsfpStatusGateOperGateState                          VTSSpsfpGateState,
    vtssPsfpStatusGateOperIpv                                Integer32,
    vtssPsfpStatusGateConfigChangeTimeTxt                    VTSSTextualTimestamp,
    vtssPsfpStatusGateConfigChangeTimeIso8601                VTSSDisplayString,
    vtssPsfpStatusGateCurrentTimeTxt                         VTSSTextualTimestamp,
    vtssPsfpStatusGateCurrentTimeIso8601                     VTSSDisplayString,
    vtssPsfpStatusGateTickGranularity                        Unsigned32,
    vtssPsfpStatusGateConfigChangeErrors                     Unsigned32,
    vtssPsfpStatusGateGateClosedDueToInvalidRx               VTSSUnsigned8,
    vtssPsfpStatusGateGateClosedDueToOctetsExceeded          VTSSUnsigned8
}

vtssPsfpStatusGateGateId OBJECT-TYPE
    SYNTAX      Unsigned32
    MAX-ACCESS  accessible-for-notify
    STATUS      current
    DESCRIPTION
        "The ID of the Stream Gate instance"
    ::= { vtssPsfpStatusGateEntry 1 }

vtssPsfpStatusGateOperConfValid OBJECT-TYPE
    SYNTAX      TruthValue
    MAX-ACCESS  read-only
    STATUS      current
    DESCRIPTION
        "Indicates whether the contentsof the operational configuration is
         valid."
    ::= { vtssPsfpStatusGateEntry 2 }

vtssPsfpStatusGateOperConfGateState OBJECT-TYPE
    SYNTAX      VTSSpsfpGateState
    MAX-ACCESS  read-only
    STATUS      current
    DESCRIPTION
        "The administrative value of the GateState parameter for the stream
         gate. The open value indicates that the gate is open, the closed value
         indicates that the gate is closed."
    ::= { vtssPsfpStatusGateEntry 3 }

vtssPsfpStatusGateOperConfCycleTimeNumerator OBJECT-TYPE
    SYNTAX      Unsigned32
    MAX-ACCESS  read-only
    STATUS      current
    DESCRIPTION
        "The numerator of the administrative value of the AdminCycleTime
         parameter measured in units of AdminCycleTimeUnit."
    ::= { vtssPsfpStatusGateEntry 4 }

vtssPsfpStatusGateOperConfCycleTimeUnit OBJECT-TYPE
    SYNTAX      VTSSpsfpTimeUnit
    MAX-ACCESS  read-only
    STATUS      current
    DESCRIPTION
        "The denominator (units) of the administrative value of the
         AdminCycleTime parameter. Numerator in AdminCycleTimeNumerator."
    ::= { vtssPsfpStatusGateEntry 5 }

vtssPsfpStatusGateOperConfCycleTimeExtensionNumerator OBJECT-TYPE
    SYNTAX      Unsigned32
    MAX-ACCESS  read-only
    STATUS      current
    DESCRIPTION
        "The numerator of the administrative value of the
         AdminCycleTimeExtension parameter measured in units of
         AdminCycleTimeExtensionUnit."
    ::= { vtssPsfpStatusGateEntry 6 }

vtssPsfpStatusGateOperConfCycleTimeExtensionUnit OBJECT-TYPE
    SYNTAX      VTSSpsfpTimeUnit
    MAX-ACCESS  read-only
    STATUS      current
    DESCRIPTION
        "The denominator (units) of the administrative value of the
         AdminCycleTimeExtension parameter. Numerator in
         AdminCycleTimeExtensionNumerator."
    ::= { vtssPsfpStatusGateEntry 7 }

vtssPsfpStatusGateOperConfBaseTimeTxt OBJECT-TYPE
    SYNTAX      VTSSTextualTimestamp
    MAX-ACCESS  read-only
    STATUS      current
    DESCRIPTION
        "The administrative value of the BaseTime parameter for the gate. The
         value is represented in the format sssssssssssssss[.sssssssss]"
    ::= { vtssPsfpStatusGateEntry 8 }

vtssPsfpStatusGateOperConfBaseTimeIso8601 OBJECT-TYPE
    SYNTAX      VTSSDisplayString (SIZE(0..24))
    MAX-ACCESS  read-only
    STATUS      current
    DESCRIPTION
        "The administrative value of the BaseTime parameter for the gate, in ISO
         8601 format (YYYY-MM-DDTHH:mm:ss.SSSZ). This is only readable, not
         writable."
    ::= { vtssPsfpStatusGateEntry 9 }

vtssPsfpStatusGateOperConfIpv OBJECT-TYPE
    SYNTAX      Integer32
    MAX-ACCESS  read-only
    STATUS      current
    DESCRIPTION
        "The administrative value of the IPV parameter for the gate. Set to -1
         in order not to map to a particular egress queue."
    ::= { vtssPsfpStatusGateEntry 10 }

vtssPsfpStatusGateOperConfCloseGateInvalidRxEnable OBJECT-TYPE
    SYNTAX      TruthValue
    MAX-ACCESS  read-only
    STATUS      current
    DESCRIPTION
        "The CloseGateInvalidRxEnable object contains a boolean value that
         indicates whether the PSFPGateClosedInvalidRx function is enabled
         (TRUE) or disabled (FALSE)."
    ::= { vtssPsfpStatusGateEntry 11 }

vtssPsfpStatusGateOperConfCloseGateOctetsExceededEnable OBJECT-TYPE
    SYNTAX      TruthValue
    MAX-ACCESS  read-only
    STATUS      current
    DESCRIPTION
        "The CloseGateOctetsExceededEnable object contains a boolean value that
         indicates whether the PSFPGateClosedOctetsExceeded function is enabled
         (TRUE) or disabled (FALSE)."
    ::= { vtssPsfpStatusGateEntry 12 }

vtssPsfpStatusGateOperConfGclLength OBJECT-TYPE
    SYNTAX      Unsigned32
    MAX-ACCESS  read-only
    STATUS      current
    DESCRIPTION
        "The length of the GCL list."
    ::= { vtssPsfpStatusGateEntry 13 }

vtssPsfpStatusGateOperConfGce0GateState OBJECT-TYPE
    SYNTAX      VTSSpsfpGateState
    MAX-ACCESS  read-only
    STATUS      current
    DESCRIPTION
        "The Gate Control entry's gate state. Default is closed."
    ::= { vtssPsfpStatusGateEntry 24 }

vtssPsfpStatusGateOperConfGce0Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 25 }

vtssPsfpStatusGateOperConfGce0TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 26 }

vtssPsfpStatusGateOperConfGce0TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 27 }

vtssPsfpStatusGateOperConfGce0IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 28 }

vtssPsfpStatusGateOperConfGce1GateState OBJECT-TYPE
    SYNTAX      VTSSpsfpGateState
    MAX-ACCESS  read-only
    STATUS      current
    DESCRIPTION
        "The Gate Control entry's gate state. Default is closed."
    ::= { vtssPsfpStatusGateEntry 34 }

vtssPsfpStatusGateOperConfGce1Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 35 }

vtssPsfpStatusGateOperConfGce1TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 36 }

vtssPsfpStatusGateOperConfGce1TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 37 }

vtssPsfpStatusGateOperConfGce1IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 38 }

vtssPsfpStatusGateOperConfGce2GateState OBJECT-TYPE
    SYNTAX      VTSSpsfpGateState
    MAX-ACCESS  read-only
    STATUS      current
    DESCRIPTION
        "The Gate Control entry's gate state. Default is closed."
    ::= { vtssPsfpStatusGateEntry 44 }

vtssPsfpStatusGateOperConfGce2Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 45 }

vtssPsfpStatusGateOperConfGce2TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 46 }

vtssPsfpStatusGateOperConfGce2TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 47 }

vtssPsfpStatusGateOperConfGce2IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 48 }

vtssPsfpStatusGateOperConfGce3GateState OBJECT-TYPE
    SYNTAX      VTSSpsfpGateState
    MAX-ACCESS  read-only
    STATUS      current
    DESCRIPTION
        "The Gate Control entry's gate state. Default is closed."
    ::= { vtssPsfpStatusGateEntry 54 }

vtssPsfpStatusGateOperConfGce3Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 55 }

vtssPsfpStatusGateOperConfGce3TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 56 }

vtssPsfpStatusGateOperConfGce3TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 57 }

vtssPsfpStatusGateOperConfGce3IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 58 }

vtssPsfpStatusGateOperConfConfigChange OBJECT-TYPE
    SYNTAX      TruthValue
    MAX-ACCESS  read-only
    STATUS      current
    DESCRIPTION
        "The ConfigChange parameter signals the start of a configuration change
         for the gate when it is set to TRUE. This should only be done when the
         various administrative parameters are all set to appropriate values."
    ::= { vtssPsfpStatusGateEntry 64 }

vtssPsfpStatusGateOperConfGateEnabled OBJECT-TYPE
    SYNTAX      TruthValue
    MAX-ACCESS  read-only
    STATUS      current
    DESCRIPTION
        "The GateEnabled parameter determines whether the stream gate is active
         (true) or inactive (false)."
    ::= { vtssPsfpStatusGateEntry 65 }

vtssPsfpStatusGateConfigPending OBJECT-TYPE
    SYNTAX      VTSSUnsigned8
    MAX-ACCESS  read-only
    STATUS      current
    DESCRIPTION
        "The value of the ConfigPending state machine variable. The value is
         TRUE if a configuration change is in progress but has not yet
         completed."
    ::= { vtssPsfpStatusGateEntry 66 }

vtssPsfpStatusGatePendConfGateState OBJECT-TYPE
    SYNTAX      VTSSpsfpGateState
    MAX-ACCESS  read-only
    STATUS      current
    DESCRIPTION
        "The administrative value of the GateState parameter for the stream
         gate. The open value indicates that the gate is open, the closed value
         indicates that the gate is closed."
    ::= { vtssPsfpStatusGateEntry 67 }

vtssPsfpStatusGatePendConfCycleTimeNumerator OBJECT-TYPE
    SYNTAX      Unsigned32
    MAX-ACCESS  read-only
    STATUS      current
    DESCRIPTION
        "The numerator of the administrative value of the AdminCycleTime
         parameter measured in units of AdminCycleTimeUnit."
    ::= { vtssPsfpStatusGateEntry 68 }

vtssPsfpStatusGatePendConfCycleTimeUnit OBJECT-TYPE
    SYNTAX      VTSSpsfpTimeUnit
    MAX-ACCESS  read-only
    STATUS      current
    DESCRIPTION
        "The denominator (units) of the administrative value of the
         AdminCycleTime parameter. Numerator in AdminCycleTimeNumerator."
    ::= { vtssPsfpStatusGateEntry 69 }

vtssPsfpStatusGatePendConfCycleTimeExtensionNumerator OBJECT-TYPE
    SYNTAX      Unsigned32
    MAX-ACCESS  read-only
    STATUS      current
    DESCRIPTION
        "The numerator of the administrative value of the
         AdminCycleTimeExtension parameter measured in units of
         AdminCycleTimeExtensionUnit."
    ::= { vtssPsfpStatusGateEntry 70 }

vtssPsfpStatusGatePendConfCycleTimeExtensionUnit OBJECT-TYPE
    SYNTAX      VTSSpsfpTimeUnit
    MAX-ACCESS  read-only
    STATUS      current
    DESCRIPTION
        "The denominator (units) of the administrative value of the
         AdminCycleTimeExtension parameter. Numerator in
         AdminCycleTimeExtensionNumerator."
    ::= { vtssPsfpStatusGateEntry 71 }

vtssPsfpStatusGatePendConfBaseTimeTxt OBJECT-TYPE
    SYNTAX      VTSSTextualTimestamp
    MAX-ACCESS  read-only
    STATUS      current
    DESCRIPTION
        "The administrative value of the BaseTime parameter for the gate. The
         value is represented in the format sssssssssssssss[.sssssssss]"
    ::= { vtssPsfpStatusGateEntry 72 }

vtssPsfpStatusGatePendConfBaseTimeIso8601 OBJECT-TYPE
    SYNTAX      VTSSDisplayString (SIZE(0..24))
    MAX-ACCESS  read-only
    STATUS      current
    DESCRIPTION
        "The administrative value of the BaseTime parameter for the gate, in ISO
         8601 format (YYYY-MM-DDTHH:mm:ss.SSSZ). This is only readable, not
         writable."
    ::= { vtssPsfpStatusGateEntry 73 }

vtssPsfpStatusGatePendConfIpv OBJECT-TYPE
    SYNTAX      Integer32
    MAX-ACCESS  read-only
    STATUS      current
    DESCRIPTION
        "The administrative value of the IPV parameter for the gate. Set to -1
         in order not to map to a particular egress queue."
    ::= { vtssPsfpStatusGateEntry 74 }

vtssPsfpStatusGatePendConfCloseGateInvalidRxEnable OBJECT-TYPE
    SYNTAX      TruthValue
    MAX-ACCESS  read-only
    STATUS      current
    DESCRIPTION
        "The CloseGateInvalidRxEnable object contains a boolean value that
         indicates whether the PSFPGateClosedInvalidRx function is enabled
         (TRUE) or disabled (FALSE)."
    ::= { vtssPsfpStatusGateEntry 75 }

vtssPsfpStatusGatePendConfCloseGateOctetsExceededEnable OBJECT-TYPE
    SYNTAX      TruthValue
    MAX-ACCESS  read-only
    STATUS      current
    DESCRIPTION
        "The CloseGateOctetsExceededEnable object contains a boolean value that
         indicates whether the PSFPGateClosedOctetsExceeded function is enabled
         (TRUE) or disabled (FALSE)."
    ::= { vtssPsfpStatusGateEntry 76 }

vtssPsfpStatusGatePendConfGclLength OBJECT-TYPE
    SYNTAX      Unsigned32
    MAX-ACCESS  read-only
    STATUS      current
    DESCRIPTION
        "The length of the GCL list."
    ::= { vtssPsfpStatusGateEntry 77 }

vtssPsfpStatusGatePendConfGce0GateState OBJECT-TYPE
    SYNTAX      VTSSpsfpGateState
    MAX-ACCESS  read-only
    STATUS      current
    DESCRIPTION
        "The Gate Control entry's gate state. Default is closed."
    ::= { vtssPsfpStatusGateEntry 88 }

vtssPsfpStatusGatePendConfGce0Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 89 }

vtssPsfpStatusGatePendConfGce0TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 90 }

vtssPsfpStatusGatePendConfGce0TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 91 }

vtssPsfpStatusGatePendConfGce0IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 92 }

vtssPsfpStatusGatePendConfGce1GateState OBJECT-TYPE
    SYNTAX      VTSSpsfpGateState
    MAX-ACCESS  read-only
    STATUS      current
    DESCRIPTION
        "The Gate Control entry's gate state. Default is closed."
    ::= { vtssPsfpStatusGateEntry 98 }

vtssPsfpStatusGatePendConfGce1Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 99 }

vtssPsfpStatusGatePendConfGce1TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 100 }

vtssPsfpStatusGatePendConfGce1TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 101 }

vtssPsfpStatusGatePendConfGce1IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 102 }

vtssPsfpStatusGatePendConfGce2GateState OBJECT-TYPE
    SYNTAX      VTSSpsfpGateState
    MAX-ACCESS  read-only
    STATUS      current
    DESCRIPTION
        "The Gate Control entry's gate state. Default is closed."
    ::= { vtssPsfpStatusGateEntry 108 }

vtssPsfpStatusGatePendConfGce2Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 109 }

vtssPsfpStatusGatePendConfGce2TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 110 }

vtssPsfpStatusGatePendConfGce2TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 111 }

vtssPsfpStatusGatePendConfGce2IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 112 }

vtssPsfpStatusGatePendConfGce3GateState OBJECT-TYPE
    SYNTAX      VTSSpsfpGateState
    MAX-ACCESS  read-only
    STATUS      current
    DESCRIPTION
        "The Gate Control entry's gate state. Default is closed."
    ::= { vtssPsfpStatusGateEntry 118 }

vtssPsfpStatusGatePendConfGce3Ipv OBJECT-TYPE
    SYNTAX      Integer32
    MAX-ACCESS  read-only
    STATUS      current
    DESCRIPTION
        "The internal priority value of the gate entry used to map frames to a
         particular egress queue. Set to -1 in order to map frames to their
         default egress queue."
    ::= { vtssPsfpStatusGateEntry 119 }

vtssPsfpStatusGatePendConfGce3TimeIntervalNumerator OBJECT-TYPE
    SYNTAX      Unsigned32
    MAX-ACCESS  read-only
    STATUS      current
    DESCRIPTION
        "The numerator of the gate entry's time interval parameter measured in
         units of this gate entry's TimeIntervalUnit."
    ::= { vtssPsfpStatusGateEntry 120 }

vtssPsfpStatusGatePendConfGce3TimeIntervalUnit OBJECT-TYPE
    SYNTAX      VTSSpsfpTimeUnit
    MAX-ACCESS  read-only
    STATUS      current
    DESCRIPTION
        "The denominator (units) of the gate entry's time interval parameter.
         Numerator in this gate entry's TimeIntervalNumerator."
    ::= { vtssPsfpStatusGateEntry 121 }

vtssPsfpStatusGatePendConfGce3IntervalOctetMax OBJECT-TYPE
    SYNTAX      Unsigned32
    MAX-ACCESS  read-only
    STATUS      current
    DESCRIPTION
        "Frames larger than this value are discarded by the Gate Control entry.
         Set to 0 to disable this check and let any frame size pass through."
    ::= { vtssPsfpStatusGateEntry 122 }

vtssPsfpStatusGatePendConfConfigChange OBJECT-TYPE
    SYNTAX      TruthValue
    MAX-ACCESS  read-only
    STATUS      current
    DESCRIPTION
        "The ConfigChange parameter signals the start of a configuration change
         for the gate when it is set to TRUE. This should only be done when the
         various administrative parameters are all set to appropriate values."
    ::= { vtssPsfpStatusGateEntry 128 }

vtssPsfpStatusGatePendConfGateEnabled OBJECT-TYPE
    SYNTAX      TruthValue
    MAX-ACCESS  read-only
    STATUS      current
    DESCRIPTION
        "The GateEnabled parameter determines whether the stream gate is active
         (true) or inactive (false)."
    ::= { vtssPsfpStatusGateEntry 129 }

vtssPsfpStatusGateOperGateState OBJECT-TYPE
    SYNTAX      VTSSpsfpGateState
    MAX-ACCESS  read-only
    STATUS      current
    DESCRIPTION
        "The operational value of the GateState parameter for the stream gate."
    ::= { vtssPsfpStatusGateEntry 130 }

vtssPsfpStatusGateOperIpv OBJECT-TYPE
    SYNTAX      Integer32
    MAX-ACCESS  read-only
    STATUS      current
    DESCRIPTION
        "The operational value of the IPV parameter for the gate. -1 if
         disabled."
    ::= { vtssPsfpStatusGateEntry 131 }

vtssPsfpStatusGateConfigChangeTimeTxt OBJECT-TYPE
    SYNTAX      VTSSTextualTimestamp
    MAX-ACCESS  read-only
    STATUS      current
    DESCRIPTION
        "If ConfigPending, the time at which the next config change is scheduled
         to occur. If not ConfigPending, the time at which the last config
         change occurred. The value is represented in the format
         sssssssssssssss[.sssssssss]."
    ::= { vtssPsfpStatusGateEntry 132 }

vtssPsfpStatusGateConfigChangeTimeIso8601 OBJECT-TYPE
    SYNTAX      VTSSDisplayString (SIZE(0..24))
    MAX-ACCESS  read-only
    STATUS      current
    DESCRIPTION
        "If ConfigPending, the time at which the next config change is scheduled
         to occur. If not ConfigPending, the time at which the last config
         change occurred. The value is in ISO 8601 format
         (YYYY-MM-DDTHH:mm:ss.SSSZ)."
    ::= { vtssPsfpStatusGateEntry 133 }

vtssPsfpStatusGateCurrentTimeTxt OBJECT-TYPE
    SYNTAX      VTSSTextualTimestamp
    MAX-ACCESS  read-only
    STATUS      current
    DESCRIPTION
        "The current time as maintained by the local system. The value is
         represented in the format sssssssssssssss[.sssssssss]"
    ::= { vtssPsfpStatusGateEntry 134 }

vtssPsfpStatusGateCurrentTimeIso8601 OBJECT-TYPE
    SYNTAX      VTSSDisplayString (SIZE(0..24))
    MAX-ACCESS  read-only
    STATUS      current
    DESCRIPTION
        "The current time as maintained by the local system. The value is in ISO
         8601 format (YYYY-MM-DDTHH:mm:ss.SSSZ)."
    ::= { vtssPsfpStatusGateEntry 135 }

vtssPsfpStatusGateTickGranularity OBJECT-TYPE
    SYNTAX      Unsigned32
    MAX-ACCESS  read-only
    STATUS      current
    DESCRIPTION
        "The granularity of the cycle time clock, represented as an unsigned
         number of tenths of nanoseconds."
    ::= { vtssPsfpStatusGateEntry 136 }

vtssPsfpStatusGateConfigChangeErrors OBJECT-TYPE
    SYNTAX      Unsigned32
    MAX-ACCESS  read-only
    STATUS      current
    DESCRIPTION
        "A counter of the number of times that a re-configuration of the traffic
         schedule has been requested with the old schedule still running and the
         requested base time was in the past."
    ::= { vtssPsfpStatusGateEntry 137 }

vtssPsfpStatusGateGateClosedDueToInvalidRx OBJECT-TYPE
    SYNTAX      VTSSUnsigned8
    MAX-ACCESS  read-only
    STATUS      current
    DESCRIPTION
        "The GateClosedDueToInvalidRx object contains a boolean value that
         indicates whether, if the PSFPGateClosedDueToInvalidRx function is
         enabled, all frames are to be discarded (TRUE) or not (FALSE)"
    ::= { vtssPsfpStatusGateEntry 138 }

vtssPsfpStatusGateGateClosedDueToOctetsExceeded OBJECT-TYPE
    SYNTAX      VTSSUnsigned8
    MAX-ACCESS  read-only
    STATUS      current
    DESCRIPTION
        "The GateClosedDueToOctetsExceeded parameter contains a boolean value
         that indicates whether, if the PSFPGateClosedDueToOctetsExceeded
         function is enabled, all frames are to be discarded (TRUE) or not
         (FALSE)."
    ::= { vtssPsfpStatusGateEntry 139 }

vtssPsfpStatusFilterTable OBJECT-TYPE
    SYNTAX      SEQUENCE OF VTSSPsfpStatusFilterEntry
    MAX-ACCESS  not-accessible
    STATUS      current
    DESCRIPTION
        "This table holds the status of PSFP stream filters"
    ::= { vtssPsfpStatus 3 }

vtssPsfpStatusFilterEntry OBJECT-TYPE
    SYNTAX      VTSSPsfpStatusFilterEntry
    MAX-ACCESS  not-accessible
    STATUS      current
    DESCRIPTION
        "Each index points to a given filter ID"
    INDEX       { vtssPsfpStatusFilterFilterId }
    ::= { vtssPsfpStatusFilterTable 1 }

VTSSPsfpStatusFilterEntry ::= SEQUENCE {
    vtssPsfpStatusFilterFilterId                                 Unsigned32,
    vtssPsfpStatusFilterBlockedDueToOversizeFrame                TruthValue,
    vtssPsfpStatusFilterWarningNone                              TruthValue,
    vtssPsfpStatusFilterWarningNoStreamOrStreamCollection        TruthValue,
    vtssPsfpStatusFilterWarningStreamNotFound                    TruthValue,
    vtssPsfpStatusFilterWarningStreamCollectionNotFound          TruthValue,
    vtssPsfpStatusFilterWarningStreamAttachFail                  TruthValue,
    vtssPsfpStatusFilterWarningStreamCollectionAttachFail        TruthValue,
    vtssPsfpStatusFilterWarningStreamHasConfigurationalWarnings  TruthValue,
    vtssPsfpStatusFilterWarningStreamCollectionHasConfWarnings   TruthValue,
    vtssPsfpStatusFilterWarningFlowMeterNotFound                 TruthValue,
    vtssPsfpStatusFilterWarningGateNotFound                      TruthValue,
    vtssPsfpStatusFilterWarningGateNotEnabled                    TruthValue
}

vtssPsfpStatusFilterFilterId OBJECT-TYPE
    SYNTAX      Unsigned32
    MAX-ACCESS  accessible-for-notify
    STATUS      current
    DESCRIPTION
        "The ID of the Stream Filter instance"
    ::= { vtssPsfpStatusFilterEntry 1 }

vtssPsfpStatusFilterBlockedDueToOversizeFrame OBJECT-TYPE
    SYNTAX      TruthValue
    MAX-ACCESS  read-only
    STATUS      current
    DESCRIPTION
        "If feature is enabled, and this is true and an oversize frame is
         received, the stream filter will discard all subsequent frames as well,
         until cleared."
    ::= { vtssPsfpStatusFilterEntry 2 }

vtssPsfpStatusFilterWarningNone OBJECT-TYPE
    SYNTAX      TruthValue
    MAX-ACCESS  read-only
    STATUS      current
    DESCRIPTION
        "No warnings found."
    ::= { vtssPsfpStatusFilterEntry 3 }

vtssPsfpStatusFilterWarningNoStreamOrStreamCollection OBJECT-TYPE
    SYNTAX      TruthValue
    MAX-ACCESS  read-only
    STATUS      current
    DESCRIPTION
        "Neither a stream or a stream collection is specified."
    ::= { vtssPsfpStatusFilterEntry 4 }

vtssPsfpStatusFilterWarningStreamNotFound OBJECT-TYPE
    SYNTAX      TruthValue
    MAX-ACCESS  read-only
    STATUS      current
    DESCRIPTION
        "The specified stream ID does not exist."
    ::= { vtssPsfpStatusFilterEntry 5 }

vtssPsfpStatusFilterWarningStreamCollectionNotFound OBJECT-TYPE
    SYNTAX      TruthValue
    MAX-ACCESS  read-only
    STATUS      current
    DESCRIPTION
        "The specified stream collection ID does not exist."
    ::= { vtssPsfpStatusFilterEntry 6 }

vtssPsfpStatusFilterWarningStreamAttachFail OBJECT-TYPE
    SYNTAX      TruthValue
    MAX-ACCESS  read-only
    STATUS      current
    DESCRIPTION
        "Unable to attach to the specified stream, possibly because it is part
         of a stream collection"
    ::= { vtssPsfpStatusFilterEntry 7 }

vtssPsfpStatusFilterWarningStreamCollectionAttachFail OBJECT-TYPE
    SYNTAX      TruthValue
    MAX-ACCESS  read-only
    STATUS      current
    DESCRIPTION
        "Unable to attach to the specified stream collection."
    ::= { vtssPsfpStatusFilterEntry 8 }

vtssPsfpStatusFilterWarningStreamHasConfigurationalWarnings OBJECT-TYPE
    SYNTAX      TruthValue
    MAX-ACCESS  read-only
    STATUS      current
    DESCRIPTION
        "The specified stream has configurational warnings."
    ::= { vtssPsfpStatusFilterEntry 9 }

vtssPsfpStatusFilterWarningStreamCollectionHasConfWarnings OBJECT-TYPE
    SYNTAX      TruthValue
    MAX-ACCESS  read-only
    STATUS      current
    DESCRIPTION
        "The specified stream collection has configurational warnings."
    ::= { vtssPsfpStatusFilterEntry 10 }

vtssPsfpStatusFilterWarningFlowMeterNotFound OBJECT-TYPE
    SYNTAX      TruthValue
    MAX-ACCESS  read-only
    STATUS      current
    DESCRIPTION
        "The specified flow meter ID does not exist."
    ::= { vtssPsfpStatusFilterEntry 11 }

vtssPsfpStatusFilterWarningGateNotFound OBJECT-TYPE
    SYNTAX      TruthValue
    MAX-ACCESS  read-only
    STATUS      current
    DESCRIPTION
        "The specified stream gate ID does not exist."
    ::= { vtssPsfpStatusFilterEntry 12 }

vtssPsfpStatusFilterWarningGateNotEnabled OBJECT-TYPE
    SYNTAX      TruthValue
    MAX-ACCESS  read-only
    STATUS      current
    DESCRIPTION
        "The specified stream gate is not enabled."
    ::= { vtssPsfpStatusFilterEntry 13 }

vtssPsfpControl OBJECT IDENTIFIER
    ::= { vtssPsfpMibObjects 4 }

vtssPsfpControlFlowMeterClearTable OBJECT-TYPE
    SYNTAX      SEQUENCE OF VTSSPsfpControlFlowMeterClearEntry
    MAX-ACCESS  not-accessible
    STATUS      current
    DESCRIPTION
        "PSFP Flow Meter state clear"
    ::= { vtssPsfpControl 1 }

vtssPsfpControlFlowMeterClearEntry OBJECT-TYPE
    SYNTAX      VTSSPsfpControlFlowMeterClearEntry
    MAX-ACCESS  not-accessible
    STATUS      current
    DESCRIPTION
        "Each index points to a given flow meter ID"
    INDEX       { vtssPsfpControlFlowMeterClearFlowMeterId }
    ::= { vtssPsfpControlFlowMeterClearTable 1 }

VTSSPsfpControlFlowMeterClearEntry ::= SEQUENCE {
    vtssPsfpControlFlowMeterClearFlowMeterId            Unsigned32,
    vtssPsfpControlFlowMeterClearClearMarkAllFramesRed  VTSSUnsigned8
}

vtssPsfpControlFlowMeterClearFlowMeterId OBJECT-TYPE
    SYNTAX      Unsigned32
    MAX-ACCESS  accessible-for-notify
    STATUS      current
    DESCRIPTION
        "The ID of the Flow Meter instance"
    ::= { vtssPsfpControlFlowMeterClearEntry 1 }

vtssPsfpControlFlowMeterClearClearMarkAllFramesRed OBJECT-TYPE
    SYNTAX      VTSSUnsigned8
    MAX-ACCESS  read-write
    STATUS      current
    DESCRIPTION
        "Set to TRUE to clear the MarkAllFramesRed flag."
    ::= { vtssPsfpControlFlowMeterClearEntry 2 }

vtssPsfpControlGateClearTable OBJECT-TYPE
    SYNTAX      SEQUENCE OF VTSSPsfpControlGateClearEntry
    MAX-ACCESS  not-accessible
    STATUS      current
    DESCRIPTION
        "Table for clearing various stream gate status"
    ::= { vtssPsfpControl 2 }

vtssPsfpControlGateClearEntry OBJECT-TYPE
    SYNTAX      VTSSPsfpControlGateClearEntry
    MAX-ACCESS  not-accessible
    STATUS      current
    DESCRIPTION
        "Each index in the table represents a stream gate instance"
    INDEX       { vtssPsfpControlGateClearGateId }
    ::= { vtssPsfpControlGateClearTable 1 }

VTSSPsfpControlGateClearEntry ::= SEQUENCE {
    vtssPsfpControlGateClearGateId                              Unsigned32,
    vtssPsfpControlGateClearClearGateClosedDueToInvalidRx       TruthValue,
    vtssPsfpControlGateClearClearGateClosedDueToOctetsExceeded  TruthValue
}

vtssPsfpControlGateClearGateId OBJECT-TYPE
    SYNTAX      Unsigned32
    MAX-ACCESS  accessible-for-notify
    STATUS      current
    DESCRIPTION
        "The ID of the Stream Gate instance"
    ::= { vtssPsfpControlGateClearEntry 1 }

vtssPsfpControlGateClearClearGateClosedDueToInvalidRx OBJECT-TYPE
    SYNTAX      TruthValue
    MAX-ACCESS  read-write
    STATUS      current
    DESCRIPTION
        "Set to TRUE to clear the GateClosedDueToInvalidRx flag."
    ::= { vtssPsfpControlGateClearEntry 2 }

vtssPsfpControlGateClearClearGateClosedDueToOctetsExceeded OBJECT-TYPE
    SYNTAX      TruthValue
    MAX-ACCESS  read-write
    STATUS      current
    DESCRIPTION
        "Set to TRUE to clear the GateClosedDueToOctetsExceeded flag."
    ::= { vtssPsfpControlGateClearEntry 3 }

vtssPsfpControlFilterClearTable OBJECT-TYPE
    SYNTAX      SEQUENCE OF VTSSPsfpControlFilterClearEntry
    MAX-ACCESS  not-accessible
    STATUS      current
    DESCRIPTION
        "Table for clearing stream filter status"
    ::= { vtssPsfpControl 3 }

vtssPsfpControlFilterClearEntry OBJECT-TYPE
    SYNTAX      VTSSPsfpControlFilterClearEntry
    MAX-ACCESS  not-accessible
    STATUS      current
    DESCRIPTION
        "Each index in the table represents a stream filter instance"
    INDEX       { vtssPsfpControlFilterClearFilterId }
    ::= { vtssPsfpControlFilterClearTable 1 }

VTSSPsfpControlFilterClearEntry ::= SEQUENCE {
    vtssPsfpControlFilterClearFilterId                        Unsigned32,
    vtssPsfpControlFilterClearClearBlockedDueToOversizeFrame  TruthValue
}

vtssPsfpControlFilterClearFilterId OBJECT-TYPE
    SYNTAX      Unsigned32
    MAX-ACCESS  accessible-for-notify
    STATUS      current
    DESCRIPTION
        "The ID of the Stream Filter instance"
    ::= { vtssPsfpControlFilterClearEntry 1 }

vtssPsfpControlFilterClearClearBlockedDueToOversizeFrame OBJECT-TYPE
    SYNTAX      TruthValue
    MAX-ACCESS  read-write
    STATUS      current
    DESCRIPTION
        "If the stream is blocked due to reception of an oversize frame all
         subsequent frames are discarded despite their size until this field
         gets set to true."
    ::= { vtssPsfpControlFilterClearEntry 2 }

vtssPsfpControlFilterStatisticsClearTable OBJECT-TYPE
    SYNTAX      SEQUENCE OF VTSSPsfpControlFilterStatisticsClearEntry
    MAX-ACCESS  not-accessible
    STATUS      current
    DESCRIPTION
        "This is a table to clear stream filter statistics"
    ::= { vtssPsfpControl 4 }

vtssPsfpControlFilterStatisticsClearEntry OBJECT-TYPE
    SYNTAX      VTSSPsfpControlFilterStatisticsClearEntry
    MAX-ACCESS  not-accessible
    STATUS      current
    DESCRIPTION
        "Each index points to a given stream filter ID"
    INDEX       { vtssPsfpControlFilterStatisticsClearFilterId }
    ::= { vtssPsfpControlFilterStatisticsClearTable 1 }

VTSSPsfpControlFilterStatisticsClearEntry ::= SEQUENCE {
    vtssPsfpControlFilterStatisticsClearFilterId  Unsigned32,
    vtssPsfpControlFilterStatisticsClearClear     TruthValue
}

vtssPsfpControlFilterStatisticsClearFilterId OBJECT-TYPE
    SYNTAX      Unsigned32
    MAX-ACCESS  accessible-for-notify
    STATUS      current
    DESCRIPTION
        "The ID of the Stream Filter instance"
    ::= { vtssPsfpControlFilterStatisticsClearEntry 1 }

vtssPsfpControlFilterStatisticsClearClear OBJECT-TYPE
    SYNTAX      TruthValue
    MAX-ACCESS  read-write
    STATUS      current
    DESCRIPTION
        "Set to TRUE to clear the statistics of a stream filter instance."
    ::= { vtssPsfpControlFilterStatisticsClearEntry 2 }

vtssPsfpStatistics OBJECT IDENTIFIER
    ::= { vtssPsfpMibObjects 5 }

vtssPsfpStatisticsFilterTable OBJECT-TYPE
    SYNTAX      SEQUENCE OF VTSSPsfpStatisticsFilterEntry
    MAX-ACCESS  not-accessible
    STATUS      current
    DESCRIPTION
        "This table holds statistics of PSFP stream filters"
    ::= { vtssPsfpStatistics 1 }

vtssPsfpStatisticsFilterEntry OBJECT-TYPE
    SYNTAX      VTSSPsfpStatisticsFilterEntry
    MAX-ACCESS  not-accessible
    STATUS      current
    DESCRIPTION
        "Each index points to a given filter ID"
    INDEX       { vtssPsfpStatisticsFilterFilterId }
    ::= { vtssPsfpStatisticsFilterTable 1 }

VTSSPsfpStatisticsFilterEntry ::= SEQUENCE {
    vtssPsfpStatisticsFilterFilterId       Unsigned32,
    vtssPsfpStatisticsFilterMatching       VTSSUnsigned64,
    vtssPsfpStatisticsFilterPassing        VTSSUnsigned64,
    vtssPsfpStatisticsFilterNotPassing     VTSSUnsigned64,
    vtssPsfpStatisticsFilterPassingSDU     VTSSUnsigned64,
    vtssPsfpStatisticsFilterNotPassingSDU  VTSSUnsigned64,
    vtssPsfpStatisticsFilterRed            VTSSUnsigned64
}

vtssPsfpStatisticsFilterFilterId OBJECT-TYPE
    SYNTAX      Unsigned32
    MAX-ACCESS  accessible-for-notify
    STATUS      current
    DESCRIPTION
        "The ID of the Stream Filter instance"
    ::= { vtssPsfpStatisticsFilterEntry 1 }

vtssPsfpStatisticsFilterMatching OBJECT-TYPE
    SYNTAX      VTSSUnsigned64
    MAX-ACCESS  read-only
    STATUS      current
    DESCRIPTION
        "Counts received frames that match this stream filter."
    ::= { vtssPsfpStatisticsFilterEntry 21 }

vtssPsfpStatisticsFilterPassing OBJECT-TYPE
    SYNTAX      VTSSUnsigned64
    MAX-ACCESS  read-only
    STATUS      current
    DESCRIPTION
        "Counts received frames that pass the gate associated with this stream
         filter."
    ::= { vtssPsfpStatisticsFilterEntry 22 }

vtssPsfpStatisticsFilterNotPassing OBJECT-TYPE
    SYNTAX      VTSSUnsigned64
    MAX-ACCESS  read-only
    STATUS      current
    DESCRIPTION
        "Counts received frames that do not pass the gate associated with this
         stream filter."
    ::= { vtssPsfpStatisticsFilterEntry 23 }

vtssPsfpStatisticsFilterPassingSDU OBJECT-TYPE
    SYNTAX      VTSSUnsigned64
    MAX-ACCESS  read-only
    STATUS      current
    DESCRIPTION
        "Counts received frames that pass the SDU size filter specifications
         associated with this stream filter."
    ::= { vtssPsfpStatisticsFilterEntry 24 }

vtssPsfpStatisticsFilterNotPassingSDU OBJECT-TYPE
    SYNTAX      VTSSUnsigned64
    MAX-ACCESS  read-only
    STATUS      current
    DESCRIPTION
        "Counts received frames that do not pass the SDU size filter
         specifications associated with this stream filter."
    ::= { vtssPsfpStatisticsFilterEntry 25 }

vtssPsfpStatisticsFilterRed OBJECT-TYPE
    SYNTAX      VTSSUnsigned64
    MAX-ACCESS  read-only
    STATUS      current
    DESCRIPTION
        "Counts received frames that were discarded as a result of the flow
         meter associated with this stream filter."
    ::= { vtssPsfpStatisticsFilterEntry 26 }

vtssPsfpMibConformance OBJECT IDENTIFIER
    ::= { vtssPsfpMib 2 }

vtssPsfpMibCompliances OBJECT IDENTIFIER
    ::= { vtssPsfpMibConformance 1 }

vtssPsfpMibGroups OBJECT IDENTIFIER
    ::= { vtssPsfpMibConformance 2 }

vtssPsfpCapabilitiesInfoGroup OBJECT-GROUP
    OBJECTS     { vtssPsfpCapabilitiesFilterInstanceCntMax,
                  vtssPsfpCapabilitiesGateInstanceCntMax,
                  vtssPsfpCapabilitiesFlowMeterInstanceCntMax,
                  vtssPsfpCapabilitiesGateControlListLengthMax,
                  vtssPsfpCapabilitiesStreamIdMax,
                  vtssPsfpCapabilitiesStreamCollectionIdMax,
                  vtssPsfpCapabilitiesPsfpSupported }
    STATUS      current
    DESCRIPTION
        "A collection of objects."
    ::= { vtssPsfpMibGroups 1 }

vtssPsfpConfigFlowMeterTableInfoGroup OBJECT-GROUP
    OBJECTS     { vtssPsfpConfigFlowMeterFlowMeterId,
                  vtssPsfpConfigFlowMeterCIR,
                  vtssPsfpConfigFlowMeterCBS,
                  vtssPsfpConfigFlowMeterEIR,
                  vtssPsfpConfigFlowMeterEBS,
                  vtssPsfpConfigFlowMeterCF,
                  vtssPsfpConfigFlowMeterCM,
                  vtssPsfpConfigFlowMeterDropOnYellow,
                  vtssPsfpConfigFlowMeterMarkAllFramesRedEnable,
                  vtssPsfpConfigFlowMeterAction }
    STATUS      current
    DESCRIPTION
        "A collection of objects."
    ::= { vtssPsfpMibGroups 2 }

vtssPsfpConfigFlowMeterRowEditorInfoGroup OBJECT-GROUP
    OBJECTS     { vtssPsfpConfigFlowMeterRowEditorFlowMeterId,
                  vtssPsfpConfigFlowMeterRowEditorCIR,
                  vtssPsfpConfigFlowMeterRowEditorCBS,
                  vtssPsfpConfigFlowMeterRowEditorEIR,
                  vtssPsfpConfigFlowMeterRowEditorEBS,
                  vtssPsfpConfigFlowMeterRowEditorCF,
                  vtssPsfpConfigFlowMeterRowEditorCM,
                  vtssPsfpConfigFlowMeterRowEditorDropOnYellow,
                  vtssPsfpConfigFlowMeterRowEditorMarkAllFramesRedEnable,
                  vtssPsfpConfigFlowMeterRowEditorAction }
    STATUS      current
    DESCRIPTION
        "A collection of objects."
    ::= { vtssPsfpMibGroups 3 }

vtssPsfpConfigGateTableInfoGroup OBJECT-GROUP
    OBJECTS     { vtssPsfpConfigGateGateId,
                  vtssPsfpConfigGateAdminGateState,
                  vtssPsfpConfigGateAdminCycleTimeNumerator,
                  vtssPsfpConfigGateAdminCycleTimeUnit,
                  vtssPsfpConfigGateAdminCycleTimeExtensionNumerator,
                  vtssPsfpConfigGateAdminCycleTimeExtensionUnit,
                  vtssPsfpConfigGateAdminBaseTimeTxt,
                  vtssPsfpConfigGateAdminBaseTimeIso8601,
                  vtssPsfpConfigGateAdminIpv,
                  vtssPsfpConfigGateAdminCloseGateInvalidRxEnable,
                  vtssPsfpConfigGateAdminCloseGateOctetsExceededEnable,
                  vtssPsfpConfigGateAdminGclLength,
                  vtssPsfpConfigGateAdminGce0GateState,
                  vtssPsfpConfigGateAdminGce0Ipv,
                  vtssPsfpConfigGateAdminGce0TimeIntervalNumerator,
                  vtssPsfpConfigGateAdminGce0TimeIntervalUnit,
                  vtssPsfpConfigGateAdminGce0IntervalOctetMax,
                  vtssPsfpConfigGateAdminGce1GateState,
                  vtssPsfpConfigGateAdminGce1Ipv,
                  vtssPsfpConfigGateAdminGce1TimeIntervalNumerator,
                  vtssPsfpConfigGateAdminGce1TimeIntervalUnit,
                  vtssPsfpConfigGateAdminGce1IntervalOctetMax,
                  vtssPsfpConfigGateAdminGce2GateState,
                  vtssPsfpConfigGateAdminGce2Ipv,
                  vtssPsfpConfigGateAdminGce2TimeIntervalNumerator,
                  vtssPsfpConfigGateAdminGce2TimeIntervalUnit,
                  vtssPsfpConfigGateAdminGce2IntervalOctetMax,
                  vtssPsfpConfigGateAdminGce3GateState,
                  vtssPsfpConfigGateAdminGce3Ipv,
                  vtssPsfpConfigGateAdminGce3TimeIntervalNumerator,
                  vtssPsfpConfigGateAdminGce3TimeIntervalUnit,
                  vtssPsfpConfigGateAdminGce3IntervalOctetMax,
                  vtssPsfpConfigGateAdminConfigChange,
                  vtssPsfpConfigGateAdminGateEnabled,
                  vtssPsfpConfigGateAction }
    STATUS      current
    DESCRIPTION
        "A collection of objects."
    ::= { vtssPsfpMibGroups 4 }

vtssPsfpConfigGateRowEditorInfoGroup OBJECT-GROUP
    OBJECTS     { vtssPsfpConfigGateRowEditorGateId,
                  vtssPsfpConfigGateRowEditorAdminGateState,
                  vtssPsfpConfigGateRowEditorAdminCycleTimeNumerator,
                  vtssPsfpConfigGateRowEditorAdminCycleTimeUnit,
                  vtssPsfpConfigGateRowEditorAdminCycleTimeExtensionNumerator,
                  vtssPsfpConfigGateRowEditorAdminCycleTimeExtensionUnit,
                  vtssPsfpConfigGateRowEditorAdminBaseTimeTxt,
                  vtssPsfpConfigGateRowEditorAdminBaseTimeIso8601,
                  vtssPsfpConfigGateRowEditorAdminIpv,
                  vtssPsfpConfigGateRowEditorAdminCloseGateInvalidRxEnable,
                  vtssPsfpConfigGateRowEditorAdminCloseGateOctetsExceededEnable,
                  vtssPsfpConfigGateRowEditorAdminGclLength,
                  vtssPsfpConfigGateRowEditorAdminGce0GateState,
                  vtssPsfpConfigGateRowEditorAdminGce0Ipv,
                  vtssPsfpConfigGateRowEditorAdminGce0TimeIntervalNumerator,
                  vtssPsfpConfigGateRowEditorAdminGce0TimeIntervalUnit,
                  vtssPsfpConfigGateRowEditorAdminGce0IntervalOctetMax,
                  vtssPsfpConfigGateRowEditorAdminGce1GateState,
                  vtssPsfpConfigGateRowEditorAdminGce1Ipv,
                  vtssPsfpConfigGateRowEditorAdminGce1TimeIntervalNumerator,
                  vtssPsfpConfigGateRowEditorAdminGce1TimeIntervalUnit,
                  vtssPsfpConfigGateRowEditorAdminGce1IntervalOctetMax,
                  vtssPsfpConfigGateRowEditorAdminGce2GateState,
                  vtssPsfpConfigGateRowEditorAdminGce2Ipv,
                  vtssPsfpConfigGateRowEditorAdminGce2TimeIntervalNumerator,
                  vtssPsfpConfigGateRowEditorAdminGce2TimeIntervalUnit,
                  vtssPsfpConfigGateRowEditorAdminGce2IntervalOctetMax,
                  vtssPsfpConfigGateRowEditorAdminGce3GateState,
                  vtssPsfpConfigGateRowEditorAdminGce3Ipv,
                  vtssPsfpConfigGateRowEditorAdminGce3TimeIntervalNumerator,
                  vtssPsfpConfigGateRowEditorAdminGce3TimeIntervalUnit,
                  vtssPsfpConfigGateRowEditorAdminGce3IntervalOctetMax,
                  vtssPsfpConfigGateRowEditorAdminConfigChange,
                  vtssPsfpConfigGateRowEditorAdminGateEnabled,
                  vtssPsfpConfigGateRowEditorAction }
    STATUS      current
    DESCRIPTION
        "A collection of objects."
    ::= { vtssPsfpMibGroups 5 }

vtssPsfpConfigFilterTableInfoGroup OBJECT-GROUP
    OBJECTS     { vtssPsfpConfigFilterFilterId,
                  vtssPsfpConfigFilterStreamId,
                  vtssPsfpConfigFilterStreamCollectionId,
                  vtssPsfpConfigFilterFlowMeterId,
                  vtssPsfpConfigFilterGateId,
                  vtssPsfpConfigFilterMaxSDUSize,
                  vtssPsfpConfigFilterBlockDueToOversizeFrameEnable,
                  vtssPsfpConfigFilterAction }
    STATUS      current
    DESCRIPTION
        "A collection of objects."
    ::= { vtssPsfpMibGroups 6 }

vtssPsfpConfigFilterRowEditorInfoGroup OBJECT-GROUP
    OBJECTS     { vtssPsfpConfigFilterRowEditorFilterId,
                  vtssPsfpConfigFilterRowEditorStreamId,
                  vtssPsfpConfigFilterRowEditorStreamCollectionId,
                  vtssPsfpConfigFilterRowEditorFlowMeterId,
                  vtssPsfpConfigFilterRowEditorGateId,
                  vtssPsfpConfigFilterRowEditorMaxSDUSize,
                  vtssPsfpConfigFilterRowEditorBlockDueToOversizeFrameEnable,
                  vtssPsfpConfigFilterRowEditorAction }
    STATUS      current
    DESCRIPTION
        "A collection of objects."
    ::= { vtssPsfpMibGroups 7 }

vtssPsfpStatusFlowMeterTableInfoGroup OBJECT-GROUP
    OBJECTS     { vtssPsfpStatusFlowMeterFlowMeterId,
                  vtssPsfpStatusFlowMeterMarkAllFramesRed }
    STATUS      current
    DESCRIPTION
        "A collection of objects."
    ::= { vtssPsfpMibGroups 8 }

vtssPsfpStatusGateTableInfoGroup OBJECT-GROUP
    OBJECTS     { vtssPsfpStatusGateGateId,
                  vtssPsfpStatusGateOperConfValid,
                  vtssPsfpStatusGateOperConfGateState,
                  vtssPsfpStatusGateOperConfCycleTimeNumerator,
                  vtssPsfpStatusGateOperConfCycleTimeUnit,
                  vtssPsfpStatusGateOperConfCycleTimeExtensionNumerator,
                  vtssPsfpStatusGateOperConfCycleTimeExtensionUnit,
                  vtssPsfpStatusGateOperConfBaseTimeTxt,
                  vtssPsfpStatusGateOperConfBaseTimeIso8601,
                  vtssPsfpStatusGateOperConfIpv,
                  vtssPsfpStatusGateOperConfCloseGateInvalidRxEnable,
                  vtssPsfpStatusGateOperConfCloseGateOctetsExceededEnable,
                  vtssPsfpStatusGateOperConfGclLength,
                  vtssPsfpStatusGateOperConfGce0GateState,
                  vtssPsfpStatusGateOperConfGce0Ipv,
                  vtssPsfpStatusGateOperConfGce0TimeIntervalNumerator,
                  vtssPsfpStatusGateOperConfGce0TimeIntervalUnit,
                  vtssPsfpStatusGateOperConfGce0IntervalOctetMax,
                  vtssPsfpStatusGateOperConfGce1GateState,
                  vtssPsfpStatusGateOperConfGce1Ipv,
                  vtssPsfpStatusGateOperConfGce1TimeIntervalNumerator,
                  vtssPsfpStatusGateOperConfGce1TimeIntervalUnit,
                  vtssPsfpStatusGateOperConfGce1IntervalOctetMax,
                  vtssPsfpStatusGateOperConfGce2GateState,
                  vtssPsfpStatusGateOperConfGce2Ipv,
                  vtssPsfpStatusGateOperConfGce2TimeIntervalNumerator,
                  vtssPsfpStatusGateOperConfGce2TimeIntervalUnit,
                  vtssPsfpStatusGateOperConfGce2IntervalOctetMax,
                  vtssPsfpStatusGateOperConfGce3GateState,
                  vtssPsfpStatusGateOperConfGce3Ipv,
                  vtssPsfpStatusGateOperConfGce3TimeIntervalNumerator,
                  vtssPsfpStatusGateOperConfGce3TimeIntervalUnit,
                  vtssPsfpStatusGateOperConfGce3IntervalOctetMax,
                  vtssPsfpStatusGateOperConfConfigChange,
                  vtssPsfpStatusGateOperConfGateEnabled,
                  vtssPsfpStatusGateConfigPending,
                  vtssPsfpStatusGatePendConfGateState,
                  vtssPsfpStatusGatePendConfCycleTimeNumerator,
                  vtssPsfpStatusGatePendConfCycleTimeUnit,
                  vtssPsfpStatusGatePendConfCycleTimeExtensionNumerator,
                  vtssPsfpStatusGatePendConfCycleTimeExtensionUnit,
                  vtssPsfpStatusGatePendConfBaseTimeTxt,
                  vtssPsfpStatusGatePendConfBaseTimeIso8601,
                  vtssPsfpStatusGatePendConfIpv,
                  vtssPsfpStatusGatePendConfCloseGateInvalidRxEnable,
                  vtssPsfpStatusGatePendConfCloseGateOctetsExceededEnable,
                  vtssPsfpStatusGatePendConfGclLength,
                  vtssPsfpStatusGatePendConfGce0GateState,
                  vtssPsfpStatusGatePendConfGce0Ipv,
                  vtssPsfpStatusGatePendConfGce0TimeIntervalNumerator,
                  vtssPsfpStatusGatePendConfGce0TimeIntervalUnit,
                  vtssPsfpStatusGatePendConfGce0IntervalOctetMax,
                  vtssPsfpStatusGatePendConfGce1GateState,
                  vtssPsfpStatusGatePendConfGce1Ipv,
                  vtssPsfpStatusGatePendConfGce1TimeIntervalNumerator,
                  vtssPsfpStatusGatePendConfGce1TimeIntervalUnit,
                  vtssPsfpStatusGatePendConfGce1IntervalOctetMax,
                  vtssPsfpStatusGatePendConfGce2GateState,
                  vtssPsfpStatusGatePendConfGce2Ipv,
                  vtssPsfpStatusGatePendConfGce2TimeIntervalNumerator,
                  vtssPsfpStatusGatePendConfGce2TimeIntervalUnit,
                  vtssPsfpStatusGatePendConfGce2IntervalOctetMax,
                  vtssPsfpStatusGatePendConfGce3GateState,
                  vtssPsfpStatusGatePendConfGce3Ipv,
                  vtssPsfpStatusGatePendConfGce3TimeIntervalNumerator,
                  vtssPsfpStatusGatePendConfGce3TimeIntervalUnit,
                  vtssPsfpStatusGatePendConfGce3IntervalOctetMax,
                  vtssPsfpStatusGatePendConfConfigChange,
                  vtssPsfpStatusGatePendConfGateEnabled,
                  vtssPsfpStatusGateOperGateState,
                  vtssPsfpStatusGateOperIpv,
                  vtssPsfpStatusGateConfigChangeTimeTxt,
                  vtssPsfpStatusGateConfigChangeTimeIso8601,
                  vtssPsfpStatusGateCurrentTimeTxt,
                  vtssPsfpStatusGateCurrentTimeIso8601,
                  vtssPsfpStatusGateTickGranularity,
                  vtssPsfpStatusGateConfigChangeErrors,
                  vtssPsfpStatusGateGateClosedDueToInvalidRx,
                  vtssPsfpStatusGateGateClosedDueToOctetsExceeded }
    STATUS      current
    DESCRIPTION
        "A collection of objects."
    ::= { vtssPsfpMibGroups 9 }

vtssPsfpStatusFilterTableInfoGroup OBJECT-GROUP
    OBJECTS     { vtssPsfpStatusFilterFilterId,
                  vtssPsfpStatusFilterBlockedDueToOversizeFrame,
                  vtssPsfpStatusFilterWarningNone,
                  vtssPsfpStatusFilterWarningNoStreamOrStreamCollection,
                  vtssPsfpStatusFilterWarningStreamNotFound,
                  vtssPsfpStatusFilterWarningStreamCollectionNotFound,
                  vtssPsfpStatusFilterWarningStreamAttachFail,
                  vtssPsfpStatusFilterWarningStreamCollectionAttachFail,
                  vtssPsfpStatusFilterWarningStreamHasConfigurationalWarnings,
                  vtssPsfpStatusFilterWarningStreamCollectionHasConfWarnings,
                  vtssPsfpStatusFilterWarningFlowMeterNotFound,
                  vtssPsfpStatusFilterWarningGateNotFound,
                  vtssPsfpStatusFilterWarningGateNotEnabled }
    STATUS      current
    DESCRIPTION
        "A collection of objects."
    ::= { vtssPsfpMibGroups 10 }

vtssPsfpControlFlowMeterClearTableInfoGroup OBJECT-GROUP
    OBJECTS     { vtssPsfpControlFlowMeterClearFlowMeterId,
                  vtssPsfpControlFlowMeterClearClearMarkAllFramesRed }
    STATUS      current
    DESCRIPTION
        "A collection of objects."
    ::= { vtssPsfpMibGroups 11 }

vtssPsfpControlGateClearTableInfoGroup OBJECT-GROUP
    OBJECTS     { vtssPsfpControlGateClearGateId,
                  vtssPsfpControlGateClearClearGateClosedDueToInvalidRx,
                  vtssPsfpControlGateClearClearGateClosedDueToOctetsExceeded }
    STATUS      current
    DESCRIPTION
        "A collection of objects."
    ::= { vtssPsfpMibGroups 12 }

vtssPsfpControlFilterClearTableInfoGroup OBJECT-GROUP
    OBJECTS     { vtssPsfpControlFilterClearFilterId,
                  vtssPsfpControlFilterClearClearBlockedDueToOversizeFrame }
    STATUS      current
    DESCRIPTION
        "A collection of objects."
    ::= { vtssPsfpMibGroups 13 }

vtssPsfpControlFilterStatisticsClearInfoGroup OBJECT-GROUP
    OBJECTS     { vtssPsfpControlFilterStatisticsClearFilterId,
                  vtssPsfpControlFilterStatisticsClearClear }
    STATUS      current
    DESCRIPTION
        "A collection of objects."
    ::= { vtssPsfpMibGroups 14 }

vtssPsfpStatisticsFilterTableInfoGroup OBJECT-GROUP
    OBJECTS     { vtssPsfpStatisticsFilterFilterId,
                  vtssPsfpStatisticsFilterMatching,
                  vtssPsfpStatisticsFilterPassing,
                  vtssPsfpStatisticsFilterNotPassing,
                  vtssPsfpStatisticsFilterPassingSDU,
                  vtssPsfpStatisticsFilterNotPassingSDU,
                  vtssPsfpStatisticsFilterRed }
    STATUS      current
    DESCRIPTION
        "A collection of objects."
    ::= { vtssPsfpMibGroups 15 }

vtssPsfpMibCompliance MODULE-COMPLIANCE
    STATUS      current
    DESCRIPTION
        "The compliance statement for the implementation."

    MODULE      -- this module

    MANDATORY-GROUPS { vtssPsfpCapabilitiesInfoGroup,
                       vtssPsfpConfigFlowMeterTableInfoGroup,
                       vtssPsfpConfigFlowMeterRowEditorInfoGroup,
                       vtssPsfpConfigGateTableInfoGroup,
                       vtssPsfpConfigGateRowEditorInfoGroup,
                       vtssPsfpConfigFilterTableInfoGroup,
                       vtssPsfpConfigFilterRowEditorInfoGroup,
                       vtssPsfpStatusFlowMeterTableInfoGroup,
                       vtssPsfpStatusGateTableInfoGroup,
                       vtssPsfpStatusFilterTableInfoGroup,
                       vtssPsfpControlFlowMeterClearTableInfoGroup,
                       vtssPsfpControlGateClearTableInfoGroup,
                       vtssPsfpControlFilterClearTableInfoGroup,
                       vtssPsfpControlFilterStatisticsClearInfoGroup,
                       vtssPsfpStatisticsFilterTableInfoGroup }

    ::= { vtssPsfpMibCompliances 1 }

END
