-- *****************************************************************
-- MACSEC-MIB:  Microsemi ENT private MIB
-- ****************************************************************

VTSS-MACSEC-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Unsigned32 FROM SNMPv2-SMI
    MacAddress FROM SNMPv2-TC
    TruthValue FROM SNMPv2-TC
    VTSSDisplayString FROM VTSS-TC
    VTSSInterfaceIndex FROM VTSS-TC
    VTSSRowEditorState FROM VTSS-TC
    VTSSUnsigned16 FROM VTSS-TC
    VTSSUnsigned64 FROM VTSS-TC
    ;

vtssMacsecMib MODULE-IDENTITY
    LAST-UPDATED "202405170000Z"
    ORGANIZATION
        "Microsemi Corporation"
    CONTACT-INFO
        "Application support: http://www.microchip.com/support"
    DESCRIPTION
        "Private MIB for MACsec (IEEE 802.1AE) Demo Module"
    REVISION    "202405170000Z"
    DESCRIPTION
        "Initial version"
    ::= { vtssSwitchMgmt 112 }


VTSSMacsecCipherSuite ::= TEXTUAL-CONVENTION
    STATUS      current
    DESCRIPTION
        "This enumeration defines the chosen cipher suite of the SecY."
    SYNTAX      INTEGER { gcmAes128(1), gcmAes256(2), gcmAesXpn128(4),
                          gcmAesXpn256(8) }

VTSSMacsecFrameValidation ::= TEXTUAL-CONVENTION
    STATUS      current
    DESCRIPTION
        "Configuration of how MACsec handled the ICV of incoming frames:"
    SYNTAX      INTEGER { disabled(0), check(1), strict(2) }

VTSSMacsecStatisticsClearWhat ::= TEXTUAL-CONVENTION
    STATUS      current
    DESCRIPTION
        "Controls which statistics to clear."
    SYNTAX      INTEGER { controlled(0), controlledTx(1),
                          controlledRx(2), uncontrolled(3), common(4),
                          all(5) }

VTSSMacsecTxScMacType ::= TEXTUAL-CONVENTION
    STATUS      current
    DESCRIPTION
        "This enumeration makes it possible to choose between Tx Secure Channel
         MAC address match options."
    SYNTAX      INTEGER { management(0), port(1), custom(2) }

vtssMacsecMibObjects OBJECT IDENTIFIER
    ::= { vtssMacsecMib 1 }

vtssMacsecCapabilities OBJECT IDENTIFIER
    ::= { vtssMacsecMibObjects 1 }

vtssMacsecCapabilitiesList OBJECT IDENTIFIER
    ::= { vtssMacsecCapabilities 1 }

vtssMacsecCapabilitiesListMacsecSupported OBJECT-TYPE
    SYNTAX      TruthValue
    MAX-ACCESS  read-only
    STATUS      current
    DESCRIPTION
        "True if at least one port on this device has MACsec capabilities."
    ::= { vtssMacsecCapabilitiesList 1 }

vtssMacsecCapabilitiesInterfacesTable OBJECT-TYPE
    SYNTAX      SEQUENCE OF VTSSMacsecCapabilitiesInterfacesEntry
    MAX-ACCESS  not-accessible
    STATUS      current
    DESCRIPTION
        "This table contains - per interface - the MACsec capabilities"
    ::= { vtssMacsecCapabilities 2 }

vtssMacsecCapabilitiesInterfacesEntry OBJECT-TYPE
    SYNTAX      VTSSMacsecCapabilitiesInterfacesEntry
    MAX-ACCESS  not-accessible
    STATUS      current
    DESCRIPTION
        "Each entry shows what a given interface is capable of in terms of
         MACsec"
    INDEX       { vtssMacsecCapabilitiesInterfacesIfIndex }
    ::= { vtssMacsecCapabilitiesInterfacesTable 1 }

VTSSMacsecCapabilitiesInterfacesEntry ::= SEQUENCE {
    vtssMacsecCapabilitiesInterfacesIfIndex            VTSSInterfaceIndex,
    vtssMacsecCapabilitiesInterfacesMacsecCapable      TruthValue,
    vtssMacsecCapabilitiesInterfacesGcmAes128          TruthValue,
    vtssMacsecCapabilitiesInterfacesGcmAes256          TruthValue,
    vtssMacsecCapabilitiesInterfacesGcmAesXpn128       TruthValue,
    vtssMacsecCapabilitiesInterfacesGcmAesXpn256       TruthValue,
    vtssMacsecCapabilitiesInterfacesTotalRxSaCnt       Unsigned32,
    vtssMacsecCapabilitiesInterfacesTotalTxSaCnt       Unsigned32,
    vtssMacsecCapabilitiesInterfacesSecyCntMax         Unsigned32,
    vtssMacsecCapabilitiesInterfacesTxScCntPerSecyMax  Unsigned32,
    vtssMacsecCapabilitiesInterfacesRxScCntPerSecyMax  Unsigned32,
    vtssMacsecCapabilitiesInterfacesTxSaCntPerScMax    Unsigned32,
    vtssMacsecCapabilitiesInterfacesRxSaCntPerScMax    Unsigned32
}

vtssMacsecCapabilitiesInterfacesIfIndex OBJECT-TYPE
    SYNTAX      VTSSInterfaceIndex
    MAX-ACCESS  accessible-for-notify
    STATUS      current
    DESCRIPTION
        "Logical port interface number."
    ::= { vtssMacsecCapabilitiesInterfacesEntry 1 }

vtssMacsecCapabilitiesInterfacesMacsecCapable OBJECT-TYPE
    SYNTAX      TruthValue
    MAX-ACCESS  read-only
    STATUS      current
    DESCRIPTION
        "True if this port supports MACsec, false otherwise. If false, the
         remaining parameters make no sense."
    ::= { vtssMacsecCapabilitiesInterfacesEntry 2 }

vtssMacsecCapabilitiesInterfacesGcmAes128 OBJECT-TYPE
    SYNTAX      TruthValue
    MAX-ACCESS  read-only
    STATUS      current
    DESCRIPTION
        "True if this interface supports the GCM-AES-128 cipher suite"
    ::= { vtssMacsecCapabilitiesInterfacesEntry 3 }

vtssMacsecCapabilitiesInterfacesGcmAes256 OBJECT-TYPE
    SYNTAX      TruthValue
    MAX-ACCESS  read-only
    STATUS      current
    DESCRIPTION
        "True if this interface supports the GCM-AES-256 cipher suite"
    ::= { vtssMacsecCapabilitiesInterfacesEntry 4 }

vtssMacsecCapabilitiesInterfacesGcmAesXpn128 OBJECT-TYPE
    SYNTAX      TruthValue
    MAX-ACCESS  read-only
    STATUS      current
    DESCRIPTION
        "True if this interface supports the GCM-AES-XPN-128 cipher suite"
    ::= { vtssMacsecCapabilitiesInterfacesEntry 5 }

vtssMacsecCapabilitiesInterfacesGcmAesXpn256 OBJECT-TYPE
    SYNTAX      TruthValue
    MAX-ACCESS  read-only
    STATUS      current
    DESCRIPTION
        "True if this interface supports the GCM-AES-XPN-256 cipher suite"
    ::= { vtssMacsecCapabilitiesInterfacesEntry 6 }

vtssMacsecCapabilitiesInterfacesTotalRxSaCnt OBJECT-TYPE
    SYNTAX      Unsigned32
    MAX-ACCESS  read-only
    STATUS      current
    DESCRIPTION
        "Total number of supported Rx Secure Associations."
    ::= { vtssMacsecCapabilitiesInterfacesEntry 7 }

vtssMacsecCapabilitiesInterfacesTotalTxSaCnt OBJECT-TYPE
    SYNTAX      Unsigned32
    MAX-ACCESS  read-only
    STATUS      current
    DESCRIPTION
        "Total number of supported Tx Secure Associations."
    ::= { vtssMacsecCapabilitiesInterfacesEntry 8 }

vtssMacsecCapabilitiesInterfacesSecyCntMax OBJECT-TYPE
    SYNTAX      Unsigned32
    MAX-ACCESS  read-only
    STATUS      current
    DESCRIPTION
        "Maximum number of SecYs that can be configured on this interface."
    ::= { vtssMacsecCapabilitiesInterfacesEntry 9 }

vtssMacsecCapabilitiesInterfacesTxScCntPerSecyMax OBJECT-TYPE
    SYNTAX      Unsigned32
    MAX-ACCESS  read-only
    STATUS      current
    DESCRIPTION
        "Maximum number of Tx Secure Channels that can be configured per SecY.
         Always 1."
    ::= { vtssMacsecCapabilitiesInterfacesEntry 10 }

vtssMacsecCapabilitiesInterfacesRxScCntPerSecyMax OBJECT-TYPE
    SYNTAX      Unsigned32
    MAX-ACCESS  read-only
    STATUS      current
    DESCRIPTION
        "Maximum number of Rx Secure Channels that can be configured per SecY."
    ::= { vtssMacsecCapabilitiesInterfacesEntry 11 }

vtssMacsecCapabilitiesInterfacesTxSaCntPerScMax OBJECT-TYPE
    SYNTAX      Unsigned32
    MAX-ACCESS  read-only
    STATUS      current
    DESCRIPTION
        "Maximum number of Tx Secure Associations that can be configured per Tx
         Secure Channel."
    ::= { vtssMacsecCapabilitiesInterfacesEntry 12 }

vtssMacsecCapabilitiesInterfacesRxSaCntPerScMax OBJECT-TYPE
    SYNTAX      Unsigned32
    MAX-ACCESS  read-only
    STATUS      current
    DESCRIPTION
        "Maximum number of Rx Secure Associations that can be configured per Rx
         Secure Channel."
    ::= { vtssMacsecCapabilitiesInterfacesEntry 13 }

vtssMacsecConfig OBJECT IDENTIFIER
    ::= { vtssMacsecMibObjects 2 }

vtssMacsecConfigPortTable OBJECT-TYPE
    SYNTAX      SEQUENCE OF VTSSMacsecConfigPortEntry
    MAX-ACCESS  not-accessible
    STATUS      current
    DESCRIPTION
        "Enable or disable MACsec on a given interface."
    ::= { vtssMacsecConfig 1 }

vtssMacsecConfigPortEntry OBJECT-TYPE
    SYNTAX      VTSSMacsecConfigPortEntry
    MAX-ACCESS  not-accessible
    STATUS      current
    DESCRIPTION
        "Each entry in this table represents a port interface where MACsec - if
         supported - can be enabled."
    INDEX       { vtssMacsecConfigPortIfIndex }
    ::= { vtssMacsecConfigPortTable 1 }

VTSSMacsecConfigPortEntry ::= SEQUENCE {
    vtssMacsecConfigPortIfIndex  VTSSInterfaceIndex,
    vtssMacsecConfigPortEnable   TruthValue
}

vtssMacsecConfigPortIfIndex OBJECT-TYPE
    SYNTAX      VTSSInterfaceIndex
    MAX-ACCESS  accessible-for-notify
    STATUS      current
    DESCRIPTION
        "Logical port interface number."
    ::= { vtssMacsecConfigPortEntry 1 }

vtssMacsecConfigPortEnable OBJECT-TYPE
    SYNTAX      TruthValue
    MAX-ACCESS  read-write
    STATUS      current
    DESCRIPTION
        "Set to true to enable MACsec on this interface, false to disable. Once
         enabled, it is possible to add SecYs. Disabling causes possible SecYs
         to be deleted."
    ::= { vtssMacsecConfigPortEntry 2 }

vtssMacsecConfigSecyTable OBJECT-TYPE
    SYNTAX      SEQUENCE OF VTSSMacsecConfigSecyEntry
    MAX-ACCESS  not-accessible
    STATUS      current
    DESCRIPTION
        "Configure a SecY on a given interface."
    ::= { vtssMacsecConfig 2 }

vtssMacsecConfigSecyEntry OBJECT-TYPE
    SYNTAX      VTSSMacsecConfigSecyEntry
    MAX-ACCESS  not-accessible
    STATUS      current
    DESCRIPTION
        "Each entry in this table represents a SecY on a given interface."
    INDEX       { vtssMacsecConfigSecyIfIndex,
                  vtssMacsecConfigSecySecyId }
    ::= { vtssMacsecConfigSecyTable 1 }

VTSSMacsecConfigSecyEntry ::= SEQUENCE {
    vtssMacsecConfigSecyIfIndex                VTSSInterfaceIndex,
    vtssMacsecConfigSecySecyId                 Unsigned32,
    vtssMacsecConfigSecyAdminActive            TruthValue,
    vtssMacsecConfigSecyVirtualPortId          VTSSUnsigned16,
    vtssMacsecConfigSecyCipherSuite            VTSSMacsecCipherSuite,
    vtssMacsecConfigSecyConfidentialityOffset  Unsigned32,
    vtssMacsecConfigSecyTxProtectFrames        TruthValue,
    vtssMacsecConfigSecyTxAlwaysIncludeSci     TruthValue,
    vtssMacsecConfigSecyTxUseES                TruthValue,
    vtssMacsecConfigSecyTxUseSCB               TruthValue,
    vtssMacsecConfigSecyRxFrameValidation      VTSSMacsecFrameValidation,
    vtssMacsecConfigSecyRxReplayProtect        TruthValue,
    vtssMacsecConfigSecyRxReplayWindow         Unsigned32,
    vtssMacsecConfigSecyTxScConfigured         TruthValue,
    vtssMacsecConfigSecyTxScMacType            VTSSMacsecTxScMacType,
    vtssMacsecConfigSecyTxScCustomMac          MacAddress,
    vtssMacsecConfigSecyTxSa1Configured        TruthValue,
    vtssMacsecConfigSecyTxSa1Active            TruthValue,
    vtssMacsecConfigSecyTxSa1NextPN            VTSSUnsigned64,
    vtssMacsecConfigSecyTxSa1Encrypt           TruthValue,
    vtssMacsecConfigSecyTxSa1Key               VTSSDisplayString,
    vtssMacsecConfigSecyTxSa1Salt              VTSSDisplayString,
    vtssMacsecConfigSecyTxSa2Configured        TruthValue,
    vtssMacsecConfigSecyTxSa2Active            TruthValue,
    vtssMacsecConfigSecyTxSa2NextPN            VTSSUnsigned64,
    vtssMacsecConfigSecyTxSa2Encrypt           TruthValue,
    vtssMacsecConfigSecyTxSa2Key               VTSSDisplayString,
    vtssMacsecConfigSecyTxSa2Salt              VTSSDisplayString,
    vtssMacsecConfigSecyTxSa3Configured        TruthValue,
    vtssMacsecConfigSecyTxSa3Active            TruthValue,
    vtssMacsecConfigSecyTxSa3NextPN            VTSSUnsigned64,
    vtssMacsecConfigSecyTxSa3Encrypt           TruthValue,
    vtssMacsecConfigSecyTxSa3Key               VTSSDisplayString,
    vtssMacsecConfigSecyTxSa3Salt              VTSSDisplayString,
    vtssMacsecConfigSecyTxSa4Configured        TruthValue,
    vtssMacsecConfigSecyTxSa4Active            TruthValue,
    vtssMacsecConfigSecyTxSa4NextPN            VTSSUnsigned64,
    vtssMacsecConfigSecyTxSa4Encrypt           TruthValue,
    vtssMacsecConfigSecyTxSa4Key               VTSSDisplayString,
    vtssMacsecConfigSecyTxSa4Salt              VTSSDisplayString,
    vtssMacsecConfigSecyRxSc1Configured        TruthValue,
    vtssMacsecConfigSecyRxSc1PeerMac           MacAddress,
    vtssMacsecConfigSecyRxSc1Sa1Configured     TruthValue,
    vtssMacsecConfigSecyRxSc1Sa1Active         TruthValue,
    vtssMacsecConfigSecyRxSc1Sa1LowestPN       VTSSUnsigned64,
    vtssMacsecConfigSecyRxSc1Sa1Key            VTSSDisplayString,
    vtssMacsecConfigSecyRxSc1Sa1Salt           VTSSDisplayString,
    vtssMacsecConfigSecyRxSc1Sa2Configured     TruthValue,
    vtssMacsecConfigSecyRxSc1Sa2Active         TruthValue,
    vtssMacsecConfigSecyRxSc1Sa2LowestPN       VTSSUnsigned64,
    vtssMacsecConfigSecyRxSc1Sa2Key            VTSSDisplayString,
    vtssMacsecConfigSecyRxSc1Sa2Salt           VTSSDisplayString,
    vtssMacsecConfigSecyRxSc1Sa3Configured     TruthValue,
    vtssMacsecConfigSecyRxSc1Sa3Active         TruthValue,
    vtssMacsecConfigSecyRxSc1Sa3LowestPN       VTSSUnsigned64,
    vtssMacsecConfigSecyRxSc1Sa3Key            VTSSDisplayString,
    vtssMacsecConfigSecyRxSc1Sa3Salt           VTSSDisplayString,
    vtssMacsecConfigSecyRxSc1Sa4Configured     TruthValue,
    vtssMacsecConfigSecyRxSc1Sa4Active         TruthValue,
    vtssMacsecConfigSecyRxSc1Sa4LowestPN       VTSSUnsigned64,
    vtssMacsecConfigSecyRxSc1Sa4Key            VTSSDisplayString,
    vtssMacsecConfigSecyRxSc1Sa4Salt           VTSSDisplayString,
    vtssMacsecConfigSecyRxSc2Configured        TruthValue,
    vtssMacsecConfigSecyRxSc2PeerMac           MacAddress,
    vtssMacsecConfigSecyRxSc2Sa1Configured     TruthValue,
    vtssMacsecConfigSecyRxSc2Sa1Active         TruthValue,
    vtssMacsecConfigSecyRxSc2Sa1LowestPN       VTSSUnsigned64,
    vtssMacsecConfigSecyRxSc2Sa1Key            VTSSDisplayString,
    vtssMacsecConfigSecyRxSc2Sa1Salt           VTSSDisplayString,
    vtssMacsecConfigSecyRxSc2Sa2Configured     TruthValue,
    vtssMacsecConfigSecyRxSc2Sa2Active         TruthValue,
    vtssMacsecConfigSecyRxSc2Sa2LowestPN       VTSSUnsigned64,
    vtssMacsecConfigSecyRxSc2Sa2Key            VTSSDisplayString,
    vtssMacsecConfigSecyRxSc2Sa2Salt           VTSSDisplayString,
    vtssMacsecConfigSecyRxSc2Sa3Configured     TruthValue,
    vtssMacsecConfigSecyRxSc2Sa3Active         TruthValue,
    vtssMacsecConfigSecyRxSc2Sa3LowestPN       VTSSUnsigned64,
    vtssMacsecConfigSecyRxSc2Sa3Key            VTSSDisplayString,
    vtssMacsecConfigSecyRxSc2Sa3Salt           VTSSDisplayString,
    vtssMacsecConfigSecyRxSc2Sa4Configured     TruthValue,
    vtssMacsecConfigSecyRxSc2Sa4Active         TruthValue,
    vtssMacsecConfigSecyRxSc2Sa4LowestPN       VTSSUnsigned64,
    vtssMacsecConfigSecyRxSc2Sa4Key            VTSSDisplayString,
    vtssMacsecConfigSecyRxSc2Sa4Salt           VTSSDisplayString,
    vtssMacsecConfigSecyRxSc3Configured        TruthValue,
    vtssMacsecConfigSecyRxSc3PeerMac           MacAddress,
    vtssMacsecConfigSecyRxSc3Sa1Configured     TruthValue,
    vtssMacsecConfigSecyRxSc3Sa1Active         TruthValue,
    vtssMacsecConfigSecyRxSc3Sa1LowestPN       VTSSUnsigned64,
    vtssMacsecConfigSecyRxSc3Sa1Key            VTSSDisplayString,
    vtssMacsecConfigSecyRxSc3Sa1Salt           VTSSDisplayString,
    vtssMacsecConfigSecyRxSc3Sa2Configured     TruthValue,
    vtssMacsecConfigSecyRxSc3Sa2Active         TruthValue,
    vtssMacsecConfigSecyRxSc3Sa2LowestPN       VTSSUnsigned64,
    vtssMacsecConfigSecyRxSc3Sa2Key            VTSSDisplayString,
    vtssMacsecConfigSecyRxSc3Sa2Salt           VTSSDisplayString,
    vtssMacsecConfigSecyRxSc3Sa3Configured     TruthValue,
    vtssMacsecConfigSecyRxSc3Sa3Active         TruthValue,
    vtssMacsecConfigSecyRxSc3Sa3LowestPN       VTSSUnsigned64,
    vtssMacsecConfigSecyRxSc3Sa3Key            VTSSDisplayString,
    vtssMacsecConfigSecyRxSc3Sa3Salt           VTSSDisplayString,
    vtssMacsecConfigSecyRxSc3Sa4Configured     TruthValue,
    vtssMacsecConfigSecyRxSc3Sa4Active         TruthValue,
    vtssMacsecConfigSecyRxSc3Sa4LowestPN       VTSSUnsigned64,
    vtssMacsecConfigSecyRxSc3Sa4Key            VTSSDisplayString,
    vtssMacsecConfigSecyRxSc3Sa4Salt           VTSSDisplayString,
    vtssMacsecConfigSecyRxSc4Configured        TruthValue,
    vtssMacsecConfigSecyRxSc4PeerMac           MacAddress,
    vtssMacsecConfigSecyRxSc4Sa1Configured     TruthValue,
    vtssMacsecConfigSecyRxSc4Sa1Active         TruthValue,
    vtssMacsecConfigSecyRxSc4Sa1LowestPN       VTSSUnsigned64,
    vtssMacsecConfigSecyRxSc4Sa1Key            VTSSDisplayString,
    vtssMacsecConfigSecyRxSc4Sa1Salt           VTSSDisplayString,
    vtssMacsecConfigSecyRxSc4Sa2Configured     TruthValue,
    vtssMacsecConfigSecyRxSc4Sa2Active         TruthValue,
    vtssMacsecConfigSecyRxSc4Sa2LowestPN       VTSSUnsigned64,
    vtssMacsecConfigSecyRxSc4Sa2Key            VTSSDisplayString,
    vtssMacsecConfigSecyRxSc4Sa2Salt           VTSSDisplayString,
    vtssMacsecConfigSecyRxSc4Sa3Configured     TruthValue,
    vtssMacsecConfigSecyRxSc4Sa3Active         TruthValue,
    vtssMacsecConfigSecyRxSc4Sa3LowestPN       VTSSUnsigned64,
    vtssMacsecConfigSecyRxSc4Sa3Key            VTSSDisplayString,
    vtssMacsecConfigSecyRxSc4Sa3Salt           VTSSDisplayString,
    vtssMacsecConfigSecyRxSc4Sa4Configured     TruthValue,
    vtssMacsecConfigSecyRxSc4Sa4Active         TruthValue,
    vtssMacsecConfigSecyRxSc4Sa4LowestPN       VTSSUnsigned64,
    vtssMacsecConfigSecyRxSc4Sa4Key            VTSSDisplayString,
    vtssMacsecConfigSecyRxSc4Sa4Salt           VTSSDisplayString,
    vtssMacsecConfigSecyRxSc5Configured        TruthValue,
    vtssMacsecConfigSecyRxSc5PeerMac           MacAddress,
    vtssMacsecConfigSecyRxSc5Sa1Configured     TruthValue,
    vtssMacsecConfigSecyRxSc5Sa1Active         TruthValue,
    vtssMacsecConfigSecyRxSc5Sa1LowestPN       VTSSUnsigned64,
    vtssMacsecConfigSecyRxSc5Sa1Key            VTSSDisplayString,
    vtssMacsecConfigSecyRxSc5Sa1Salt           VTSSDisplayString,
    vtssMacsecConfigSecyRxSc5Sa2Configured     TruthValue,
    vtssMacsecConfigSecyRxSc5Sa2Active         TruthValue,
    vtssMacsecConfigSecyRxSc5Sa2LowestPN       VTSSUnsigned64,
    vtssMacsecConfigSecyRxSc5Sa2Key            VTSSDisplayString,
    vtssMacsecConfigSecyRxSc5Sa2Salt           VTSSDisplayString,
    vtssMacsecConfigSecyRxSc5Sa3Configured     TruthValue,
    vtssMacsecConfigSecyRxSc5Sa3Active         TruthValue,
    vtssMacsecConfigSecyRxSc5Sa3LowestPN       VTSSUnsigned64,
    vtssMacsecConfigSecyRxSc5Sa3Key            VTSSDisplayString,
    vtssMacsecConfigSecyRxSc5Sa3Salt           VTSSDisplayString,
    vtssMacsecConfigSecyRxSc5Sa4Configured     TruthValue,
    vtssMacsecConfigSecyRxSc5Sa4Active         TruthValue,
    vtssMacsecConfigSecyRxSc5Sa4LowestPN       VTSSUnsigned64,
    vtssMacsecConfigSecyRxSc5Sa4Key            VTSSDisplayString,
    vtssMacsecConfigSecyRxSc5Sa4Salt           VTSSDisplayString,
    vtssMacsecConfigSecyRxSc6Configured        TruthValue,
    vtssMacsecConfigSecyRxSc6PeerMac           MacAddress,
    vtssMacsecConfigSecyRxSc6Sa1Configured     TruthValue,
    vtssMacsecConfigSecyRxSc6Sa1Active         TruthValue,
    vtssMacsecConfigSecyRxSc6Sa1LowestPN       VTSSUnsigned64,
    vtssMacsecConfigSecyRxSc6Sa1Key            VTSSDisplayString,
    vtssMacsecConfigSecyRxSc6Sa1Salt           VTSSDisplayString,
    vtssMacsecConfigSecyRxSc6Sa2Configured     TruthValue,
    vtssMacsecConfigSecyRxSc6Sa2Active         TruthValue,
    vtssMacsecConfigSecyRxSc6Sa2LowestPN       VTSSUnsigned64,
    vtssMacsecConfigSecyRxSc6Sa2Key            VTSSDisplayString,
    vtssMacsecConfigSecyRxSc6Sa2Salt           VTSSDisplayString,
    vtssMacsecConfigSecyRxSc6Sa3Configured     TruthValue,
    vtssMacsecConfigSecyRxSc6Sa3Active         TruthValue,
    vtssMacsecConfigSecyRxSc6Sa3LowestPN       VTSSUnsigned64,
    vtssMacsecConfigSecyRxSc6Sa3Key            VTSSDisplayString,
    vtssMacsecConfigSecyRxSc6Sa3Salt           VTSSDisplayString,
    vtssMacsecConfigSecyRxSc6Sa4Configured     TruthValue,
    vtssMacsecConfigSecyRxSc6Sa4Active         TruthValue,
    vtssMacsecConfigSecyRxSc6Sa4LowestPN       VTSSUnsigned64,
    vtssMacsecConfigSecyRxSc6Sa4Key            VTSSDisplayString,
    vtssMacsecConfigSecyRxSc6Sa4Salt           VTSSDisplayString,
    vtssMacsecConfigSecyRxSc7Configured        TruthValue,
    vtssMacsecConfigSecyRxSc7PeerMac           MacAddress,
    vtssMacsecConfigSecyRxSc7Sa1Configured     TruthValue,
    vtssMacsecConfigSecyRxSc7Sa1Active         TruthValue,
    vtssMacsecConfigSecyRxSc7Sa1LowestPN       VTSSUnsigned64,
    vtssMacsecConfigSecyRxSc7Sa1Key            VTSSDisplayString,
    vtssMacsecConfigSecyRxSc7Sa1Salt           VTSSDisplayString,
    vtssMacsecConfigSecyRxSc7Sa2Configured     TruthValue,
    vtssMacsecConfigSecyRxSc7Sa2Active         TruthValue,
    vtssMacsecConfigSecyRxSc7Sa2LowestPN       VTSSUnsigned64,
    vtssMacsecConfigSecyRxSc7Sa2Key            VTSSDisplayString,
    vtssMacsecConfigSecyRxSc7Sa2Salt           VTSSDisplayString,
    vtssMacsecConfigSecyRxSc7Sa3Configured     TruthValue,
    vtssMacsecConfigSecyRxSc7Sa3Active         TruthValue,
    vtssMacsecConfigSecyRxSc7Sa3LowestPN       VTSSUnsigned64,
    vtssMacsecConfigSecyRxSc7Sa3Key            VTSSDisplayString,
    vtssMacsecConfigSecyRxSc7Sa3Salt           VTSSDisplayString,
    vtssMacsecConfigSecyRxSc7Sa4Configured     TruthValue,
    vtssMacsecConfigSecyRxSc7Sa4Active         TruthValue,
    vtssMacsecConfigSecyRxSc7Sa4LowestPN       VTSSUnsigned64,
    vtssMacsecConfigSecyRxSc7Sa4Key            VTSSDisplayString,
    vtssMacsecConfigSecyRxSc7Sa4Salt           VTSSDisplayString,
    vtssMacsecConfigSecyRxSc8Configured        TruthValue,
    vtssMacsecConfigSecyRxSc8PeerMac           MacAddress,
    vtssMacsecConfigSecyRxSc8Sa1Configured     TruthValue,
    vtssMacsecConfigSecyRxSc8Sa1Active         TruthValue,
    vtssMacsecConfigSecyRxSc8Sa1LowestPN       VTSSUnsigned64,
    vtssMacsecConfigSecyRxSc8Sa1Key            VTSSDisplayString,
    vtssMacsecConfigSecyRxSc8Sa1Salt           VTSSDisplayString,
    vtssMacsecConfigSecyRxSc8Sa2Configured     TruthValue,
    vtssMacsecConfigSecyRxSc8Sa2Active         TruthValue,
    vtssMacsecConfigSecyRxSc8Sa2LowestPN       VTSSUnsigned64,
    vtssMacsecConfigSecyRxSc8Sa2Key            VTSSDisplayString,
    vtssMacsecConfigSecyRxSc8Sa2Salt           VTSSDisplayString,
    vtssMacsecConfigSecyRxSc8Sa3Configured     TruthValue,
    vtssMacsecConfigSecyRxSc8Sa3Active         TruthValue,
    vtssMacsecConfigSecyRxSc8Sa3LowestPN       VTSSUnsigned64,
    vtssMacsecConfigSecyRxSc8Sa3Key            VTSSDisplayString,
    vtssMacsecConfigSecyRxSc8Sa3Salt           VTSSDisplayString,
    vtssMacsecConfigSecyRxSc8Sa4Configured     TruthValue,
    vtssMacsecConfigSecyRxSc8Sa4Active         TruthValue,
    vtssMacsecConfigSecyRxSc8Sa4LowestPN       VTSSUnsigned64,
    vtssMacsecConfigSecyRxSc8Sa4Key            VTSSDisplayString,
    vtssMacsecConfigSecyRxSc8Sa4Salt           VTSSDisplayString,
    vtssMacsecConfigSecyAction                 VTSSRowEditorState
}

vtssMacsecConfigSecyIfIndex OBJECT-TYPE
    SYNTAX      VTSSInterfaceIndex
    MAX-ACCESS  accessible-for-notify
    STATUS      current
    DESCRIPTION
        "Logical port interface index."
    ::= { vtssMacsecConfigSecyEntry 1 }

vtssMacsecConfigSecySecyId OBJECT-TYPE
    SYNTAX      Unsigned32
    MAX-ACCESS  accessible-for-notify
    STATUS      current
    DESCRIPTION
        "SecY IDs are numbered 1 through maximum number of SecYs support on an
         interface."
    ::= { vtssMacsecConfigSecyEntry 2 }

vtssMacsecConfigSecyAdminActive OBJECT-TYPE
    SYNTAX      TruthValue
    MAX-ACCESS  read-write
    STATUS      current
    DESCRIPTION
        "Controls whether this SecY is applied to H/W or not."
    ::= { vtssMacsecConfigSecyEntry 3 }

vtssMacsecConfigSecyVirtualPortId OBJECT-TYPE
    SYNTAX      VTSSUnsigned16
    MAX-ACCESS  read-write
    STATUS      current
    DESCRIPTION
        "The virtual port ID is used in the SCI tag if present. Changing the
         virtual port ID causes all Secure Channels and their Secure
         Associations to be recreated."
    ::= { vtssMacsecConfigSecyEntry 4 }

vtssMacsecConfigSecyCipherSuite OBJECT-TYPE
    SYNTAX      VTSSMacsecCipherSuite
    MAX-ACCESS  read-write
    STATUS      current
    DESCRIPTION
        "The cipher suite to be used by all used SCs in this SecY. Changing the
         cipher suite from a 128- to a 256-bit or vice versa requires all SAs to
         be removed before-hand."
    ::= { vtssMacsecConfigSecyEntry 5 }

vtssMacsecConfigSecyConfidentialityOffset OBJECT-TYPE
    SYNTAX      Unsigned32
    MAX-ACCESS  read-write
    STATUS      current
    DESCRIPTION
        "Select the offset into frames where encryption and decryption starts."
    ::= { vtssMacsecConfigSecyEntry 6 }

vtssMacsecConfigSecyTxProtectFrames OBJECT-TYPE
    SYNTAX      TruthValue
    MAX-ACCESS  read-write
    STATUS      current
    DESCRIPTION
        "If true, frames will be MACsec encapsulated with an ICV. If Encrypt is
         also set, the data will be encrypted. If false, frames will pass
         through the crypto-core without modification."
    ::= { vtssMacsecConfigSecyEntry 7 }

vtssMacsecConfigSecyTxAlwaysIncludeSci OBJECT-TYPE
    SYNTAX      TruthValue
    MAX-ACCESS  read-write
    STATUS      current
    DESCRIPTION
        "If true, the SCI will be included in the SecTAG."
    ::= { vtssMacsecConfigSecyEntry 8 }

vtssMacsecConfigSecyTxUseES OBJECT-TYPE
    SYNTAX      TruthValue
    MAX-ACCESS  read-write
    STATUS      current
    DESCRIPTION
        "Enables the use of the ES (End Station) bit in the SecTAG when
         transmitting protected frames."
    ::= { vtssMacsecConfigSecyEntry 9 }

vtssMacsecConfigSecyTxUseSCB OBJECT-TYPE
    SYNTAX      TruthValue
    MAX-ACCESS  read-write
    STATUS      current
    DESCRIPTION
        "Enables the use of the SCB (Single Copy Broadcast) bit in the SecTAG
         when transmitting protected frames."
    ::= { vtssMacsecConfigSecyEntry 10 }

vtssMacsecConfigSecyRxFrameValidation OBJECT-TYPE
    SYNTAX      VTSSMacsecFrameValidation
    MAX-ACCESS  read-write
    STATUS      current
    DESCRIPTION
        "Controls how MACsec handles the ICV of incoming frames."
    ::= { vtssMacsecConfigSecyEntry 11 }

vtssMacsecConfigSecyRxReplayProtect OBJECT-TYPE
    SYNTAX      TruthValue
    MAX-ACCESS  read-write
    STATUS      current
    DESCRIPTION
        "If true, frames arriving with a packet number outside the replay
         protect window are discarded. If false, such frames are allowed."
    ::= { vtssMacsecConfigSecyEntry 12 }

vtssMacsecConfigSecyRxReplayWindow OBJECT-TYPE
    SYNTAX      Unsigned32
    MAX-ACCESS  read-write
    STATUS      current
    DESCRIPTION
        "Controls the window size within which a frame's packet number is
         accepted. Only used if ReplayProtect is true."
    ::= { vtssMacsecConfigSecyEntry 13 }

vtssMacsecConfigSecyTxScConfigured OBJECT-TYPE
    SYNTAX      TruthValue
    MAX-ACCESS  read-write
    STATUS      current
    DESCRIPTION
        "If true, this Tx SC will be be applied to H/W. Set to false to remove."
    ::= { vtssMacsecConfigSecyEntry 22 }

vtssMacsecConfigSecyTxScMacType OBJECT-TYPE
    SYNTAX      VTSSMacsecTxScMacType
    MAX-ACCESS  read-write
    STATUS      current
    DESCRIPTION
        "Set to Management to use the switch's management MAC address, or set to
         Port to use this interface's MAC address, or set to Custom to use the
         CustomMac in this Tx SC."
    ::= { vtssMacsecConfigSecyEntry 23 }

vtssMacsecConfigSecyTxScCustomMac OBJECT-TYPE
    SYNTAX      MacAddress
    MAX-ACCESS  read-write
    STATUS      current
    DESCRIPTION
        "When MacType is set to Custom, this is this Tx SC's MacAddress.
         Otherwise unused."
    ::= { vtssMacsecConfigSecyEntry 24 }

vtssMacsecConfigSecyTxSa1Configured OBJECT-TYPE
    SYNTAX      TruthValue
    MAX-ACCESS  read-write
    STATUS      current
    DESCRIPTION
        "If true, this Tx SA will be applied to H/W. Set to false to remove"
    ::= { vtssMacsecConfigSecyEntry 33 }

vtssMacsecConfigSecyTxSa1Active OBJECT-TYPE
    SYNTAX      TruthValue
    MAX-ACCESS  read-write
    STATUS      current
    DESCRIPTION
        "When the SecY is administratively enabled, exactly one Tx SA must be
         active."
    ::= { vtssMacsecConfigSecyEntry 34 }

vtssMacsecConfigSecyTxSa1NextPN OBJECT-TYPE
    SYNTAX      VTSSUnsigned64
    MAX-ACCESS  read-write
    STATUS      current
    DESCRIPTION
        "Packet number of the first packet sent using this Tx SA."
    ::= { vtssMacsecConfigSecyEntry 35 }

vtssMacsecConfigSecyTxSa1Encrypt OBJECT-TYPE
    SYNTAX      TruthValue
    MAX-ACCESS  read-write
    STATUS      current
    DESCRIPTION
        "Set to true to encrypt user data for this Tx SA. Set to false to only
         integrity protect."
    ::= { vtssMacsecConfigSecyEntry 36 }

vtssMacsecConfigSecyTxSa1Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyEntry 37 }

vtssMacsecConfigSecyTxSa1Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyEntry 38 }

vtssMacsecConfigSecyTxSa2Configured OBJECT-TYPE
    SYNTAX      TruthValue
    MAX-ACCESS  read-write
    STATUS      current
    DESCRIPTION
        "If true, this Tx SA will be applied to H/W. Set to false to remove"
    ::= { vtssMacsecConfigSecyEntry 44 }

vtssMacsecConfigSecyTxSa2Active OBJECT-TYPE
    SYNTAX      TruthValue
    MAX-ACCESS  read-write
    STATUS      current
    DESCRIPTION
        "When the SecY is administratively enabled, exactly one Tx SA must be
         active."
    ::= { vtssMacsecConfigSecyEntry 45 }

vtssMacsecConfigSecyTxSa2NextPN OBJECT-TYPE
    SYNTAX      VTSSUnsigned64
    MAX-ACCESS  read-write
    STATUS      current
    DESCRIPTION
        "Packet number of the first packet sent using this Tx SA."
    ::= { vtssMacsecConfigSecyEntry 46 }

vtssMacsecConfigSecyTxSa2Encrypt OBJECT-TYPE
    SYNTAX      TruthValue
    MAX-ACCESS  read-write
    STATUS      current
    DESCRIPTION
        "Set to true to encrypt user data for this Tx SA. Set to false to only
         integrity protect."
    ::= { vtssMacsecConfigSecyEntry 47 }

vtssMacsecConfigSecyTxSa2Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyEntry 48 }

vtssMacsecConfigSecyTxSa2Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyEntry 49 }

vtssMacsecConfigSecyTxSa3Configured OBJECT-TYPE
    SYNTAX      TruthValue
    MAX-ACCESS  read-write
    STATUS      current
    DESCRIPTION
        "If true, this Tx SA will be applied to H/W. Set to false to remove"
    ::= { vtssMacsecConfigSecyEntry 55 }

vtssMacsecConfigSecyTxSa3Active OBJECT-TYPE
    SYNTAX      TruthValue
    MAX-ACCESS  read-write
    STATUS      current
    DESCRIPTION
        "When the SecY is administratively enabled, exactly one Tx SA must be
         active."
    ::= { vtssMacsecConfigSecyEntry 56 }

vtssMacsecConfigSecyTxSa3NextPN OBJECT-TYPE
    SYNTAX      VTSSUnsigned64
    MAX-ACCESS  read-write
    STATUS      current
    DESCRIPTION
        "Packet number of the first packet sent using this Tx SA."
    ::= { vtssMacsecConfigSecyEntry 57 }

vtssMacsecConfigSecyTxSa3Encrypt OBJECT-TYPE
    SYNTAX      TruthValue
    MAX-ACCESS  read-write
    STATUS      current
    DESCRIPTION
        "Set to true to encrypt user data for this Tx SA. Set to false to only
         integrity protect."
    ::= { vtssMacsecConfigSecyEntry 58 }

vtssMacsecConfigSecyTxSa3Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyEntry 59 }

vtssMacsecConfigSecyTxSa3Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyEntry 60 }

vtssMacsecConfigSecyTxSa4Configured OBJECT-TYPE
    SYNTAX      TruthValue
    MAX-ACCESS  read-write
    STATUS      current
    DESCRIPTION
        "If true, this Tx SA will be applied to H/W. Set to false to remove"
    ::= { vtssMacsecConfigSecyEntry 66 }

vtssMacsecConfigSecyTxSa4Active OBJECT-TYPE
    SYNTAX      TruthValue
    MAX-ACCESS  read-write
    STATUS      current
    DESCRIPTION
        "When the SecY is administratively enabled, exactly one Tx SA must be
         active."
    ::= { vtssMacsecConfigSecyEntry 67 }

vtssMacsecConfigSecyTxSa4NextPN OBJECT-TYPE
    SYNTAX      VTSSUnsigned64
    MAX-ACCESS  read-write
    STATUS      current
    DESCRIPTION
        "Packet number of the first packet sent using this Tx SA."
    ::= { vtssMacsecConfigSecyEntry 68 }

vtssMacsecConfigSecyTxSa4Encrypt OBJECT-TYPE
    SYNTAX      TruthValue
    MAX-ACCESS  read-write
    STATUS      current
    DESCRIPTION
        "Set to true to encrypt user data for this Tx SA. Set to false to only
         integrity protect."
    ::= { vtssMacsecConfigSecyEntry 69 }

vtssMacsecConfigSecyTxSa4Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyEntry 70 }

vtssMacsecConfigSecyTxSa4Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyEntry 71 }

vtssMacsecConfigSecyRxSc1Configured OBJECT-TYPE
    SYNTAX      TruthValue
    MAX-ACCESS  read-write
    STATUS      current
    DESCRIPTION
        "If true, this Rx SC will be be applied to H/W. Set to false to remove."
    ::= { vtssMacsecConfigSecyEntry 77 }

vtssMacsecConfigSecyRxSc1PeerMac OBJECT-TYPE
    SYNTAX      MacAddress
    MAX-ACCESS  read-write
    STATUS      current
    DESCRIPTION
        "The MAC address of the peer (the one who sends MACsec encapsulated
         frames to us."
    ::= { vtssMacsecConfigSecyEntry 78 }

vtssMacsecConfigSecyRxSc1Sa1Configured OBJECT-TYPE
    SYNTAX      TruthValue
    MAX-ACCESS  read-write
    STATUS      current
    DESCRIPTION
        "If true, this Rx SA will be applied to H/W. Set to false to remove."
    ::= { vtssMacsecConfigSecyEntry 87 }

vtssMacsecConfigSecyRxSc1Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 88 }

vtssMacsecConfigSecyRxSc1Sa1LowestPN OBJECT-TYPE
    SYNTAX      VTSSUnsigned64
    MAX-ACCESS  read-write
    STATUS      current
    DESCRIPTION
        "The lowest packet number associated with this Rx SA."
    ::= { vtssMacsecConfigSecyEntry 89 }

vtssMacsecConfigSecyRxSc1Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 90 }

vtssMacsecConfigSecyRxSc1Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 91 }

vtssMacsecConfigSecyRxSc1Sa2Configured OBJECT-TYPE
    SYNTAX      TruthValue
    MAX-ACCESS  read-write
    STATUS      current
    DESCRIPTION
        "If true, this Rx SA will be applied to H/W. Set to false to remove."
    ::= { vtssMacsecConfigSecyEntry 97 }

vtssMacsecConfigSecyRxSc1Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 98 }

vtssMacsecConfigSecyRxSc1Sa2LowestPN OBJECT-TYPE
    SYNTAX      VTSSUnsigned64
    MAX-ACCESS  read-write
    STATUS      current
    DESCRIPTION
        "The lowest packet number associated with this Rx SA."
    ::= { vtssMacsecConfigSecyEntry 99 }

vtssMacsecConfigSecyRxSc1Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 100 }

vtssMacsecConfigSecyRxSc1Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 101 }

vtssMacsecConfigSecyRxSc1Sa3Configured OBJECT-TYPE
    SYNTAX      TruthValue
    MAX-ACCESS  read-write
    STATUS      current
    DESCRIPTION
        "If true, this Rx SA will be applied to H/W. Set to false to remove."
    ::= { vtssMacsecConfigSecyEntry 107 }

vtssMacsecConfigSecyRxSc1Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 108 }

vtssMacsecConfigSecyRxSc1Sa3LowestPN OBJECT-TYPE
    SYNTAX      VTSSUnsigned64
    MAX-ACCESS  read-write
    STATUS      current
    DESCRIPTION
        "The lowest packet number associated with this Rx SA."
    ::= { vtssMacsecConfigSecyEntry 109 }

vtssMacsecConfigSecyRxSc1Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 110 }

vtssMacsecConfigSecyRxSc1Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 111 }

vtssMacsecConfigSecyRxSc1Sa4Configured OBJECT-TYPE
    SYNTAX      TruthValue
    MAX-ACCESS  read-write
    STATUS      current
    DESCRIPTION
        "If true, this Rx SA will be applied to H/W. Set to false to remove."
    ::= { vtssMacsecConfigSecyEntry 117 }

vtssMacsecConfigSecyRxSc1Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 118 }

vtssMacsecConfigSecyRxSc1Sa4LowestPN OBJECT-TYPE
    SYNTAX      VTSSUnsigned64
    MAX-ACCESS  read-write
    STATUS      current
    DESCRIPTION
        "The lowest packet number associated with this Rx SA."
    ::= { vtssMacsecConfigSecyEntry 119 }

vtssMacsecConfigSecyRxSc1Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 120 }

vtssMacsecConfigSecyRxSc1Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 121 }

vtssMacsecConfigSecyRxSc2Configured OBJECT-TYPE
    SYNTAX      TruthValue
    MAX-ACCESS  read-write
    STATUS      current
    DESCRIPTION
        "If true, this Rx SC will be be applied to H/W. Set to false to remove."
    ::= { vtssMacsecConfigSecyEntry 127 }

vtssMacsecConfigSecyRxSc2PeerMac OBJECT-TYPE
    SYNTAX      MacAddress
    MAX-ACCESS  read-write
    STATUS      current
    DESCRIPTION
        "The MAC address of the peer (the one who sends MACsec encapsulated
         frames to us."
    ::= { vtssMacsecConfigSecyEntry 128 }

vtssMacsecConfigSecyRxSc2Sa1Configured OBJECT-TYPE
    SYNTAX      TruthValue
    MAX-ACCESS  read-write
    STATUS      current
    DESCRIPTION
        "If true, this Rx SA will be applied to H/W. Set to false to remove."
    ::= { vtssMacsecConfigSecyEntry 137 }

vtssMacsecConfigSecyRxSc2Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 138 }

vtssMacsecConfigSecyRxSc2Sa1LowestPN OBJECT-TYPE
    SYNTAX      VTSSUnsigned64
    MAX-ACCESS  read-write
    STATUS      current
    DESCRIPTION
        "The lowest packet number associated with this Rx SA."
    ::= { vtssMacsecConfigSecyEntry 139 }

vtssMacsecConfigSecyRxSc2Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 140 }

vtssMacsecConfigSecyRxSc2Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 141 }

vtssMacsecConfigSecyRxSc2Sa2Configured OBJECT-TYPE
    SYNTAX      TruthValue
    MAX-ACCESS  read-write
    STATUS      current
    DESCRIPTION
        "If true, this Rx SA will be applied to H/W. Set to false to remove."
    ::= { vtssMacsecConfigSecyEntry 147 }

vtssMacsecConfigSecyRxSc2Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 148 }

vtssMacsecConfigSecyRxSc2Sa2LowestPN OBJECT-TYPE
    SYNTAX      VTSSUnsigned64
    MAX-ACCESS  read-write
    STATUS      current
    DESCRIPTION
        "The lowest packet number associated with this Rx SA."
    ::= { vtssMacsecConfigSecyEntry 149 }

vtssMacsecConfigSecyRxSc2Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 150 }

vtssMacsecConfigSecyRxSc2Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 151 }

vtssMacsecConfigSecyRxSc2Sa3Configured OBJECT-TYPE
    SYNTAX      TruthValue
    MAX-ACCESS  read-write
    STATUS      current
    DESCRIPTION
        "If true, this Rx SA will be applied to H/W. Set to false to remove."
    ::= { vtssMacsecConfigSecyEntry 157 }

vtssMacsecConfigSecyRxSc2Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 158 }

vtssMacsecConfigSecyRxSc2Sa3LowestPN OBJECT-TYPE
    SYNTAX      VTSSUnsigned64
    MAX-ACCESS  read-write
    STATUS      current
    DESCRIPTION
        "The lowest packet number associated with this Rx SA."
    ::= { vtssMacsecConfigSecyEntry 159 }

vtssMacsecConfigSecyRxSc2Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 160 }

vtssMacsecConfigSecyRxSc2Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 161 }

vtssMacsecConfigSecyRxSc2Sa4Configured OBJECT-TYPE
    SYNTAX      TruthValue
    MAX-ACCESS  read-write
    STATUS      current
    DESCRIPTION
        "If true, this Rx SA will be applied to H/W. Set to false to remove."
    ::= { vtssMacsecConfigSecyEntry 167 }

vtssMacsecConfigSecyRxSc2Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 168 }

vtssMacsecConfigSecyRxSc2Sa4LowestPN OBJECT-TYPE
    SYNTAX      VTSSUnsigned64
    MAX-ACCESS  read-write
    STATUS      current
    DESCRIPTION
        "The lowest packet number associated with this Rx SA."
    ::= { vtssMacsecConfigSecyEntry 169 }

vtssMacsecConfigSecyRxSc2Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 170 }

vtssMacsecConfigSecyRxSc2Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 171 }

vtssMacsecConfigSecyRxSc3Configured OBJECT-TYPE
    SYNTAX      TruthValue
    MAX-ACCESS  read-write
    STATUS      current
    DESCRIPTION
        "If true, this Rx SC will be be applied to H/W. Set to false to remove."
    ::= { vtssMacsecConfigSecyEntry 177 }

vtssMacsecConfigSecyRxSc3PeerMac OBJECT-TYPE
    SYNTAX      MacAddress
    MAX-ACCESS  read-write
    STATUS      current
    DESCRIPTION
        "The MAC address of the peer (the one who sends MACsec encapsulated
         frames to us."
    ::= { vtssMacsecConfigSecyEntry 178 }

vtssMacsecConfigSecyRxSc3Sa1Configured OBJECT-TYPE
    SYNTAX      TruthValue
    MAX-ACCESS  read-write
    STATUS      current
    DESCRIPTION
        "If true, this Rx SA will be applied to H/W. Set to false to remove."
    ::= { vtssMacsecConfigSecyEntry 187 }

vtssMacsecConfigSecyRxSc3Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 188 }

vtssMacsecConfigSecyRxSc3Sa1LowestPN OBJECT-TYPE
    SYNTAX      VTSSUnsigned64
    MAX-ACCESS  read-write
    STATUS      current
    DESCRIPTION
        "The lowest packet number associated with this Rx SA."
    ::= { vtssMacsecConfigSecyEntry 189 }

vtssMacsecConfigSecyRxSc3Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 190 }

vtssMacsecConfigSecyRxSc3Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 191 }

vtssMacsecConfigSecyRxSc3Sa2Configured OBJECT-TYPE
    SYNTAX      TruthValue
    MAX-ACCESS  read-write
    STATUS      current
    DESCRIPTION
        "If true, this Rx SA will be applied to H/W. Set to false to remove."
    ::= { vtssMacsecConfigSecyEntry 197 }

vtssMacsecConfigSecyRxSc3Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 198 }

vtssMacsecConfigSecyRxSc3Sa2LowestPN OBJECT-TYPE
    SYNTAX      VTSSUnsigned64
    MAX-ACCESS  read-write
    STATUS      current
    DESCRIPTION
        "The lowest packet number associated with this Rx SA."
    ::= { vtssMacsecConfigSecyEntry 199 }

vtssMacsecConfigSecyRxSc3Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 200 }

vtssMacsecConfigSecyRxSc3Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 201 }

vtssMacsecConfigSecyRxSc3Sa3Configured OBJECT-TYPE
    SYNTAX      TruthValue
    MAX-ACCESS  read-write
    STATUS      current
    DESCRIPTION
        "If true, this Rx SA will be applied to H/W. Set to false to remove."
    ::= { vtssMacsecConfigSecyEntry 207 }

vtssMacsecConfigSecyRxSc3Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 208 }

vtssMacsecConfigSecyRxSc3Sa3LowestPN OBJECT-TYPE
    SYNTAX      VTSSUnsigned64
    MAX-ACCESS  read-write
    STATUS      current
    DESCRIPTION
        "The lowest packet number associated with this Rx SA."
    ::= { vtssMacsecConfigSecyEntry 209 }

vtssMacsecConfigSecyRxSc3Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 210 }

vtssMacsecConfigSecyRxSc3Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 211 }

vtssMacsecConfigSecyRxSc3Sa4Configured OBJECT-TYPE
    SYNTAX      TruthValue
    MAX-ACCESS  read-write
    STATUS      current
    DESCRIPTION
        "If true, this Rx SA will be applied to H/W. Set to false to remove."
    ::= { vtssMacsecConfigSecyEntry 217 }

vtssMacsecConfigSecyRxSc3Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 218 }

vtssMacsecConfigSecyRxSc3Sa4LowestPN OBJECT-TYPE
    SYNTAX      VTSSUnsigned64
    MAX-ACCESS  read-write
    STATUS      current
    DESCRIPTION
        "The lowest packet number associated with this Rx SA."
    ::= { vtssMacsecConfigSecyEntry 219 }

vtssMacsecConfigSecyRxSc3Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 220 }

vtssMacsecConfigSecyRxSc3Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 221 }

vtssMacsecConfigSecyRxSc4Configured OBJECT-TYPE
    SYNTAX      TruthValue
    MAX-ACCESS  read-write
    STATUS      current
    DESCRIPTION
        "If true, this Rx SC will be be applied to H/W. Set to false to remove."
    ::= { vtssMacsecConfigSecyEntry 227 }

vtssMacsecConfigSecyRxSc4PeerMac OBJECT-TYPE
    SYNTAX      MacAddress
    MAX-ACCESS  read-write
    STATUS      current
    DESCRIPTION
        "The MAC address of the peer (the one who sends MACsec encapsulated
         frames to us."
    ::= { vtssMacsecConfigSecyEntry 228 }

vtssMacsecConfigSecyRxSc4Sa1Configured OBJECT-TYPE
    SYNTAX      TruthValue
    MAX-ACCESS  read-write
    STATUS      current
    DESCRIPTION
        "If true, this Rx SA will be applied to H/W. Set to false to remove."
    ::= { vtssMacsecConfigSecyEntry 237 }

vtssMacsecConfigSecyRxSc4Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 238 }

vtssMacsecConfigSecyRxSc4Sa1LowestPN OBJECT-TYPE
    SYNTAX      VTSSUnsigned64
    MAX-ACCESS  read-write
    STATUS      current
    DESCRIPTION
        "The lowest packet number associated with this Rx SA."
    ::= { vtssMacsecConfigSecyEntry 239 }

vtssMacsecConfigSecyRxSc4Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 240 }

vtssMacsecConfigSecyRxSc4Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 241 }

vtssMacsecConfigSecyRxSc4Sa2Configured OBJECT-TYPE
    SYNTAX      TruthValue
    MAX-ACCESS  read-write
    STATUS      current
    DESCRIPTION
        "If true, this Rx SA will be applied to H/W. Set to false to remove."
    ::= { vtssMacsecConfigSecyEntry 247 }

vtssMacsecConfigSecyRxSc4Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 248 }

vtssMacsecConfigSecyRxSc4Sa2LowestPN OBJECT-TYPE
    SYNTAX      VTSSUnsigned64
    MAX-ACCESS  read-write
    STATUS      current
    DESCRIPTION
        "The lowest packet number associated with this Rx SA."
    ::= { vtssMacsecConfigSecyEntry 249 }

vtssMacsecConfigSecyRxSc4Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 250 }

vtssMacsecConfigSecyRxSc4Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 251 }

vtssMacsecConfigSecyRxSc4Sa3Configured OBJECT-TYPE
    SYNTAX      TruthValue
    MAX-ACCESS  read-write
    STATUS      current
    DESCRIPTION
        "If true, this Rx SA will be applied to H/W. Set to false to remove."
    ::= { vtssMacsecConfigSecyEntry 257 }

vtssMacsecConfigSecyRxSc4Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 258 }

vtssMacsecConfigSecyRxSc4Sa3LowestPN OBJECT-TYPE
    SYNTAX      VTSSUnsigned64
    MAX-ACCESS  read-write
    STATUS      current
    DESCRIPTION
        "The lowest packet number associated with this Rx SA."
    ::= { vtssMacsecConfigSecyEntry 259 }

vtssMacsecConfigSecyRxSc4Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 260 }

vtssMacsecConfigSecyRxSc4Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 261 }

vtssMacsecConfigSecyRxSc4Sa4Configured OBJECT-TYPE
    SYNTAX      TruthValue
    MAX-ACCESS  read-write
    STATUS      current
    DESCRIPTION
        "If true, this Rx SA will be applied to H/W. Set to false to remove."
    ::= { vtssMacsecConfigSecyEntry 267 }

vtssMacsecConfigSecyRxSc4Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 268 }

vtssMacsecConfigSecyRxSc4Sa4LowestPN OBJECT-TYPE
    SYNTAX      VTSSUnsigned64
    MAX-ACCESS  read-write
    STATUS      current
    DESCRIPTION
        "The lowest packet number associated with this Rx SA."
    ::= { vtssMacsecConfigSecyEntry 269 }

vtssMacsecConfigSecyRxSc4Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 270 }

vtssMacsecConfigSecyRxSc4Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 271 }

vtssMacsecConfigSecyRxSc5Configured OBJECT-TYPE
    SYNTAX      TruthValue
    MAX-ACCESS  read-write
    STATUS      current
    DESCRIPTION
        "If true, this Rx SC will be be applied to H/W. Set to false to remove."
    ::= { vtssMacsecConfigSecyEntry 277 }

vtssMacsecConfigSecyRxSc5PeerMac OBJECT-TYPE
    SYNTAX      MacAddress
    MAX-ACCESS  read-write
    STATUS      current
    DESCRIPTION
        "The MAC address of the peer (the one who sends MACsec encapsulated
         frames to us."
    ::= { vtssMacsecConfigSecyEntry 278 }

vtssMacsecConfigSecyRxSc5Sa1Configured OBJECT-TYPE
    SYNTAX      TruthValue
    MAX-ACCESS  read-write
    STATUS      current
    DESCRIPTION
        "If true, this Rx SA will be applied to H/W. Set to false to remove."
    ::= { vtssMacsecConfigSecyEntry 287 }

vtssMacsecConfigSecyRxSc5Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 288 }

vtssMacsecConfigSecyRxSc5Sa1LowestPN OBJECT-TYPE
    SYNTAX      VTSSUnsigned64
    MAX-ACCESS  read-write
    STATUS      current
    DESCRIPTION
        "The lowest packet number associated with this Rx SA."
    ::= { vtssMacsecConfigSecyEntry 289 }

vtssMacsecConfigSecyRxSc5Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 290 }

vtssMacsecConfigSecyRxSc5Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 291 }

vtssMacsecConfigSecyRxSc5Sa2Configured OBJECT-TYPE
    SYNTAX      TruthValue
    MAX-ACCESS  read-write
    STATUS      current
    DESCRIPTION
        "If true, this Rx SA will be applied to H/W. Set to false to remove."
    ::= { vtssMacsecConfigSecyEntry 297 }

vtssMacsecConfigSecyRxSc5Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 298 }

vtssMacsecConfigSecyRxSc5Sa2LowestPN OBJECT-TYPE
    SYNTAX      VTSSUnsigned64
    MAX-ACCESS  read-write
    STATUS      current
    DESCRIPTION
        "The lowest packet number associated with this Rx SA."
    ::= { vtssMacsecConfigSecyEntry 299 }

vtssMacsecConfigSecyRxSc5Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 300 }

vtssMacsecConfigSecyRxSc5Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 301 }

vtssMacsecConfigSecyRxSc5Sa3Configured OBJECT-TYPE
    SYNTAX      TruthValue
    MAX-ACCESS  read-write
    STATUS      current
    DESCRIPTION
        "If true, this Rx SA will be applied to H/W. Set to false to remove."
    ::= { vtssMacsecConfigSecyEntry 307 }

vtssMacsecConfigSecyRxSc5Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 308 }

vtssMacsecConfigSecyRxSc5Sa3LowestPN OBJECT-TYPE
    SYNTAX      VTSSUnsigned64
    MAX-ACCESS  read-write
    STATUS      current
    DESCRIPTION
        "The lowest packet number associated with this Rx SA."
    ::= { vtssMacsecConfigSecyEntry 309 }

vtssMacsecConfigSecyRxSc5Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 310 }

vtssMacsecConfigSecyRxSc5Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 311 }

vtssMacsecConfigSecyRxSc5Sa4Configured OBJECT-TYPE
    SYNTAX      TruthValue
    MAX-ACCESS  read-write
    STATUS      current
    DESCRIPTION
        "If true, this Rx SA will be applied to H/W. Set to false to remove."
    ::= { vtssMacsecConfigSecyEntry 317 }

vtssMacsecConfigSecyRxSc5Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 318 }

vtssMacsecConfigSecyRxSc5Sa4LowestPN OBJECT-TYPE
    SYNTAX      VTSSUnsigned64
    MAX-ACCESS  read-write
    STATUS      current
    DESCRIPTION
        "The lowest packet number associated with this Rx SA."
    ::= { vtssMacsecConfigSecyEntry 319 }

vtssMacsecConfigSecyRxSc5Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 320 }

vtssMacsecConfigSecyRxSc5Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 321 }

vtssMacsecConfigSecyRxSc6Configured OBJECT-TYPE
    SYNTAX      TruthValue
    MAX-ACCESS  read-write
    STATUS      current
    DESCRIPTION
        "If true, this Rx SC will be be applied to H/W. Set to false to remove."
    ::= { vtssMacsecConfigSecyEntry 327 }

vtssMacsecConfigSecyRxSc6PeerMac OBJECT-TYPE
    SYNTAX      MacAddress
    MAX-ACCESS  read-write
    STATUS      current
    DESCRIPTION
        "The MAC address of the peer (the one who sends MACsec encapsulated
         frames to us."
    ::= { vtssMacsecConfigSecyEntry 328 }

vtssMacsecConfigSecyRxSc6Sa1Configured OBJECT-TYPE
    SYNTAX      TruthValue
    MAX-ACCESS  read-write
    STATUS      current
    DESCRIPTION
        "If true, this Rx SA will be applied to H/W. Set to false to remove."
    ::= { vtssMacsecConfigSecyEntry 337 }

vtssMacsecConfigSecyRxSc6Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 338 }

vtssMacsecConfigSecyRxSc6Sa1LowestPN OBJECT-TYPE
    SYNTAX      VTSSUnsigned64
    MAX-ACCESS  read-write
    STATUS      current
    DESCRIPTION
        "The lowest packet number associated with this Rx SA."
    ::= { vtssMacsecConfigSecyEntry 339 }

vtssMacsecConfigSecyRxSc6Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 340 }

vtssMacsecConfigSecyRxSc6Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 341 }

vtssMacsecConfigSecyRxSc6Sa2Configured OBJECT-TYPE
    SYNTAX      TruthValue
    MAX-ACCESS  read-write
    STATUS      current
    DESCRIPTION
        "If true, this Rx SA will be applied to H/W. Set to false to remove."
    ::= { vtssMacsecConfigSecyEntry 347 }

vtssMacsecConfigSecyRxSc6Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 348 }

vtssMacsecConfigSecyRxSc6Sa2LowestPN OBJECT-TYPE
    SYNTAX      VTSSUnsigned64
    MAX-ACCESS  read-write
    STATUS      current
    DESCRIPTION
        "The lowest packet number associated with this Rx SA."
    ::= { vtssMacsecConfigSecyEntry 349 }

vtssMacsecConfigSecyRxSc6Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 350 }

vtssMacsecConfigSecyRxSc6Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 351 }

vtssMacsecConfigSecyRxSc6Sa3Configured OBJECT-TYPE
    SYNTAX      TruthValue
    MAX-ACCESS  read-write
    STATUS      current
    DESCRIPTION
        "If true, this Rx SA will be applied to H/W. Set to false to remove."
    ::= { vtssMacsecConfigSecyEntry 357 }

vtssMacsecConfigSecyRxSc6Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 358 }

vtssMacsecConfigSecyRxSc6Sa3LowestPN OBJECT-TYPE
    SYNTAX      VTSSUnsigned64
    MAX-ACCESS  read-write
    STATUS      current
    DESCRIPTION
        "The lowest packet number associated with this Rx SA."
    ::= { vtssMacsecConfigSecyEntry 359 }

vtssMacsecConfigSecyRxSc6Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 360 }

vtssMacsecConfigSecyRxSc6Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 361 }

vtssMacsecConfigSecyRxSc6Sa4Configured OBJECT-TYPE
    SYNTAX      TruthValue
    MAX-ACCESS  read-write
    STATUS      current
    DESCRIPTION
        "If true, this Rx SA will be applied to H/W. Set to false to remove."
    ::= { vtssMacsecConfigSecyEntry 367 }

vtssMacsecConfigSecyRxSc6Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 368 }

vtssMacsecConfigSecyRxSc6Sa4LowestPN OBJECT-TYPE
    SYNTAX      VTSSUnsigned64
    MAX-ACCESS  read-write
    STATUS      current
    DESCRIPTION
        "The lowest packet number associated with this Rx SA."
    ::= { vtssMacsecConfigSecyEntry 369 }

vtssMacsecConfigSecyRxSc6Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 370 }

vtssMacsecConfigSecyRxSc6Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 371 }

vtssMacsecConfigSecyRxSc7Configured OBJECT-TYPE
    SYNTAX      TruthValue
    MAX-ACCESS  read-write
    STATUS      current
    DESCRIPTION
        "If true, this Rx SC will be be applied to H/W. Set to false to remove."
    ::= { vtssMacsecConfigSecyEntry 377 }

vtssMacsecConfigSecyRxSc7PeerMac OBJECT-TYPE
    SYNTAX      MacAddress
    MAX-ACCESS  read-write
    STATUS      current
    DESCRIPTION
        "The MAC address of the peer (the one who sends MACsec encapsulated
         frames to us."
    ::= { vtssMacsecConfigSecyEntry 378 }

vtssMacsecConfigSecyRxSc7Sa1Configured OBJECT-TYPE
    SYNTAX      TruthValue
    MAX-ACCESS  read-write
    STATUS      current
    DESCRIPTION
        "If true, this Rx SA will be applied to H/W. Set to false to remove."
    ::= { vtssMacsecConfigSecyEntry 387 }

vtssMacsecConfigSecyRxSc7Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 388 }

vtssMacsecConfigSecyRxSc7Sa1LowestPN OBJECT-TYPE
    SYNTAX      VTSSUnsigned64
    MAX-ACCESS  read-write
    STATUS      current
    DESCRIPTION
        "The lowest packet number associated with this Rx SA."
    ::= { vtssMacsecConfigSecyEntry 389 }

vtssMacsecConfigSecyRxSc7Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 390 }

vtssMacsecConfigSecyRxSc7Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 391 }

vtssMacsecConfigSecyRxSc7Sa2Configured OBJECT-TYPE
    SYNTAX      TruthValue
    MAX-ACCESS  read-write
    STATUS      current
    DESCRIPTION
        "If true, this Rx SA will be applied to H/W. Set to false to remove."
    ::= { vtssMacsecConfigSecyEntry 397 }

vtssMacsecConfigSecyRxSc7Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 398 }

vtssMacsecConfigSecyRxSc7Sa2LowestPN OBJECT-TYPE
    SYNTAX      VTSSUnsigned64
    MAX-ACCESS  read-write
    STATUS      current
    DESCRIPTION
        "The lowest packet number associated with this Rx SA."
    ::= { vtssMacsecConfigSecyEntry 399 }

vtssMacsecConfigSecyRxSc7Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 400 }

vtssMacsecConfigSecyRxSc7Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 401 }

vtssMacsecConfigSecyRxSc7Sa3Configured OBJECT-TYPE
    SYNTAX      TruthValue
    MAX-ACCESS  read-write
    STATUS      current
    DESCRIPTION
        "If true, this Rx SA will be applied to H/W. Set to false to remove."
    ::= { vtssMacsecConfigSecyEntry 407 }

vtssMacsecConfigSecyRxSc7Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 408 }

vtssMacsecConfigSecyRxSc7Sa3LowestPN OBJECT-TYPE
    SYNTAX      VTSSUnsigned64
    MAX-ACCESS  read-write
    STATUS      current
    DESCRIPTION
        "The lowest packet number associated with this Rx SA."
    ::= { vtssMacsecConfigSecyEntry 409 }

vtssMacsecConfigSecyRxSc7Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 410 }

vtssMacsecConfigSecyRxSc7Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 411 }

vtssMacsecConfigSecyRxSc7Sa4Configured OBJECT-TYPE
    SYNTAX      TruthValue
    MAX-ACCESS  read-write
    STATUS      current
    DESCRIPTION
        "If true, this Rx SA will be applied to H/W. Set to false to remove."
    ::= { vtssMacsecConfigSecyEntry 417 }

vtssMacsecConfigSecyRxSc7Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 418 }

vtssMacsecConfigSecyRxSc7Sa4LowestPN OBJECT-TYPE
    SYNTAX      VTSSUnsigned64
    MAX-ACCESS  read-write
    STATUS      current
    DESCRIPTION
        "The lowest packet number associated with this Rx SA."
    ::= { vtssMacsecConfigSecyEntry 419 }

vtssMacsecConfigSecyRxSc7Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 420 }

vtssMacsecConfigSecyRxSc7Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 421 }

vtssMacsecConfigSecyRxSc8Configured OBJECT-TYPE
    SYNTAX      TruthValue
    MAX-ACCESS  read-write
    STATUS      current
    DESCRIPTION
        "If true, this Rx SC will be be applied to H/W. Set to false to remove."
    ::= { vtssMacsecConfigSecyEntry 427 }

vtssMacsecConfigSecyRxSc8PeerMac OBJECT-TYPE
    SYNTAX      MacAddress
    MAX-ACCESS  read-write
    STATUS      current
    DESCRIPTION
        "The MAC address of the peer (the one who sends MACsec encapsulated
         frames to us."
    ::= { vtssMacsecConfigSecyEntry 428 }

vtssMacsecConfigSecyRxSc8Sa1Configured OBJECT-TYPE
    SYNTAX      TruthValue
    MAX-ACCESS  read-write
    STATUS      current
    DESCRIPTION
        "If true, this Rx SA will be applied to H/W. Set to false to remove."
    ::= { vtssMacsecConfigSecyEntry 437 }

vtssMacsecConfigSecyRxSc8Sa1Active OBJECT-TYPE
    SYNTAX      TruthValue
    MAX-ACCESS  read-write
    STATUS      current
    DESCRIPTION
        "When the SecY is administratively enabled, exactly one Rx SA per
         configured Rx SC must be active."
    ::= { vtssMacsecConfigSecyEntry 438 }

vtssMacsecConfigSecyRxSc8Sa1LowestPN OBJECT-TYPE
    SYNTAX      VTSSUnsigned64
    MAX-ACCESS  read-write
    STATUS      current
    DESCRIPTION
        "The lowest packet number associated with this Rx SA."
    ::= { vtssMacsecConfigSecyEntry 439 }

vtssMacsecConfigSecyRxSc8Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 440 }

vtssMacsecConfigSecyRxSc8Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 441 }

vtssMacsecConfigSecyRxSc8Sa2Configured OBJECT-TYPE
    SYNTAX      TruthValue
    MAX-ACCESS  read-write
    STATUS      current
    DESCRIPTION
        "If true, this Rx SA will be applied to H/W. Set to false to remove."
    ::= { vtssMacsecConfigSecyEntry 447 }

vtssMacsecConfigSecyRxSc8Sa2Active OBJECT-TYPE
    SYNTAX      TruthValue
    MAX-ACCESS  read-write
    STATUS      current
    DESCRIPTION
        "When the SecY is administratively enabled, exactly one Rx SA per
         configured Rx SC must be active."
    ::= { vtssMacsecConfigSecyEntry 448 }

vtssMacsecConfigSecyRxSc8Sa2LowestPN OBJECT-TYPE
    SYNTAX      VTSSUnsigned64
    MAX-ACCESS  read-write
    STATUS      current
    DESCRIPTION
        "The lowest packet number associated with this Rx SA."
    ::= { vtssMacsecConfigSecyEntry 449 }

vtssMacsecConfigSecyRxSc8Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 450 }

vtssMacsecConfigSecyRxSc8Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 451 }

vtssMacsecConfigSecyRxSc8Sa3Configured OBJECT-TYPE
    SYNTAX      TruthValue
    MAX-ACCESS  read-write
    STATUS      current
    DESCRIPTION
        "If true, this Rx SA will be applied to H/W. Set to false to remove."
    ::= { vtssMacsecConfigSecyEntry 457 }

vtssMacsecConfigSecyRxSc8Sa3Active OBJECT-TYPE
    SYNTAX      TruthValue
    MAX-ACCESS  read-write
    STATUS      current
    DESCRIPTION
        "When the SecY is administratively enabled, exactly one Rx SA per
         configured Rx SC must be active."
    ::= { vtssMacsecConfigSecyEntry 458 }

vtssMacsecConfigSecyRxSc8Sa3LowestPN OBJECT-TYPE
    SYNTAX      VTSSUnsigned64
    MAX-ACCESS  read-write
    STATUS      current
    DESCRIPTION
        "The lowest packet number associated with this Rx SA."
    ::= { vtssMacsecConfigSecyEntry 459 }

vtssMacsecConfigSecyRxSc8Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 460 }

vtssMacsecConfigSecyRxSc8Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 461 }

vtssMacsecConfigSecyRxSc8Sa4Configured OBJECT-TYPE
    SYNTAX      TruthValue
    MAX-ACCESS  read-write
    STATUS      current
    DESCRIPTION
        "If true, this Rx SA will be applied to H/W. Set to false to remove."
    ::= { vtssMacsecConfigSecyEntry 467 }

vtssMacsecConfigSecyRxSc8Sa4Active OBJECT-TYPE
    SYNTAX      TruthValue
    MAX-ACCESS  read-write
    STATUS      current
    DESCRIPTION
        "When the SecY is administratively enabled, exactly one Rx SA per
         configured Rx SC must be active."
    ::= { vtssMacsecConfigSecyEntry 468 }

vtssMacsecConfigSecyRxSc8Sa4LowestPN OBJECT-TYPE
    SYNTAX      VTSSUnsigned64
    MAX-ACCESS  read-write
    STATUS      current
    DESCRIPTION
        "The lowest packet number associated with this Rx SA."
    ::= { vtssMacsecConfigSecyEntry 469 }

vtssMacsecConfigSecyRxSc8Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyEntry 470 }

vtssMacsecConfigSecyRxSc8Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyEntry 471 }

vtssMacsecConfigSecyAction OBJECT-TYPE
    SYNTAX      VTSSRowEditorState
    MAX-ACCESS  read-write
    STATUS      current
    DESCRIPTION
        "Action"
    ::= { vtssMacsecConfigSecyEntry 1000 }

vtssMacsecConfigSecyRowEditor OBJECT IDENTIFIER
    ::= { vtssMacsecConfig 3 }

vtssMacsecConfigSecyRowEditorIfIndex OBJECT-TYPE
    SYNTAX      VTSSInterfaceIndex
    MAX-ACCESS  read-write
    STATUS      current
    DESCRIPTION
        "Logical port interface index."
    ::= { vtssMacsecConfigSecyRowEditor 1 }

vtssMacsecConfigSecyRowEditorSecyId OBJECT-TYPE
    SYNTAX      Unsigned32
    MAX-ACCESS  read-write
    STATUS      current
    DESCRIPTION
        "SecY IDs are numbered 1 through maximum number of SecYs support on an
         interface."
    ::= { vtssMacsecConfigSecyRowEditor 2 }

vtssMacsecConfigSecyRowEditorAdminActive OBJECT-TYPE
    SYNTAX      TruthValue
    MAX-ACCESS  read-write
    STATUS      current
    DESCRIPTION
        "Controls whether this SecY is applied to H/W or not."
    ::= { vtssMacsecConfigSecyRowEditor 3 }

vtssMacsecConfigSecyRowEditorVirtualPortId OBJECT-TYPE
    SYNTAX      VTSSUnsigned16
    MAX-ACCESS  read-write
    STATUS      current
    DESCRIPTION
        "The virtual port ID is used in the SCI tag if present. Changing the
         virtual port ID causes all Secure Channels and their Secure
         Associations to be recreated."
    ::= { vtssMacsecConfigSecyRowEditor 4 }

vtssMacsecConfigSecyRowEditorCipherSuite OBJECT-TYPE
    SYNTAX      VTSSMacsecCipherSuite
    MAX-ACCESS  read-write
    STATUS      current
    DESCRIPTION
        "The cipher suite to be used by all used SCs in this SecY. Changing the
         cipher suite from a 128- to a 256-bit or vice versa requires all SAs to
         be removed before-hand."
    ::= { vtssMacsecConfigSecyRowEditor 5 }

vtssMacsecConfigSecyRowEditorConfidentialityOffset OBJECT-TYPE
    SYNTAX      Unsigned32
    MAX-ACCESS  read-write
    STATUS      current
    DESCRIPTION
        "Select the offset into frames where encryption and decryption starts."
    ::= { vtssMacsecConfigSecyRowEditor 6 }

vtssMacsecConfigSecyRowEditorTxProtectFrames OBJECT-TYPE
    SYNTAX      TruthValue
    MAX-ACCESS  read-write
    STATUS      current
    DESCRIPTION
        "If true, frames will be MACsec encapsulated with an ICV. If Encrypt is
         also set, the data will be encrypted. If false, frames will pass
         through the crypto-core without modification."
    ::= { vtssMacsecConfigSecyRowEditor 7 }

vtssMacsecConfigSecyRowEditorTxAlwaysIncludeSci OBJECT-TYPE
    SYNTAX      TruthValue
    MAX-ACCESS  read-write
    STATUS      current
    DESCRIPTION
        "If true, the SCI will be included in the SecTAG."
    ::= { vtssMacsecConfigSecyRowEditor 8 }

vtssMacsecConfigSecyRowEditorTxUseES OBJECT-TYPE
    SYNTAX      TruthValue
    MAX-ACCESS  read-write
    STATUS      current
    DESCRIPTION
        "Enables the use of the ES (End Station) bit in the SecTAG when
         transmitting protected frames."
    ::= { vtssMacsecConfigSecyRowEditor 9 }

vtssMacsecConfigSecyRowEditorTxUseSCB OBJECT-TYPE
    SYNTAX      TruthValue
    MAX-ACCESS  read-write
    STATUS      current
    DESCRIPTION
        "Enables the use of the SCB (Single Copy Broadcast) bit in the SecTAG
         when transmitting protected frames."
    ::= { vtssMacsecConfigSecyRowEditor 10 }

vtssMacsecConfigSecyRowEditorRxFrameValidation OBJECT-TYPE
    SYNTAX      VTSSMacsecFrameValidation
    MAX-ACCESS  read-write
    STATUS      current
    DESCRIPTION
        "Controls how MACsec handles the ICV of incoming frames."
    ::= { vtssMacsecConfigSecyRowEditor 11 }

vtssMacsecConfigSecyRowEditorRxReplayProtect OBJECT-TYPE
    SYNTAX      TruthValue
    MAX-ACCESS  read-write
    STATUS      current
    DESCRIPTION
        "If true, frames arriving with a packet number outside the replay
         protect window are discarded. If false, such frames are allowed."
    ::= { vtssMacsecConfigSecyRowEditor 12 }

vtssMacsecConfigSecyRowEditorRxReplayWindow OBJECT-TYPE
    SYNTAX      Unsigned32
    MAX-ACCESS  read-write
    STATUS      current
    DESCRIPTION
        "Controls the window size within which a frame's packet number is
         accepted. Only used if ReplayProtect is true."
    ::= { vtssMacsecConfigSecyRowEditor 13 }

vtssMacsecConfigSecyRowEditorTxScConfigured OBJECT-TYPE
    SYNTAX      TruthValue
    MAX-ACCESS  read-write
    STATUS      current
    DESCRIPTION
        "If true, this Tx SC will be be applied to H/W. Set to false to remove."
    ::= { vtssMacsecConfigSecyRowEditor 22 }

vtssMacsecConfigSecyRowEditorTxScMacType OBJECT-TYPE
    SYNTAX      VTSSMacsecTxScMacType
    MAX-ACCESS  read-write
    STATUS      current
    DESCRIPTION
        "Set to Management to use the switch's management MAC address, or set to
         Port to use this interface's MAC address, or set to Custom to use the
         CustomMac in this Tx SC."
    ::= { vtssMacsecConfigSecyRowEditor 23 }

vtssMacsecConfigSecyRowEditorTxScCustomMac OBJECT-TYPE
    SYNTAX      MacAddress
    MAX-ACCESS  read-write
    STATUS      current
    DESCRIPTION
        "When MacType is set to Custom, this is this Tx SC's MacAddress.
         Otherwise unused."
    ::= { vtssMacsecConfigSecyRowEditor 24 }

vtssMacsecConfigSecyRowEditorTxSa1Configured OBJECT-TYPE
    SYNTAX      TruthValue
    MAX-ACCESS  read-write
    STATUS      current
    DESCRIPTION
        "If true, this Tx SA will be applied to H/W. Set to false to remove"
    ::= { vtssMacsecConfigSecyRowEditor 33 }

vtssMacsecConfigSecyRowEditorTxSa1Active OBJECT-TYPE
    SYNTAX      TruthValue
    MAX-ACCESS  read-write
    STATUS      current
    DESCRIPTION
        "When the SecY is administratively enabled, exactly one Tx SA must be
         active."
    ::= { vtssMacsecConfigSecyRowEditor 34 }

vtssMacsecConfigSecyRowEditorTxSa1NextPN OBJECT-TYPE
    SYNTAX      VTSSUnsigned64
    MAX-ACCESS  read-write
    STATUS      current
    DESCRIPTION
        "Packet number of the first packet sent using this Tx SA."
    ::= { vtssMacsecConfigSecyRowEditor 35 }

vtssMacsecConfigSecyRowEditorTxSa1Encrypt OBJECT-TYPE
    SYNTAX      TruthValue
    MAX-ACCESS  read-write
    STATUS      current
    DESCRIPTION
        "Set to true to encrypt user data for this Tx SA. Set to false to only
         integrity protect."
    ::= { vtssMacsecConfigSecyRowEditor 36 }

vtssMacsecConfigSecyRowEditorTxSa1Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyRowEditor 37 }

vtssMacsecConfigSecyRowEditorTxSa1Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyRowEditor 38 }

vtssMacsecConfigSecyRowEditorTxSa2Configured OBJECT-TYPE
    SYNTAX      TruthValue
    MAX-ACCESS  read-write
    STATUS      current
    DESCRIPTION
        "If true, this Tx SA will be applied to H/W. Set to false to remove"
    ::= { vtssMacsecConfigSecyRowEditor 44 }

vtssMacsecConfigSecyRowEditorTxSa2Active OBJECT-TYPE
    SYNTAX      TruthValue
    MAX-ACCESS  read-write
    STATUS      current
    DESCRIPTION
        "When the SecY is administratively enabled, exactly one Tx SA must be
         active."
    ::= { vtssMacsecConfigSecyRowEditor 45 }

vtssMacsecConfigSecyRowEditorTxSa2NextPN OBJECT-TYPE
    SYNTAX      VTSSUnsigned64
    MAX-ACCESS  read-write
    STATUS      current
    DESCRIPTION
        "Packet number of the first packet sent using this Tx SA."
    ::= { vtssMacsecConfigSecyRowEditor 46 }

vtssMacsecConfigSecyRowEditorTxSa2Encrypt OBJECT-TYPE
    SYNTAX      TruthValue
    MAX-ACCESS  read-write
    STATUS      current
    DESCRIPTION
        "Set to true to encrypt user data for this Tx SA. Set to false to only
         integrity protect."
    ::= { vtssMacsecConfigSecyRowEditor 47 }

vtssMacsecConfigSecyRowEditorTxSa2Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyRowEditor 48 }

vtssMacsecConfigSecyRowEditorTxSa2Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyRowEditor 49 }

vtssMacsecConfigSecyRowEditorTxSa3Configured OBJECT-TYPE
    SYNTAX      TruthValue
    MAX-ACCESS  read-write
    STATUS      current
    DESCRIPTION
        "If true, this Tx SA will be applied to H/W. Set to false to remove"
    ::= { vtssMacsecConfigSecyRowEditor 55 }

vtssMacsecConfigSecyRowEditorTxSa3Active OBJECT-TYPE
    SYNTAX      TruthValue
    MAX-ACCESS  read-write
    STATUS      current
    DESCRIPTION
        "When the SecY is administratively enabled, exactly one Tx SA must be
         active."
    ::= { vtssMacsecConfigSecyRowEditor 56 }

vtssMacsecConfigSecyRowEditorTxSa3NextPN OBJECT-TYPE
    SYNTAX      VTSSUnsigned64
    MAX-ACCESS  read-write
    STATUS      current
    DESCRIPTION
        "Packet number of the first packet sent using this Tx SA."
    ::= { vtssMacsecConfigSecyRowEditor 57 }

vtssMacsecConfigSecyRowEditorTxSa3Encrypt OBJECT-TYPE
    SYNTAX      TruthValue
    MAX-ACCESS  read-write
    STATUS      current
    DESCRIPTION
        "Set to true to encrypt user data for this Tx SA. Set to false to only
         integrity protect."
    ::= { vtssMacsecConfigSecyRowEditor 58 }

vtssMacsecConfigSecyRowEditorTxSa3Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyRowEditor 59 }

vtssMacsecConfigSecyRowEditorTxSa3Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyRowEditor 60 }

vtssMacsecConfigSecyRowEditorTxSa4Configured OBJECT-TYPE
    SYNTAX      TruthValue
    MAX-ACCESS  read-write
    STATUS      current
    DESCRIPTION
        "If true, this Tx SA will be applied to H/W. Set to false to remove"
    ::= { vtssMacsecConfigSecyRowEditor 66 }

vtssMacsecConfigSecyRowEditorTxSa4Active OBJECT-TYPE
    SYNTAX      TruthValue
    MAX-ACCESS  read-write
    STATUS      current
    DESCRIPTION
        "When the SecY is administratively enabled, exactly one Tx SA must be
         active."
    ::= { vtssMacsecConfigSecyRowEditor 67 }

vtssMacsecConfigSecyRowEditorTxSa4NextPN OBJECT-TYPE
    SYNTAX      VTSSUnsigned64
    MAX-ACCESS  read-write
    STATUS      current
    DESCRIPTION
        "Packet number of the first packet sent using this Tx SA."
    ::= { vtssMacsecConfigSecyRowEditor 68 }

vtssMacsecConfigSecyRowEditorTxSa4Encrypt OBJECT-TYPE
    SYNTAX      TruthValue
    MAX-ACCESS  read-write
    STATUS      current
    DESCRIPTION
        "Set to true to encrypt user data for this Tx SA. Set to false to only
         integrity protect."
    ::= { vtssMacsecConfigSecyRowEditor 69 }

vtssMacsecConfigSecyRowEditorTxSa4Key OBJECT-TYPE
    SYNTAX      VTSSDisplayString (SIZE(0..64))
    MAX-ACCESS  read-write
    STATUS      current
    DESCRIPTION
        "This is the static key to use for this Tx SA. Use exactly 32
         hexadecimal charcters for 128-bit ciphers and 64 hexadecimal characters
         for 256-bit ciphers."
    ::= { vtssMacsecConfigSecyRowEditor 70 }

vtssMacsecConfigSecyRowEditorTxSa4Salt OBJECT-TYPE
    SYNTAX      VTSSDisplayString (SIZE(0..24))
    MAX-ACCESS  read-write
    STATUS      current
    DESCRIPTION
        "This is the salt to use for XPN ciphers for this Tx SA. Use exactly 24
         hexadecimal characters."
    ::= { vtssMacsecConfigSecyRowEditor 71 }

vtssMacsecConfigSecyRowEditorRxSc1Configured OBJECT-TYPE
    SYNTAX      TruthValue
    MAX-ACCESS  read-write
    STATUS      current
    DESCRIPTION
        "If true, this Rx SC will be be applied to H/W. Set to false to remove."
    ::= { vtssMacsecConfigSecyRowEditor 77 }

vtssMacsecConfigSecyRowEditorRxSc1PeerMac OBJECT-TYPE
    SYNTAX      MacAddress
    MAX-ACCESS  read-write
    STATUS      current
    DESCRIPTION
        "The MAC address of the peer (the one who sends MACsec encapsulated
         frames to us."
    ::= { vtssMacsecConfigSecyRowEditor 78 }

vtssMacsecConfigSecyRowEditorRxSc1Sa1Configured OBJECT-TYPE
    SYNTAX      TruthValue
    MAX-ACCESS  read-write
    STATUS      current
    DESCRIPTION
        "If true, this Rx SA will be applied to H/W. Set to false to remove."
    ::= { vtssMacsecConfigSecyRowEditor 87 }

vtssMacsecConfigSecyRowEditorRxSc1Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 88 }

vtssMacsecConfigSecyRowEditorRxSc1Sa1LowestPN OBJECT-TYPE
    SYNTAX      VTSSUnsigned64
    MAX-ACCESS  read-write
    STATUS      current
    DESCRIPTION
        "The lowest packet number associated with this Rx SA."
    ::= { vtssMacsecConfigSecyRowEditor 89 }

vtssMacsecConfigSecyRowEditorRxSc1Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 90 }

vtssMacsecConfigSecyRowEditorRxSc1Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 91 }

vtssMacsecConfigSecyRowEditorRxSc1Sa2Configured OBJECT-TYPE
    SYNTAX      TruthValue
    MAX-ACCESS  read-write
    STATUS      current
    DESCRIPTION
        "If true, this Rx SA will be applied to H/W. Set to false to remove."
    ::= { vtssMacsecConfigSecyRowEditor 97 }

vtssMacsecConfigSecyRowEditorRxSc1Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 98 }

vtssMacsecConfigSecyRowEditorRxSc1Sa2LowestPN OBJECT-TYPE
    SYNTAX      VTSSUnsigned64
    MAX-ACCESS  read-write
    STATUS      current
    DESCRIPTION
        "The lowest packet number associated with this Rx SA."
    ::= { vtssMacsecConfigSecyRowEditor 99 }

vtssMacsecConfigSecyRowEditorRxSc1Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 100 }

vtssMacsecConfigSecyRowEditorRxSc1Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 101 }

vtssMacsecConfigSecyRowEditorRxSc1Sa3Configured OBJECT-TYPE
    SYNTAX      TruthValue
    MAX-ACCESS  read-write
    STATUS      current
    DESCRIPTION
        "If true, this Rx SA will be applied to H/W. Set to false to remove."
    ::= { vtssMacsecConfigSecyRowEditor 107 }

vtssMacsecConfigSecyRowEditorRxSc1Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 108 }

vtssMacsecConfigSecyRowEditorRxSc1Sa3LowestPN OBJECT-TYPE
    SYNTAX      VTSSUnsigned64
    MAX-ACCESS  read-write
    STATUS      current
    DESCRIPTION
        "The lowest packet number associated with this Rx SA."
    ::= { vtssMacsecConfigSecyRowEditor 109 }

vtssMacsecConfigSecyRowEditorRxSc1Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 110 }

vtssMacsecConfigSecyRowEditorRxSc1Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 111 }

vtssMacsecConfigSecyRowEditorRxSc1Sa4Configured OBJECT-TYPE
    SYNTAX      TruthValue
    MAX-ACCESS  read-write
    STATUS      current
    DESCRIPTION
        "If true, this Rx SA will be applied to H/W. Set to false to remove."
    ::= { vtssMacsecConfigSecyRowEditor 117 }

vtssMacsecConfigSecyRowEditorRxSc1Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 118 }

vtssMacsecConfigSecyRowEditorRxSc1Sa4LowestPN OBJECT-TYPE
    SYNTAX      VTSSUnsigned64
    MAX-ACCESS  read-write
    STATUS      current
    DESCRIPTION
        "The lowest packet number associated with this Rx SA."
    ::= { vtssMacsecConfigSecyRowEditor 119 }

vtssMacsecConfigSecyRowEditorRxSc1Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 120 }

vtssMacsecConfigSecyRowEditorRxSc1Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 121 }

vtssMacsecConfigSecyRowEditorRxSc2Configured OBJECT-TYPE
    SYNTAX      TruthValue
    MAX-ACCESS  read-write
    STATUS      current
    DESCRIPTION
        "If true, this Rx SC will be be applied to H/W. Set to false to remove."
    ::= { vtssMacsecConfigSecyRowEditor 127 }

vtssMacsecConfigSecyRowEditorRxSc2PeerMac OBJECT-TYPE
    SYNTAX      MacAddress
    MAX-ACCESS  read-write
    STATUS      current
    DESCRIPTION
        "The MAC address of the peer (the one who sends MACsec encapsulated
         frames to us."
    ::= { vtssMacsecConfigSecyRowEditor 128 }

vtssMacsecConfigSecyRowEditorRxSc2Sa1Configured OBJECT-TYPE
    SYNTAX      TruthValue
    MAX-ACCESS  read-write
    STATUS      current
    DESCRIPTION
        "If true, this Rx SA will be applied to H/W. Set to false to remove."
    ::= { vtssMacsecConfigSecyRowEditor 137 }

vtssMacsecConfigSecyRowEditorRxSc2Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 138 }

vtssMacsecConfigSecyRowEditorRxSc2Sa1LowestPN OBJECT-TYPE
    SYNTAX      VTSSUnsigned64
    MAX-ACCESS  read-write
    STATUS      current
    DESCRIPTION
        "The lowest packet number associated with this Rx SA."
    ::= { vtssMacsecConfigSecyRowEditor 139 }

vtssMacsecConfigSecyRowEditorRxSc2Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 140 }

vtssMacsecConfigSecyRowEditorRxSc2Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 141 }

vtssMacsecConfigSecyRowEditorRxSc2Sa2Configured OBJECT-TYPE
    SYNTAX      TruthValue
    MAX-ACCESS  read-write
    STATUS      current
    DESCRIPTION
        "If true, this Rx SA will be applied to H/W. Set to false to remove."
    ::= { vtssMacsecConfigSecyRowEditor 147 }

vtssMacsecConfigSecyRowEditorRxSc2Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 148 }

vtssMacsecConfigSecyRowEditorRxSc2Sa2LowestPN OBJECT-TYPE
    SYNTAX      VTSSUnsigned64
    MAX-ACCESS  read-write
    STATUS      current
    DESCRIPTION
        "The lowest packet number associated with this Rx SA."
    ::= { vtssMacsecConfigSecyRowEditor 149 }

vtssMacsecConfigSecyRowEditorRxSc2Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 150 }

vtssMacsecConfigSecyRowEditorRxSc2Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 151 }

vtssMacsecConfigSecyRowEditorRxSc2Sa3Configured OBJECT-TYPE
    SYNTAX      TruthValue
    MAX-ACCESS  read-write
    STATUS      current
    DESCRIPTION
        "If true, this Rx SA will be applied to H/W. Set to false to remove."
    ::= { vtssMacsecConfigSecyRowEditor 157 }

vtssMacsecConfigSecyRowEditorRxSc2Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 158 }

vtssMacsecConfigSecyRowEditorRxSc2Sa3LowestPN OBJECT-TYPE
    SYNTAX      VTSSUnsigned64
    MAX-ACCESS  read-write
    STATUS      current
    DESCRIPTION
        "The lowest packet number associated with this Rx SA."
    ::= { vtssMacsecConfigSecyRowEditor 159 }

vtssMacsecConfigSecyRowEditorRxSc2Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 160 }

vtssMacsecConfigSecyRowEditorRxSc2Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 161 }

vtssMacsecConfigSecyRowEditorRxSc2Sa4Configured OBJECT-TYPE
    SYNTAX      TruthValue
    MAX-ACCESS  read-write
    STATUS      current
    DESCRIPTION
        "If true, this Rx SA will be applied to H/W. Set to false to remove."
    ::= { vtssMacsecConfigSecyRowEditor 167 }

vtssMacsecConfigSecyRowEditorRxSc2Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 168 }

vtssMacsecConfigSecyRowEditorRxSc2Sa4LowestPN OBJECT-TYPE
    SYNTAX      VTSSUnsigned64
    MAX-ACCESS  read-write
    STATUS      current
    DESCRIPTION
        "The lowest packet number associated with this Rx SA."
    ::= { vtssMacsecConfigSecyRowEditor 169 }

vtssMacsecConfigSecyRowEditorRxSc2Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 170 }

vtssMacsecConfigSecyRowEditorRxSc2Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 171 }

vtssMacsecConfigSecyRowEditorRxSc3Configured OBJECT-TYPE
    SYNTAX      TruthValue
    MAX-ACCESS  read-write
    STATUS      current
    DESCRIPTION
        "If true, this Rx SC will be be applied to H/W. Set to false to remove."
    ::= { vtssMacsecConfigSecyRowEditor 177 }

vtssMacsecConfigSecyRowEditorRxSc3PeerMac OBJECT-TYPE
    SYNTAX      MacAddress
    MAX-ACCESS  read-write
    STATUS      current
    DESCRIPTION
        "The MAC address of the peer (the one who sends MACsec encapsulated
         frames to us."
    ::= { vtssMacsecConfigSecyRowEditor 178 }

vtssMacsecConfigSecyRowEditorRxSc3Sa1Configured OBJECT-TYPE
    SYNTAX      TruthValue
    MAX-ACCESS  read-write
    STATUS      current
    DESCRIPTION
        "If true, this Rx SA will be applied to H/W. Set to false to remove."
    ::= { vtssMacsecConfigSecyRowEditor 187 }

vtssMacsecConfigSecyRowEditorRxSc3Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 188 }

vtssMacsecConfigSecyRowEditorRxSc3Sa1LowestPN OBJECT-TYPE
    SYNTAX      VTSSUnsigned64
    MAX-ACCESS  read-write
    STATUS      current
    DESCRIPTION
        "The lowest packet number associated with this Rx SA."
    ::= { vtssMacsecConfigSecyRowEditor 189 }

vtssMacsecConfigSecyRowEditorRxSc3Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 190 }

vtssMacsecConfigSecyRowEditorRxSc3Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 191 }

vtssMacsecConfigSecyRowEditorRxSc3Sa2Configured OBJECT-TYPE
    SYNTAX      TruthValue
    MAX-ACCESS  read-write
    STATUS      current
    DESCRIPTION
        "If true, this Rx SA will be applied to H/W. Set to false to remove."
    ::= { vtssMacsecConfigSecyRowEditor 197 }

vtssMacsecConfigSecyRowEditorRxSc3Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 198 }

vtssMacsecConfigSecyRowEditorRxSc3Sa2LowestPN OBJECT-TYPE
    SYNTAX      VTSSUnsigned64
    MAX-ACCESS  read-write
    STATUS      current
    DESCRIPTION
        "The lowest packet number associated with this Rx SA."
    ::= { vtssMacsecConfigSecyRowEditor 199 }

vtssMacsecConfigSecyRowEditorRxSc3Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 200 }

vtssMacsecConfigSecyRowEditorRxSc3Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 201 }

vtssMacsecConfigSecyRowEditorRxSc3Sa3Configured OBJECT-TYPE
    SYNTAX      TruthValue
    MAX-ACCESS  read-write
    STATUS      current
    DESCRIPTION
        "If true, this Rx SA will be applied to H/W. Set to false to remove."
    ::= { vtssMacsecConfigSecyRowEditor 207 }

vtssMacsecConfigSecyRowEditorRxSc3Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 208 }

vtssMacsecConfigSecyRowEditorRxSc3Sa3LowestPN OBJECT-TYPE
    SYNTAX      VTSSUnsigned64
    MAX-ACCESS  read-write
    STATUS      current
    DESCRIPTION
        "The lowest packet number associated with this Rx SA."
    ::= { vtssMacsecConfigSecyRowEditor 209 }

vtssMacsecConfigSecyRowEditorRxSc3Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 210 }

vtssMacsecConfigSecyRowEditorRxSc3Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 211 }

vtssMacsecConfigSecyRowEditorRxSc3Sa4Configured OBJECT-TYPE
    SYNTAX      TruthValue
    MAX-ACCESS  read-write
    STATUS      current
    DESCRIPTION
        "If true, this Rx SA will be applied to H/W. Set to false to remove."
    ::= { vtssMacsecConfigSecyRowEditor 217 }

vtssMacsecConfigSecyRowEditorRxSc3Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 218 }

vtssMacsecConfigSecyRowEditorRxSc3Sa4LowestPN OBJECT-TYPE
    SYNTAX      VTSSUnsigned64
    MAX-ACCESS  read-write
    STATUS      current
    DESCRIPTION
        "The lowest packet number associated with this Rx SA."
    ::= { vtssMacsecConfigSecyRowEditor 219 }

vtssMacsecConfigSecyRowEditorRxSc3Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 220 }

vtssMacsecConfigSecyRowEditorRxSc3Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 221 }

vtssMacsecConfigSecyRowEditorRxSc4Configured OBJECT-TYPE
    SYNTAX      TruthValue
    MAX-ACCESS  read-write
    STATUS      current
    DESCRIPTION
        "If true, this Rx SC will be be applied to H/W. Set to false to remove."
    ::= { vtssMacsecConfigSecyRowEditor 227 }

vtssMacsecConfigSecyRowEditorRxSc4PeerMac OBJECT-TYPE
    SYNTAX      MacAddress
    MAX-ACCESS  read-write
    STATUS      current
    DESCRIPTION
        "The MAC address of the peer (the one who sends MACsec encapsulated
         frames to us."
    ::= { vtssMacsecConfigSecyRowEditor 228 }

vtssMacsecConfigSecyRowEditorRxSc4Sa1Configured OBJECT-TYPE
    SYNTAX      TruthValue
    MAX-ACCESS  read-write
    STATUS      current
    DESCRIPTION
        "If true, this Rx SA will be applied to H/W. Set to false to remove."
    ::= { vtssMacsecConfigSecyRowEditor 237 }

vtssMacsecConfigSecyRowEditorRxSc4Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 238 }

vtssMacsecConfigSecyRowEditorRxSc4Sa1LowestPN OBJECT-TYPE
    SYNTAX      VTSSUnsigned64
    MAX-ACCESS  read-write
    STATUS      current
    DESCRIPTION
        "The lowest packet number associated with this Rx SA."
    ::= { vtssMacsecConfigSecyRowEditor 239 }

vtssMacsecConfigSecyRowEditorRxSc4Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 240 }

vtssMacsecConfigSecyRowEditorRxSc4Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 241 }

vtssMacsecConfigSecyRowEditorRxSc4Sa2Configured OBJECT-TYPE
    SYNTAX      TruthValue
    MAX-ACCESS  read-write
    STATUS      current
    DESCRIPTION
        "If true, this Rx SA will be applied to H/W. Set to false to remove."
    ::= { vtssMacsecConfigSecyRowEditor 247 }

vtssMacsecConfigSecyRowEditorRxSc4Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 248 }

vtssMacsecConfigSecyRowEditorRxSc4Sa2LowestPN OBJECT-TYPE
    SYNTAX      VTSSUnsigned64
    MAX-ACCESS  read-write
    STATUS      current
    DESCRIPTION
        "The lowest packet number associated with this Rx SA."
    ::= { vtssMacsecConfigSecyRowEditor 249 }

vtssMacsecConfigSecyRowEditorRxSc4Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 250 }

vtssMacsecConfigSecyRowEditorRxSc4Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 251 }

vtssMacsecConfigSecyRowEditorRxSc4Sa3Configured OBJECT-TYPE
    SYNTAX      TruthValue
    MAX-ACCESS  read-write
    STATUS      current
    DESCRIPTION
        "If true, this Rx SA will be applied to H/W. Set to false to remove."
    ::= { vtssMacsecConfigSecyRowEditor 257 }

vtssMacsecConfigSecyRowEditorRxSc4Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 258 }

vtssMacsecConfigSecyRowEditorRxSc4Sa3LowestPN OBJECT-TYPE
    SYNTAX      VTSSUnsigned64
    MAX-ACCESS  read-write
    STATUS      current
    DESCRIPTION
        "The lowest packet number associated with this Rx SA."
    ::= { vtssMacsecConfigSecyRowEditor 259 }

vtssMacsecConfigSecyRowEditorRxSc4Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 260 }

vtssMacsecConfigSecyRowEditorRxSc4Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 261 }

vtssMacsecConfigSecyRowEditorRxSc4Sa4Configured OBJECT-TYPE
    SYNTAX      TruthValue
    MAX-ACCESS  read-write
    STATUS      current
    DESCRIPTION
        "If true, this Rx SA will be applied to H/W. Set to false to remove."
    ::= { vtssMacsecConfigSecyRowEditor 267 }

vtssMacsecConfigSecyRowEditorRxSc4Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 268 }

vtssMacsecConfigSecyRowEditorRxSc4Sa4LowestPN OBJECT-TYPE
    SYNTAX      VTSSUnsigned64
    MAX-ACCESS  read-write
    STATUS      current
    DESCRIPTION
        "The lowest packet number associated with this Rx SA."
    ::= { vtssMacsecConfigSecyRowEditor 269 }

vtssMacsecConfigSecyRowEditorRxSc4Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 270 }

vtssMacsecConfigSecyRowEditorRxSc4Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 271 }

vtssMacsecConfigSecyRowEditorRxSc5Configured OBJECT-TYPE
    SYNTAX      TruthValue
    MAX-ACCESS  read-write
    STATUS      current
    DESCRIPTION
        "If true, this Rx SC will be be applied to H/W. Set to false to remove."
    ::= { vtssMacsecConfigSecyRowEditor 277 }

vtssMacsecConfigSecyRowEditorRxSc5PeerMac OBJECT-TYPE
    SYNTAX      MacAddress
    MAX-ACCESS  read-write
    STATUS      current
    DESCRIPTION
        "The MAC address of the peer (the one who sends MACsec encapsulated
         frames to us."
    ::= { vtssMacsecConfigSecyRowEditor 278 }

vtssMacsecConfigSecyRowEditorRxSc5Sa1Configured OBJECT-TYPE
    SYNTAX      TruthValue
    MAX-ACCESS  read-write
    STATUS      current
    DESCRIPTION
        "If true, this Rx SA will be applied to H/W. Set to false to remove."
    ::= { vtssMacsecConfigSecyRowEditor 287 }

vtssMacsecConfigSecyRowEditorRxSc5Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 288 }

vtssMacsecConfigSecyRowEditorRxSc5Sa1LowestPN OBJECT-TYPE
    SYNTAX      VTSSUnsigned64
    MAX-ACCESS  read-write
    STATUS      current
    DESCRIPTION
        "The lowest packet number associated with this Rx SA."
    ::= { vtssMacsecConfigSecyRowEditor 289 }

vtssMacsecConfigSecyRowEditorRxSc5Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 290 }

vtssMacsecConfigSecyRowEditorRxSc5Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 291 }

vtssMacsecConfigSecyRowEditorRxSc5Sa2Configured OBJECT-TYPE
    SYNTAX      TruthValue
    MAX-ACCESS  read-write
    STATUS      current
    DESCRIPTION
        "If true, this Rx SA will be applied to H/W. Set to false to remove."
    ::= { vtssMacsecConfigSecyRowEditor 297 }

vtssMacsecConfigSecyRowEditorRxSc5Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 298 }

vtssMacsecConfigSecyRowEditorRxSc5Sa2LowestPN OBJECT-TYPE
    SYNTAX      VTSSUnsigned64
    MAX-ACCESS  read-write
    STATUS      current
    DESCRIPTION
        "The lowest packet number associated with this Rx SA."
    ::= { vtssMacsecConfigSecyRowEditor 299 }

vtssMacsecConfigSecyRowEditorRxSc5Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 300 }

vtssMacsecConfigSecyRowEditorRxSc5Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 301 }

vtssMacsecConfigSecyRowEditorRxSc5Sa3Configured OBJECT-TYPE
    SYNTAX      TruthValue
    MAX-ACCESS  read-write
    STATUS      current
    DESCRIPTION
        "If true, this Rx SA will be applied to H/W. Set to false to remove."
    ::= { vtssMacsecConfigSecyRowEditor 307 }

vtssMacsecConfigSecyRowEditorRxSc5Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 308 }

vtssMacsecConfigSecyRowEditorRxSc5Sa3LowestPN OBJECT-TYPE
    SYNTAX      VTSSUnsigned64
    MAX-ACCESS  read-write
    STATUS      current
    DESCRIPTION
        "The lowest packet number associated with this Rx SA."
    ::= { vtssMacsecConfigSecyRowEditor 309 }

vtssMacsecConfigSecyRowEditorRxSc5Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 310 }

vtssMacsecConfigSecyRowEditorRxSc5Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 311 }

vtssMacsecConfigSecyRowEditorRxSc5Sa4Configured OBJECT-TYPE
    SYNTAX      TruthValue
    MAX-ACCESS  read-write
    STATUS      current
    DESCRIPTION
        "If true, this Rx SA will be applied to H/W. Set to false to remove."
    ::= { vtssMacsecConfigSecyRowEditor 317 }

vtssMacsecConfigSecyRowEditorRxSc5Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 318 }

vtssMacsecConfigSecyRowEditorRxSc5Sa4LowestPN OBJECT-TYPE
    SYNTAX      VTSSUnsigned64
    MAX-ACCESS  read-write
    STATUS      current
    DESCRIPTION
        "The lowest packet number associated with this Rx SA."
    ::= { vtssMacsecConfigSecyRowEditor 319 }

vtssMacsecConfigSecyRowEditorRxSc5Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 320 }

vtssMacsecConfigSecyRowEditorRxSc5Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 321 }

vtssMacsecConfigSecyRowEditorRxSc6Configured OBJECT-TYPE
    SYNTAX      TruthValue
    MAX-ACCESS  read-write
    STATUS      current
    DESCRIPTION
        "If true, this Rx SC will be be applied to H/W. Set to false to remove."
    ::= { vtssMacsecConfigSecyRowEditor 327 }

vtssMacsecConfigSecyRowEditorRxSc6PeerMac OBJECT-TYPE
    SYNTAX      MacAddress
    MAX-ACCESS  read-write
    STATUS      current
    DESCRIPTION
        "The MAC address of the peer (the one who sends MACsec encapsulated
         frames to us."
    ::= { vtssMacsecConfigSecyRowEditor 328 }

vtssMacsecConfigSecyRowEditorRxSc6Sa1Configured OBJECT-TYPE
    SYNTAX      TruthValue
    MAX-ACCESS  read-write
    STATUS      current
    DESCRIPTION
        "If true, this Rx SA will be applied to H/W. Set to false to remove."
    ::= { vtssMacsecConfigSecyRowEditor 337 }

vtssMacsecConfigSecyRowEditorRxSc6Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 338 }

vtssMacsecConfigSecyRowEditorRxSc6Sa1LowestPN OBJECT-TYPE
    SYNTAX      VTSSUnsigned64
    MAX-ACCESS  read-write
    STATUS      current
    DESCRIPTION
        "The lowest packet number associated with this Rx SA."
    ::= { vtssMacsecConfigSecyRowEditor 339 }

vtssMacsecConfigSecyRowEditorRxSc6Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 340 }

vtssMacsecConfigSecyRowEditorRxSc6Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 341 }

vtssMacsecConfigSecyRowEditorRxSc6Sa2Configured OBJECT-TYPE
    SYNTAX      TruthValue
    MAX-ACCESS  read-write
    STATUS      current
    DESCRIPTION
        "If true, this Rx SA will be applied to H/W. Set to false to remove."
    ::= { vtssMacsecConfigSecyRowEditor 347 }

vtssMacsecConfigSecyRowEditorRxSc6Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 348 }

vtssMacsecConfigSecyRowEditorRxSc6Sa2LowestPN OBJECT-TYPE
    SYNTAX      VTSSUnsigned64
    MAX-ACCESS  read-write
    STATUS      current
    DESCRIPTION
        "The lowest packet number associated with this Rx SA."
    ::= { vtssMacsecConfigSecyRowEditor 349 }

vtssMacsecConfigSecyRowEditorRxSc6Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 350 }

vtssMacsecConfigSecyRowEditorRxSc6Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 351 }

vtssMacsecConfigSecyRowEditorRxSc6Sa3Configured OBJECT-TYPE
    SYNTAX      TruthValue
    MAX-ACCESS  read-write
    STATUS      current
    DESCRIPTION
        "If true, this Rx SA will be applied to H/W. Set to false to remove."
    ::= { vtssMacsecConfigSecyRowEditor 357 }

vtssMacsecConfigSecyRowEditorRxSc6Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 358 }

vtssMacsecConfigSecyRowEditorRxSc6Sa3LowestPN OBJECT-TYPE
    SYNTAX      VTSSUnsigned64
    MAX-ACCESS  read-write
    STATUS      current
    DESCRIPTION
        "The lowest packet number associated with this Rx SA."
    ::= { vtssMacsecConfigSecyRowEditor 359 }

vtssMacsecConfigSecyRowEditorRxSc6Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 360 }

vtssMacsecConfigSecyRowEditorRxSc6Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 361 }

vtssMacsecConfigSecyRowEditorRxSc6Sa4Configured OBJECT-TYPE
    SYNTAX      TruthValue
    MAX-ACCESS  read-write
    STATUS      current
    DESCRIPTION
        "If true, this Rx SA will be applied to H/W. Set to false to remove."
    ::= { vtssMacsecConfigSecyRowEditor 367 }

vtssMacsecConfigSecyRowEditorRxSc6Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 368 }

vtssMacsecConfigSecyRowEditorRxSc6Sa4LowestPN OBJECT-TYPE
    SYNTAX      VTSSUnsigned64
    MAX-ACCESS  read-write
    STATUS      current
    DESCRIPTION
        "The lowest packet number associated with this Rx SA."
    ::= { vtssMacsecConfigSecyRowEditor 369 }

vtssMacsecConfigSecyRowEditorRxSc6Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 370 }

vtssMacsecConfigSecyRowEditorRxSc6Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 371 }

vtssMacsecConfigSecyRowEditorRxSc7Configured OBJECT-TYPE
    SYNTAX      TruthValue
    MAX-ACCESS  read-write
    STATUS      current
    DESCRIPTION
        "If true, this Rx SC will be be applied to H/W. Set to false to remove."
    ::= { vtssMacsecConfigSecyRowEditor 377 }

vtssMacsecConfigSecyRowEditorRxSc7PeerMac OBJECT-TYPE
    SYNTAX      MacAddress
    MAX-ACCESS  read-write
    STATUS      current
    DESCRIPTION
        "The MAC address of the peer (the one who sends MACsec encapsulated
         frames to us."
    ::= { vtssMacsecConfigSecyRowEditor 378 }

vtssMacsecConfigSecyRowEditorRxSc7Sa1Configured OBJECT-TYPE
    SYNTAX      TruthValue
    MAX-ACCESS  read-write
    STATUS      current
    DESCRIPTION
        "If true, this Rx SA will be applied to H/W. Set to false to remove."
    ::= { vtssMacsecConfigSecyRowEditor 387 }

vtssMacsecConfigSecyRowEditorRxSc7Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 388 }

vtssMacsecConfigSecyRowEditorRxSc7Sa1LowestPN OBJECT-TYPE
    SYNTAX      VTSSUnsigned64
    MAX-ACCESS  read-write
    STATUS      current
    DESCRIPTION
        "The lowest packet number associated with this Rx SA."
    ::= { vtssMacsecConfigSecyRowEditor 389 }

vtssMacsecConfigSecyRowEditorRxSc7Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 390 }

vtssMacsecConfigSecyRowEditorRxSc7Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 391 }

vtssMacsecConfigSecyRowEditorRxSc7Sa2Configured OBJECT-TYPE
    SYNTAX      TruthValue
    MAX-ACCESS  read-write
    STATUS      current
    DESCRIPTION
        "If true, this Rx SA will be applied to H/W. Set to false to remove."
    ::= { vtssMacsecConfigSecyRowEditor 397 }

vtssMacsecConfigSecyRowEditorRxSc7Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 398 }

vtssMacsecConfigSecyRowEditorRxSc7Sa2LowestPN OBJECT-TYPE
    SYNTAX      VTSSUnsigned64
    MAX-ACCESS  read-write
    STATUS      current
    DESCRIPTION
        "The lowest packet number associated with this Rx SA."
    ::= { vtssMacsecConfigSecyRowEditor 399 }

vtssMacsecConfigSecyRowEditorRxSc7Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 400 }

vtssMacsecConfigSecyRowEditorRxSc7Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 401 }

vtssMacsecConfigSecyRowEditorRxSc7Sa3Configured OBJECT-TYPE
    SYNTAX      TruthValue
    MAX-ACCESS  read-write
    STATUS      current
    DESCRIPTION
        "If true, this Rx SA will be applied to H/W. Set to false to remove."
    ::= { vtssMacsecConfigSecyRowEditor 407 }

vtssMacsecConfigSecyRowEditorRxSc7Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 408 }

vtssMacsecConfigSecyRowEditorRxSc7Sa3LowestPN OBJECT-TYPE
    SYNTAX      VTSSUnsigned64
    MAX-ACCESS  read-write
    STATUS      current
    DESCRIPTION
        "The lowest packet number associated with this Rx SA."
    ::= { vtssMacsecConfigSecyRowEditor 409 }

vtssMacsecConfigSecyRowEditorRxSc7Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 410 }

vtssMacsecConfigSecyRowEditorRxSc7Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 411 }

vtssMacsecConfigSecyRowEditorRxSc7Sa4Configured OBJECT-TYPE
    SYNTAX      TruthValue
    MAX-ACCESS  read-write
    STATUS      current
    DESCRIPTION
        "If true, this Rx SA will be applied to H/W. Set to false to remove."
    ::= { vtssMacsecConfigSecyRowEditor 417 }

vtssMacsecConfigSecyRowEditorRxSc7Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 418 }

vtssMacsecConfigSecyRowEditorRxSc7Sa4LowestPN OBJECT-TYPE
    SYNTAX      VTSSUnsigned64
    MAX-ACCESS  read-write
    STATUS      current
    DESCRIPTION
        "The lowest packet number associated with this Rx SA."
    ::= { vtssMacsecConfigSecyRowEditor 419 }

vtssMacsecConfigSecyRowEditorRxSc7Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 420 }

vtssMacsecConfigSecyRowEditorRxSc7Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 421 }

vtssMacsecConfigSecyRowEditorRxSc8Configured OBJECT-TYPE
    SYNTAX      TruthValue
    MAX-ACCESS  read-write
    STATUS      current
    DESCRIPTION
        "If true, this Rx SC will be be applied to H/W. Set to false to remove."
    ::= { vtssMacsecConfigSecyRowEditor 427 }

vtssMacsecConfigSecyRowEditorRxSc8PeerMac OBJECT-TYPE
    SYNTAX      MacAddress
    MAX-ACCESS  read-write
    STATUS      current
    DESCRIPTION
        "The MAC address of the peer (the one who sends MACsec encapsulated
         frames to us."
    ::= { vtssMacsecConfigSecyRowEditor 428 }

vtssMacsecConfigSecyRowEditorRxSc8Sa1Configured OBJECT-TYPE
    SYNTAX      TruthValue
    MAX-ACCESS  read-write
    STATUS      current
    DESCRIPTION
        "If true, this Rx SA will be applied to H/W. Set to false to remove."
    ::= { vtssMacsecConfigSecyRowEditor 437 }

vtssMacsecConfigSecyRowEditorRxSc8Sa1Active OBJECT-TYPE
    SYNTAX      TruthValue
    MAX-ACCESS  read-write
    STATUS      current
    DESCRIPTION
        "When the SecY is administratively enabled, exactly one Rx SA per
         configured Rx SC must be active."
    ::= { vtssMacsecConfigSecyRowEditor 438 }

vtssMacsecConfigSecyRowEditorRxSc8Sa1LowestPN OBJECT-TYPE
    SYNTAX      VTSSUnsigned64
    MAX-ACCESS  read-write
    STATUS      current
    DESCRIPTION
        "The lowest packet number associated with this Rx SA."
    ::= { vtssMacsecConfigSecyRowEditor 439 }

vtssMacsecConfigSecyRowEditorRxSc8Sa1Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 440 }

vtssMacsecConfigSecyRowEditorRxSc8Sa1Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 441 }

vtssMacsecConfigSecyRowEditorRxSc8Sa2Configured OBJECT-TYPE
    SYNTAX      TruthValue
    MAX-ACCESS  read-write
    STATUS      current
    DESCRIPTION
        "If true, this Rx SA will be applied to H/W. Set to false to remove."
    ::= { vtssMacsecConfigSecyRowEditor 447 }

vtssMacsecConfigSecyRowEditorRxSc8Sa2Active OBJECT-TYPE
    SYNTAX      TruthValue
    MAX-ACCESS  read-write
    STATUS      current
    DESCRIPTION
        "When the SecY is administratively enabled, exactly one Rx SA per
         configured Rx SC must be active."
    ::= { vtssMacsecConfigSecyRowEditor 448 }

vtssMacsecConfigSecyRowEditorRxSc8Sa2LowestPN OBJECT-TYPE
    SYNTAX      VTSSUnsigned64
    MAX-ACCESS  read-write
    STATUS      current
    DESCRIPTION
        "The lowest packet number associated with this Rx SA."
    ::= { vtssMacsecConfigSecyRowEditor 449 }

vtssMacsecConfigSecyRowEditorRxSc8Sa2Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 450 }

vtssMacsecConfigSecyRowEditorRxSc8Sa2Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 451 }

vtssMacsecConfigSecyRowEditorRxSc8Sa3Configured OBJECT-TYPE
    SYNTAX      TruthValue
    MAX-ACCESS  read-write
    STATUS      current
    DESCRIPTION
        "If true, this Rx SA will be applied to H/W. Set to false to remove."
    ::= { vtssMacsecConfigSecyRowEditor 457 }

vtssMacsecConfigSecyRowEditorRxSc8Sa3Active OBJECT-TYPE
    SYNTAX      TruthValue
    MAX-ACCESS  read-write
    STATUS      current
    DESCRIPTION
        "When the SecY is administratively enabled, exactly one Rx SA per
         configured Rx SC must be active."
    ::= { vtssMacsecConfigSecyRowEditor 458 }

vtssMacsecConfigSecyRowEditorRxSc8Sa3LowestPN OBJECT-TYPE
    SYNTAX      VTSSUnsigned64
    MAX-ACCESS  read-write
    STATUS      current
    DESCRIPTION
        "The lowest packet number associated with this Rx SA."
    ::= { vtssMacsecConfigSecyRowEditor 459 }

vtssMacsecConfigSecyRowEditorRxSc8Sa3Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 460 }

vtssMacsecConfigSecyRowEditorRxSc8Sa3Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 461 }

vtssMacsecConfigSecyRowEditorRxSc8Sa4Configured OBJECT-TYPE
    SYNTAX      TruthValue
    MAX-ACCESS  read-write
    STATUS      current
    DESCRIPTION
        "If true, this Rx SA will be applied to H/W. Set to false to remove."
    ::= { vtssMacsecConfigSecyRowEditor 467 }

vtssMacsecConfigSecyRowEditorRxSc8Sa4Active OBJECT-TYPE
    SYNTAX      TruthValue
    MAX-ACCESS  read-write
    STATUS      current
    DESCRIPTION
        "When the SecY is administratively enabled, exactly one Rx SA per
         configured Rx SC must be active."
    ::= { vtssMacsecConfigSecyRowEditor 468 }

vtssMacsecConfigSecyRowEditorRxSc8Sa4LowestPN OBJECT-TYPE
    SYNTAX      VTSSUnsigned64
    MAX-ACCESS  read-write
    STATUS      current
    DESCRIPTION
        "The lowest packet number associated with this Rx SA."
    ::= { vtssMacsecConfigSecyRowEditor 469 }

vtssMacsecConfigSecyRowEditorRxSc8Sa4Key OBJECT-TYPE
    SYNTAX      VTSSDisplayString (SIZE(0..64))
    MAX-ACCESS  read-write
    STATUS      current
    DESCRIPTION
        "This is the static key to use for this Rx SA. Use exactly 32
         hexadecimal charcters for 128-bit ciphers and 64 hexadecimal characters
         for 256-bit ciphers."
    ::= { vtssMacsecConfigSecyRowEditor 470 }

vtssMacsecConfigSecyRowEditorRxSc8Sa4Salt OBJECT-TYPE
    SYNTAX      VTSSDisplayString (SIZE(0..24))
    MAX-ACCESS  read-write
    STATUS      current
    DESCRIPTION
        "This is the salt to use for XPN ciphers for this Rx SA. Use exactly 24
         hexadecimal characters."
    ::= { vtssMacsecConfigSecyRowEditor 471 }

vtssMacsecConfigSecyRowEditorAction OBJECT-TYPE
    SYNTAX      VTSSRowEditorState
    MAX-ACCESS  read-write
    STATUS      current
    DESCRIPTION
        "Action"
    ::= { vtssMacsecConfigSecyRowEditor 1000 }

vtssMacsecStatus OBJECT IDENTIFIER
    ::= { vtssMacsecMibObjects 3 }

vtssMacsecStatusSecyTable OBJECT-TYPE
    SYNTAX      SEQUENCE OF VTSSMacsecStatusSecyEntry
    MAX-ACCESS  not-accessible
    STATUS      current
    DESCRIPTION
        "MACsec SecY status table."
    ::= { vtssMacsecStatus 1 }

vtssMacsecStatusSecyEntry OBJECT-TYPE
    SYNTAX      VTSSMacsecStatusSecyEntry
    MAX-ACCESS  not-accessible
    STATUS      current
    DESCRIPTION
        "Each entry in this table represents a SecY's status."
    INDEX       { vtssMacsecStatusSecyIfIndex,
                  vtssMacsecStatusSecySecyId }
    ::= { vtssMacsecStatusSecyTable 1 }

VTSSMacsecStatusSecyEntry ::= SEQUENCE {
    vtssMacsecStatusSecyIfIndex               VTSSInterfaceIndex,
    vtssMacsecStatusSecySecyId                Unsigned32,
    vtssMacsecStatusSecyUptimeSeconds         Unsigned32,
    vtssMacsecStatusSecyInstalled             TruthValue,
    vtssMacsecStatusSecyMacEnabled            TruthValue,
    vtssMacsecStatusSecyMacOperational        TruthValue,
    vtssMacsecStatusSecyOperPointToPointMac   TruthValue,
    vtssMacsecStatusSecyTxScInstalled         TruthValue,
    vtssMacsecStatusSecyTxScTransmitting      TruthValue,
    vtssMacsecStatusSecyTxScEncodingSaIdx     Unsigned32,
    vtssMacsecStatusSecyTxScEncipheringSaIdx  Unsigned32,
    vtssMacsecStatusSecyTxScActiveSaIdx       Unsigned32,
    vtssMacsecStatusSecyTxScCreatedTime       Unsigned32,
    vtssMacsecStatusSecyTxScStartedTime       Unsigned32,
    vtssMacsecStatusSecyTxScStoppedTime       Unsigned32,
    vtssMacsecStatusSecyTxSa1Installed        TruthValue,
    vtssMacsecStatusSecyTxSa1InUse            TruthValue,
    vtssMacsecStatusSecyTxSa1NextPN           VTSSUnsigned64,
    vtssMacsecStatusSecyTxSa1CreatedTime      Unsigned32,
    vtssMacsecStatusSecyTxSa1StartedTime      Unsigned32,
    vtssMacsecStatusSecyTxSa1StoppedTime      Unsigned32,
    vtssMacsecStatusSecyTxSa2Installed        TruthValue,
    vtssMacsecStatusSecyTxSa2InUse            TruthValue,
    vtssMacsecStatusSecyTxSa2NextPN           VTSSUnsigned64,
    vtssMacsecStatusSecyTxSa2CreatedTime      Unsigned32,
    vtssMacsecStatusSecyTxSa2StartedTime      Unsigned32,
    vtssMacsecStatusSecyTxSa2StoppedTime      Unsigned32,
    vtssMacsecStatusSecyTxSa3Installed        TruthValue,
    vtssMacsecStatusSecyTxSa3InUse            TruthValue,
    vtssMacsecStatusSecyTxSa3NextPN           VTSSUnsigned64,
    vtssMacsecStatusSecyTxSa3CreatedTime      Unsigned32,
    vtssMacsecStatusSecyTxSa3StartedTime      Unsigned32,
    vtssMacsecStatusSecyTxSa3StoppedTime      Unsigned32,
    vtssMacsecStatusSecyTxSa4Installed        TruthValue,
    vtssMacsecStatusSecyTxSa4InUse            TruthValue,
    vtssMacsecStatusSecyTxSa4NextPN           VTSSUnsigned64,
    vtssMacsecStatusSecyTxSa4CreatedTime      Unsigned32,
    vtssMacsecStatusSecyTxSa4StartedTime      Unsigned32,
    vtssMacsecStatusSecyTxSa4StoppedTime      Unsigned32,
    vtssMacsecStatusSecyRxSc1Installed        TruthValue,
    vtssMacsecStatusSecyRxSc1Receiving        TruthValue,
    vtssMacsecStatusSecyRxSc1ActiveSaIdx      Unsigned32,
    vtssMacsecStatusSecyRxSc1CreatedTime      Unsigned32,
    vtssMacsecStatusSecyRxSc1StartedTime      Unsigned32,
    vtssMacsecStatusSecyRxSc1StoppedTime      Unsigned32,
    vtssMacsecStatusSecyRxSc1Sa1Installed     TruthValue,
    vtssMacsecStatusSecyRxSc1Sa1InUse         TruthValue,
    vtssMacsecStatusSecyRxSc1Sa1NextPN        VTSSUnsigned64,
    vtssMacsecStatusSecyRxSc1Sa1LowestPN      VTSSUnsigned64,
    vtssMacsecStatusSecyRxSc1Sa1CreatedTime   Unsigned32,
    vtssMacsecStatusSecyRxSc1Sa1StartedTime   Unsigned32,
    vtssMacsecStatusSecyRxSc1Sa1StoppedTime   Unsigned32,
    vtssMacsecStatusSecyRxSc1Sa2Installed     TruthValue,
    vtssMacsecStatusSecyRxSc1Sa2InUse         TruthValue,
    vtssMacsecStatusSecyRxSc1Sa2NextPN        VTSSUnsigned64,
    vtssMacsecStatusSecyRxSc1Sa2LowestPN      VTSSUnsigned64,
    vtssMacsecStatusSecyRxSc1Sa2CreatedTime   Unsigned32,
    vtssMacsecStatusSecyRxSc1Sa2StartedTime   Unsigned32,
    vtssMacsecStatusSecyRxSc1Sa2StoppedTime   Unsigned32,
    vtssMacsecStatusSecyRxSc1Sa3Installed     TruthValue,
    vtssMacsecStatusSecyRxSc1Sa3InUse         TruthValue,
    vtssMacsecStatusSecyRxSc1Sa3NextPN        VTSSUnsigned64,
    vtssMacsecStatusSecyRxSc1Sa3LowestPN      VTSSUnsigned64,
    vtssMacsecStatusSecyRxSc1Sa3CreatedTime   Unsigned32,
    vtssMacsecStatusSecyRxSc1Sa3StartedTime   Unsigned32,
    vtssMacsecStatusSecyRxSc1Sa3StoppedTime   Unsigned32,
    vtssMacsecStatusSecyRxSc1Sa4Installed     TruthValue,
    vtssMacsecStatusSecyRxSc1Sa4InUse         TruthValue,
    vtssMacsecStatusSecyRxSc1Sa4NextPN        VTSSUnsigned64,
    vtssMacsecStatusSecyRxSc1Sa4LowestPN      VTSSUnsigned64,
    vtssMacsecStatusSecyRxSc1Sa4CreatedTime   Unsigned32,
    vtssMacsecStatusSecyRxSc1Sa4StartedTime   Unsigned32,
    vtssMacsecStatusSecyRxSc1Sa4StoppedTime   Unsigned32,
    vtssMacsecStatusSecyRxSc2Installed        TruthValue,
    vtssMacsecStatusSecyRxSc2Receiving        TruthValue,
    vtssMacsecStatusSecyRxSc2ActiveSaIdx      Unsigned32,
    vtssMacsecStatusSecyRxSc2CreatedTime      Unsigned32,
    vtssMacsecStatusSecyRxSc2StartedTime      Unsigned32,
    vtssMacsecStatusSecyRxSc2StoppedTime      Unsigned32,
    vtssMacsecStatusSecyRxSc2Sa1Installed     TruthValue,
    vtssMacsecStatusSecyRxSc2Sa1InUse         TruthValue,
    vtssMacsecStatusSecyRxSc2Sa1NextPN        VTSSUnsigned64,
    vtssMacsecStatusSecyRxSc2Sa1LowestPN      VTSSUnsigned64,
    vtssMacsecStatusSecyRxSc2Sa1CreatedTime   Unsigned32,
    vtssMacsecStatusSecyRxSc2Sa1StartedTime   Unsigned32,
    vtssMacsecStatusSecyRxSc2Sa1StoppedTime   Unsigned32,
    vtssMacsecStatusSecyRxSc2Sa2Installed     TruthValue,
    vtssMacsecStatusSecyRxSc2Sa2InUse         TruthValue,
    vtssMacsecStatusSecyRxSc2Sa2NextPN        VTSSUnsigned64,
    vtssMacsecStatusSecyRxSc2Sa2LowestPN      VTSSUnsigned64,
    vtssMacsecStatusSecyRxSc2Sa2CreatedTime   Unsigned32,
    vtssMacsecStatusSecyRxSc2Sa2StartedTime   Unsigned32,
    vtssMacsecStatusSecyRxSc2Sa2StoppedTime   Unsigned32,
    vtssMacsecStatusSecyRxSc2Sa3Installed     TruthValue,
    vtssMacsecStatusSecyRxSc2Sa3InUse         TruthValue,
    vtssMacsecStatusSecyRxSc2Sa3NextPN        VTSSUnsigned64,
    vtssMacsecStatusSecyRxSc2Sa3LowestPN      VTSSUnsigned64,
    vtssMacsecStatusSecyRxSc2Sa3CreatedTime   Unsigned32,
    vtssMacsecStatusSecyRxSc2Sa3StartedTime   Unsigned32,
    vtssMacsecStatusSecyRxSc2Sa3StoppedTime   Unsigned32,
    vtssMacsecStatusSecyRxSc2Sa4Installed     TruthValue,
    vtssMacsecStatusSecyRxSc2Sa4InUse         TruthValue,
    vtssMacsecStatusSecyRxSc2Sa4NextPN        VTSSUnsigned64,
    vtssMacsecStatusSecyRxSc2Sa4LowestPN      VTSSUnsigned64,
    vtssMacsecStatusSecyRxSc2Sa4CreatedTime   Unsigned32,
    vtssMacsecStatusSecyRxSc2Sa4StartedTime   Unsigned32,
    vtssMacsecStatusSecyRxSc2Sa4StoppedTime   Unsigned32,
    vtssMacsecStatusSecyRxSc3Installed        TruthValue,
    vtssMacsecStatusSecyRxSc3Receiving        TruthValue,
    vtssMacsecStatusSecyRxSc3ActiveSaIdx      Unsigned32,
    vtssMacsecStatusSecyRxSc3CreatedTime      Unsigned32,
    vtssMacsecStatusSecyRxSc3StartedTime      Unsigned32,
    vtssMacsecStatusSecyRxSc3StoppedTime      Unsigned32,
    vtssMacsecStatusSecyRxSc3Sa1Installed     TruthValue,
    vtssMacsecStatusSecyRxSc3Sa1InUse         TruthValue,
    vtssMacsecStatusSecyRxSc3Sa1NextPN        VTSSUnsigned64,
    vtssMacsecStatusSecyRxSc3Sa1LowestPN      VTSSUnsigned64,
    vtssMacsecStatusSecyRxSc3Sa1CreatedTime   Unsigned32,
    vtssMacsecStatusSecyRxSc3Sa1StartedTime   Unsigned32,
    vtssMacsecStatusSecyRxSc3Sa1StoppedTime   Unsigned32,
    vtssMacsecStatusSecyRxSc3Sa2Installed     TruthValue,
    vtssMacsecStatusSecyRxSc3Sa2InUse         TruthValue,
    vtssMacsecStatusSecyRxSc3Sa2NextPN        VTSSUnsigned64,
    vtssMacsecStatusSecyRxSc3Sa2LowestPN      VTSSUnsigned64,
    vtssMacsecStatusSecyRxSc3Sa2CreatedTime   Unsigned32,
    vtssMacsecStatusSecyRxSc3Sa2StartedTime   Unsigned32,
    vtssMacsecStatusSecyRxSc3Sa2StoppedTime   Unsigned32,
    vtssMacsecStatusSecyRxSc3Sa3Installed     TruthValue,
    vtssMacsecStatusSecyRxSc3Sa3InUse         TruthValue,
    vtssMacsecStatusSecyRxSc3Sa3NextPN        VTSSUnsigned64,
    vtssMacsecStatusSecyRxSc3Sa3LowestPN      VTSSUnsigned64,
    vtssMacsecStatusSecyRxSc3Sa3CreatedTime   Unsigned32,
    vtssMacsecStatusSecyRxSc3Sa3StartedTime   Unsigned32,
    vtssMacsecStatusSecyRxSc3Sa3StoppedTime   Unsigned32,
    vtssMacsecStatusSecyRxSc3Sa4Installed     TruthValue,
    vtssMacsecStatusSecyRxSc3Sa4InUse         TruthValue,
    vtssMacsecStatusSecyRxSc3Sa4NextPN        VTSSUnsigned64,
    vtssMacsecStatusSecyRxSc3Sa4LowestPN      VTSSUnsigned64,
    vtssMacsecStatusSecyRxSc3Sa4CreatedTime   Unsigned32,
    vtssMacsecStatusSecyRxSc3Sa4StartedTime   Unsigned32,
    vtssMacsecStatusSecyRxSc3Sa4StoppedTime   Unsigned32,
    vtssMacsecStatusSecyRxSc4Installed        TruthValue,
    vtssMacsecStatusSecyRxSc4Receiving        TruthValue,
    vtssMacsecStatusSecyRxSc4ActiveSaIdx      Unsigned32,
    vtssMacsecStatusSecyRxSc4CreatedTime      Unsigned32,
    vtssMacsecStatusSecyRxSc4StartedTime      Unsigned32,
    vtssMacsecStatusSecyRxSc4StoppedTime      Unsigned32,
    vtssMacsecStatusSecyRxSc4Sa1Installed     TruthValue,
    vtssMacsecStatusSecyRxSc4Sa1InUse         TruthValue,
    vtssMacsecStatusSecyRxSc4Sa1NextPN        VTSSUnsigned64,
    vtssMacsecStatusSecyRxSc4Sa1LowestPN      VTSSUnsigned64,
    vtssMacsecStatusSecyRxSc4Sa1CreatedTime   Unsigned32,
    vtssMacsecStatusSecyRxSc4Sa1StartedTime   Unsigned32,
    vtssMacsecStatusSecyRxSc4Sa1StoppedTime   Unsigned32,
    vtssMacsecStatusSecyRxSc4Sa2Installed     TruthValue,
    vtssMacsecStatusSecyRxSc4Sa2InUse         TruthValue,
    vtssMacsecStatusSecyRxSc4Sa2NextPN        VTSSUnsigned64,
    vtssMacsecStatusSecyRxSc4Sa2LowestPN      VTSSUnsigned64,
    vtssMacsecStatusSecyRxSc4Sa2CreatedTime   Unsigned32,
    vtssMacsecStatusSecyRxSc4Sa2StartedTime   Unsigned32,
    vtssMacsecStatusSecyRxSc4Sa2StoppedTime   Unsigned32,
    vtssMacsecStatusSecyRxSc4Sa3Installed     TruthValue,
    vtssMacsecStatusSecyRxSc4Sa3InUse         TruthValue,
    vtssMacsecStatusSecyRxSc4Sa3NextPN        VTSSUnsigned64,
    vtssMacsecStatusSecyRxSc4Sa3LowestPN      VTSSUnsigned64,
    vtssMacsecStatusSecyRxSc4Sa3CreatedTime   Unsigned32,
    vtssMacsecStatusSecyRxSc4Sa3StartedTime   Unsigned32,
    vtssMacsecStatusSecyRxSc4Sa3StoppedTime   Unsigned32,
    vtssMacsecStatusSecyRxSc4Sa4Installed     TruthValue,
    vtssMacsecStatusSecyRxSc4Sa4InUse         TruthValue,
    vtssMacsecStatusSecyRxSc4Sa4NextPN        VTSSUnsigned64,
    vtssMacsecStatusSecyRxSc4Sa4LowestPN      VTSSUnsigned64,
    vtssMacsecStatusSecyRxSc4Sa4CreatedTime   Unsigned32,
    vtssMacsecStatusSecyRxSc4Sa4StartedTime   Unsigned32,
    vtssMacsecStatusSecyRxSc4Sa4StoppedTime   Unsigned32,
    vtssMacsecStatusSecyRxSc5Installed        TruthValue,
    vtssMacsecStatusSecyRxSc5Receiving        TruthValue,
    vtssMacsecStatusSecyRxSc5ActiveSaIdx      Unsigned32,
    vtssMacsecStatusSecyRxSc5CreatedTime      Unsigned32,
    vtssMacsecStatusSecyRxSc5StartedTime      Unsigned32,
    vtssMacsecStatusSecyRxSc5StoppedTime      Unsigned32,
    vtssMacsecStatusSecyRxSc5Sa1Installed     TruthValue,
    vtssMacsecStatusSecyRxSc5Sa1InUse         TruthValue,
    vtssMacsecStatusSecyRxSc5Sa1NextPN        VTSSUnsigned64,
    vtssMacsecStatusSecyRxSc5Sa1LowestPN      VTSSUnsigned64,
    vtssMacsecStatusSecyRxSc5Sa1CreatedTime   Unsigned32,
    vtssMacsecStatusSecyRxSc5Sa1StartedTime   Unsigned32,
    vtssMacsecStatusSecyRxSc5Sa1StoppedTime   Unsigned32,
    vtssMacsecStatusSecyRxSc5Sa2Installed     TruthValue,
    vtssMacsecStatusSecyRxSc5Sa2InUse         TruthValue,
    vtssMacsecStatusSecyRxSc5Sa2NextPN        VTSSUnsigned64,
    vtssMacsecStatusSecyRxSc5Sa2LowestPN      VTSSUnsigned64,
    vtssMacsecStatusSecyRxSc5Sa2CreatedTime   Unsigned32,
    vtssMacsecStatusSecyRxSc5Sa2StartedTime   Unsigned32,
    vtssMacsecStatusSecyRxSc5Sa2StoppedTime   Unsigned32,
    vtssMacsecStatusSecyRxSc5Sa3Installed     TruthValue,
    vtssMacsecStatusSecyRxSc5Sa3InUse         TruthValue,
    vtssMacsecStatusSecyRxSc5Sa3NextPN        VTSSUnsigned64,
    vtssMacsecStatusSecyRxSc5Sa3LowestPN      VTSSUnsigned64,
    vtssMacsecStatusSecyRxSc5Sa3CreatedTime   Unsigned32,
    vtssMacsecStatusSecyRxSc5Sa3StartedTime   Unsigned32,
    vtssMacsecStatusSecyRxSc5Sa3StoppedTime   Unsigned32,
    vtssMacsecStatusSecyRxSc5Sa4Installed     TruthValue,
    vtssMacsecStatusSecyRxSc5Sa4InUse         TruthValue,
    vtssMacsecStatusSecyRxSc5Sa4NextPN        VTSSUnsigned64,
    vtssMacsecStatusSecyRxSc5Sa4LowestPN      VTSSUnsigned64,
    vtssMacsecStatusSecyRxSc5Sa4CreatedTime   Unsigned32,
    vtssMacsecStatusSecyRxSc5Sa4StartedTime   Unsigned32,
    vtssMacsecStatusSecyRxSc5Sa4StoppedTime   Unsigned32,
    vtssMacsecStatusSecyRxSc6Installed        TruthValue,
    vtssMacsecStatusSecyRxSc6Receiving        TruthValue,
    vtssMacsecStatusSecyRxSc6ActiveSaIdx      Unsigned32,
    vtssMacsecStatusSecyRxSc6CreatedTime      Unsigned32,
    vtssMacsecStatusSecyRxSc6StartedTime      Unsigned32,
    vtssMacsecStatusSecyRxSc6StoppedTime      Unsigned32,
    vtssMacsecStatusSecyRxSc6Sa1Installed     TruthValue,
    vtssMacsecStatusSecyRxSc6Sa1InUse         TruthValue,
    vtssMacsecStatusSecyRxSc6Sa1NextPN        VTSSUnsigned64,
    vtssMacsecStatusSecyRxSc6Sa1LowestPN      VTSSUnsigned64,
    vtssMacsecStatusSecyRxSc6Sa1CreatedTime   Unsigned32,
    vtssMacsecStatusSecyRxSc6Sa1StartedTime   Unsigned32,
    vtssMacsecStatusSecyRxSc6Sa1StoppedTime   Unsigned32,
    vtssMacsecStatusSecyRxSc6Sa2Installed     TruthValue,
    vtssMacsecStatusSecyRxSc6Sa2InUse         TruthValue,
    vtssMacsecStatusSecyRxSc6Sa2NextPN        VTSSUnsigned64,
    vtssMacsecStatusSecyRxSc6Sa2LowestPN      VTSSUnsigned64,
    vtssMacsecStatusSecyRxSc6Sa2CreatedTime   Unsigned32,
    vtssMacsecStatusSecyRxSc6Sa2StartedTime   Unsigned32,
    vtssMacsecStatusSecyRxSc6Sa2StoppedTime   Unsigned32,
    vtssMacsecStatusSecyRxSc6Sa3Installed     TruthValue,
    vtssMacsecStatusSecyRxSc6Sa3InUse         TruthValue,
    vtssMacsecStatusSecyRxSc6Sa3NextPN        VTSSUnsigned64,
    vtssMacsecStatusSecyRxSc6Sa3LowestPN      VTSSUnsigned64,
    vtssMacsecStatusSecyRxSc6Sa3CreatedTime   Unsigned32,
    vtssMacsecStatusSecyRxSc6Sa3StartedTime   Unsigned32,
    vtssMacsecStatusSecyRxSc6Sa3StoppedTime   Unsigned32,
    vtssMacsecStatusSecyRxSc6Sa4Installed     TruthValue,
    vtssMacsecStatusSecyRxSc6Sa4InUse         TruthValue,
    vtssMacsecStatusSecyRxSc6Sa4NextPN        VTSSUnsigned64,
    vtssMacsecStatusSecyRxSc6Sa4LowestPN      VTSSUnsigned64,
    vtssMacsecStatusSecyRxSc6Sa4CreatedTime   Unsigned32,
    vtssMacsecStatusSecyRxSc6Sa4StartedTime   Unsigned32,
    vtssMacsecStatusSecyRxSc6Sa4StoppedTime   Unsigned32,
    vtssMacsecStatusSecyRxSc7Installed        TruthValue,
    vtssMacsecStatusSecyRxSc7Receiving        TruthValue,
    vtssMacsecStatusSecyRxSc7ActiveSaIdx      Unsigned32,
    vtssMacsecStatusSecyRxSc7CreatedTime      Unsigned32,
    vtssMacsecStatusSecyRxSc7StartedTime      Unsigned32,
    vtssMacsecStatusSecyRxSc7StoppedTime      Unsigned32,
    vtssMacsecStatusSecyRxSc7Sa1Installed     TruthValue,
    vtssMacsecStatusSecyRxSc7Sa1InUse         TruthValue,
    vtssMacsecStatusSecyRxSc7Sa1NextPN        VTSSUnsigned64,
    vtssMacsecStatusSecyRxSc7Sa1LowestPN      VTSSUnsigned64,
    vtssMacsecStatusSecyRxSc7Sa1CreatedTime   Unsigned32,
    vtssMacsecStatusSecyRxSc7Sa1StartedTime   Unsigned32,
    vtssMacsecStatusSecyRxSc7Sa1StoppedTime   Unsigned32,
    vtssMacsecStatusSecyRxSc7Sa2Installed     TruthValue,
    vtssMacsecStatusSecyRxSc7Sa2InUse         TruthValue,
    vtssMacsecStatusSecyRxSc7Sa2NextPN        VTSSUnsigned64,
    vtssMacsecStatusSecyRxSc7Sa2LowestPN      VTSSUnsigned64,
    vtssMacsecStatusSecyRxSc7Sa2CreatedTime   Unsigned32,
    vtssMacsecStatusSecyRxSc7Sa2StartedTime   Unsigned32,
    vtssMacsecStatusSecyRxSc7Sa2StoppedTime   Unsigned32,
    vtssMacsecStatusSecyRxSc7Sa3Installed     TruthValue,
    vtssMacsecStatusSecyRxSc7Sa3InUse         TruthValue,
    vtssMacsecStatusSecyRxSc7Sa3NextPN        VTSSUnsigned64,
    vtssMacsecStatusSecyRxSc7Sa3LowestPN      VTSSUnsigned64,
    vtssMacsecStatusSecyRxSc7Sa3CreatedTime   Unsigned32,
    vtssMacsecStatusSecyRxSc7Sa3StartedTime   Unsigned32,
    vtssMacsecStatusSecyRxSc7Sa3StoppedTime   Unsigned32,
    vtssMacsecStatusSecyRxSc7Sa4Installed     TruthValue,
    vtssMacsecStatusSecyRxSc7Sa4InUse         TruthValue,
    vtssMacsecStatusSecyRxSc7Sa4NextPN        VTSSUnsigned64,
    vtssMacsecStatusSecyRxSc7Sa4LowestPN      VTSSUnsigned64,
    vtssMacsecStatusSecyRxSc7Sa4CreatedTime   Unsigned32,
    vtssMacsecStatusSecyRxSc7Sa4StartedTime   Unsigned32,
    vtssMacsecStatusSecyRxSc7Sa4StoppedTime   Unsigned32,
    vtssMacsecStatusSecyRxSc8Installed        TruthValue,
    vtssMacsecStatusSecyRxSc8Receiving        TruthValue,
    vtssMacsecStatusSecyRxSc8ActiveSaIdx      Unsigned32,
    vtssMacsecStatusSecyRxSc8CreatedTime      Unsigned32,
    vtssMacsecStatusSecyRxSc8StartedTime      Unsigned32,
    vtssMacsecStatusSecyRxSc8StoppedTime      Unsigned32,
    vtssMacsecStatusSecyRxSc8Sa1Installed     TruthValue,
    vtssMacsecStatusSecyRxSc8Sa1InUse         TruthValue,
    vtssMacsecStatusSecyRxSc8Sa1NextPN        VTSSUnsigned64,
    vtssMacsecStatusSecyRxSc8Sa1LowestPN      VTSSUnsigned64,
    vtssMacsecStatusSecyRxSc8Sa1CreatedTime   Unsigned32,
    vtssMacsecStatusSecyRxSc8Sa1StartedTime   Unsigned32,
    vtssMacsecStatusSecyRxSc8Sa1StoppedTime   Unsigned32,
    vtssMacsecStatusSecyRxSc8Sa2Installed     TruthValue,
    vtssMacsecStatusSecyRxSc8Sa2InUse         TruthValue,
    vtssMacsecStatusSecyRxSc8Sa2NextPN        VTSSUnsigned64,
    vtssMacsecStatusSecyRxSc8Sa2LowestPN      VTSSUnsigned64,
    vtssMacsecStatusSecyRxSc8Sa2CreatedTime   Unsigned32,
    vtssMacsecStatusSecyRxSc8Sa2StartedTime   Unsigned32,
    vtssMacsecStatusSecyRxSc8Sa2StoppedTime   Unsigned32,
    vtssMacsecStatusSecyRxSc8Sa3Installed     TruthValue,
    vtssMacsecStatusSecyRxSc8Sa3InUse         TruthValue,
    vtssMacsecStatusSecyRxSc8Sa3NextPN        VTSSUnsigned64,
    vtssMacsecStatusSecyRxSc8Sa3LowestPN      VTSSUnsigned64,
    vtssMacsecStatusSecyRxSc8Sa3CreatedTime   Unsigned32,
    vtssMacsecStatusSecyRxSc8Sa3StartedTime   Unsigned32,
    vtssMacsecStatusSecyRxSc8Sa3StoppedTime   Unsigned32,
    vtssMacsecStatusSecyRxSc8Sa4Installed     TruthValue,
    vtssMacsecStatusSecyRxSc8Sa4InUse         TruthValue,
    vtssMacsecStatusSecyRxSc8Sa4NextPN        VTSSUnsigned64,
    vtssMacsecStatusSecyRxSc8Sa4LowestPN      VTSSUnsigned64,
    vtssMacsecStatusSecyRxSc8Sa4CreatedTime   Unsigned32,
    vtssMacsecStatusSecyRxSc8Sa4StartedTime   Unsigned32,
    vtssMacsecStatusSecyRxSc8Sa4StoppedTime   Unsigned32
}

vtssMacsecStatusSecyIfIndex OBJECT-TYPE
    SYNTAX      VTSSInterfaceIndex
    MAX-ACCESS  accessible-for-notify
    STATUS      current
    DESCRIPTION
        "Logical port interface index."
    ::= { vtssMacsecStatusSecyEntry 1 }

vtssMacsecStatusSecySecyId OBJECT-TYPE
    SYNTAX      Unsigned32
    MAX-ACCESS  accessible-for-notify
    STATUS      current
    DESCRIPTION
        "SecY IDs are numbered 1 through maximum number of SecYs support on an
         interface."
    ::= { vtssMacsecStatusSecyEntry 2 }

vtssMacsecStatusSecyUptimeSeconds OBJECT-TYPE
    SYNTAX      Unsigned32
    MAX-ACCESS  read-only
    STATUS      current
    DESCRIPTION
        "Number of seconds the switch has been up since boot. Useful when
         converting various timestamps to a relative time."
    ::= { vtssMacsecStatusSecyEntry 3 }

vtssMacsecStatusSecyInstalled OBJECT-TYPE
    SYNTAX      TruthValue
    MAX-ACCESS  read-only
    STATUS      current
    DESCRIPTION
        "True if installed in H/W, false if not."
    ::= { vtssMacsecStatusSecyEntry 4 }

vtssMacsecStatusSecyMacEnabled OBJECT-TYPE
    SYNTAX      TruthValue
    MAX-ACCESS  read-only
    STATUS      current
    DESCRIPTION
        "This is true if the controlled port is enabled and a Tx SA and an Rx SA
         are in use."
    ::= { vtssMacsecStatusSecyEntry 5 }

vtssMacsecStatusSecyMacOperational OBJECT-TYPE
    SYNTAX      TruthValue
    MAX-ACCESS  read-only
    STATUS      current
    DESCRIPTION
        "This is true if MacEnabled is true and the Tx SA's next packet number
         is not 0 or 0xFFFFFFFF."
    ::= { vtssMacsecStatusSecyEntry 6 }

vtssMacsecStatusSecyOperPointToPointMac OBJECT-TYPE
    SYNTAX      TruthValue
    MAX-ACCESS  read-only
    STATUS      current
    DESCRIPTION
        "This is true if and only if 1) we are running strict frame validation
         and at most one Rx SC is in use or 2) we are not running strict frame
         validation, but running full duplex on the link."
    ::= { vtssMacsecStatusSecyEntry 7 }

vtssMacsecStatusSecyTxScInstalled OBJECT-TYPE
    SYNTAX      TruthValue
    MAX-ACCESS  read-only
    STATUS      current
    DESCRIPTION
        "True if installed in H/W, false if not. If not, the remaining fields
         are invalid."
    ::= { vtssMacsecStatusSecyEntry 18 }

vtssMacsecStatusSecyTxScTransmitting OBJECT-TYPE
    SYNTAX      TruthValue
    MAX-ACCESS  read-only
    STATUS      current
    DESCRIPTION
        "True if at lest one of the SAs are in use."
    ::= { vtssMacsecStatusSecyEntry 19 }

vtssMacsecStatusSecyTxScEncodingSaIdx OBJECT-TYPE
    SYNTAX      Unsigned32
    MAX-ACCESS  read-only
    STATUS      current
    DESCRIPTION
        "Index of the encoding SA."
    ::= { vtssMacsecStatusSecyEntry 20 }

vtssMacsecStatusSecyTxScEncipheringSaIdx OBJECT-TYPE
    SYNTAX      Unsigned32
    MAX-ACCESS  read-only
    STATUS      current
    DESCRIPTION
        "Index of the enciphering SA."
    ::= { vtssMacsecStatusSecyEntry 21 }

vtssMacsecStatusSecyTxScActiveSaIdx OBJECT-TYPE
    SYNTAX      Unsigned32
    MAX-ACCESS  read-only
    STATUS      current
    DESCRIPTION
        "Index of the SA within this Tx SC that is active. -1 if no SAs are
         active."
    ::= { vtssMacsecStatusSecyEntry 22 }

vtssMacsecStatusSecyTxScCreatedTime OBJECT-TYPE
    SYNTAX      Unsigned32
    MAX-ACCESS  read-only
    STATUS      current
    DESCRIPTION
        "Time when this Tx SC was created measured in seconds since boot."
    ::= { vtssMacsecStatusSecyEntry 23 }

vtssMacsecStatusSecyTxScStartedTime OBJECT-TYPE
    SYNTAX      Unsigned32
    MAX-ACCESS  read-only
    STATUS      current
    DESCRIPTION
        "Time when this Tx SC was started measured in seconds since boot."
    ::= { vtssMacsecStatusSecyEntry 24 }

vtssMacsecStatusSecyTxScStoppedTime OBJECT-TYPE
    SYNTAX      Unsigned32
    MAX-ACCESS  read-only
    STATUS      current
    DESCRIPTION
        "Time when this Tx SC was stopped measured in seconds since boot."
    ::= { vtssMacsecStatusSecyEntry 25 }

vtssMacsecStatusSecyTxSa1Installed OBJECT-TYPE
    SYNTAX      TruthValue
    MAX-ACCESS  read-only
    STATUS      current
    DESCRIPTION
        "True if installed in H/W, false if not. If not, the remaining fields
         are invalid."
    ::= { vtssMacsecStatusSecyEntry 38 }

vtssMacsecStatusSecyTxSa1InUse OBJECT-TYPE
    SYNTAX      TruthValue
    MAX-ACCESS  read-only
    STATUS      current
    DESCRIPTION
        "If true, this SA is currently in use."
    ::= { vtssMacsecStatusSecyEntry 39 }

vtssMacsecStatusSecyTxSa1NextPN OBJECT-TYPE
    SYNTAX      VTSSUnsigned64
    MAX-ACCESS  read-only
    STATUS      current
    DESCRIPTION
        "Next packet number."
    ::= { vtssMacsecStatusSecyEntry 40 }

vtssMacsecStatusSecyTxSa1CreatedTime OBJECT-TYPE
    SYNTAX      Unsigned32
    MAX-ACCESS  read-only
    STATUS      current
    DESCRIPTION
        "Time when this Tx SA was created measured in seconds since boot."
    ::= { vtssMacsecStatusSecyEntry 41 }

vtssMacsecStatusSecyTxSa1StartedTime OBJECT-TYPE
    SYNTAX      Unsigned32
    MAX-ACCESS  read-only
    STATUS      current
    DESCRIPTION
        "Time when this Tx SA was started measured in seconds since boot."
    ::= { vtssMacsecStatusSecyEntry 42 }

vtssMacsecStatusSecyTxSa1StoppedTime OBJECT-TYPE
    SYNTAX      Unsigned32
    MAX-ACCESS  read-only
    STATUS      current
    DESCRIPTION
        "Time when this Tx SA was stopped measured in seconds since boot."
    ::= { vtssMacsecStatusSecyEntry 43 }

vtssMacsecStatusSecyTxSa2Installed OBJECT-TYPE
    SYNTAX      TruthValue
    MAX-ACCESS  read-only
    STATUS      current
    DESCRIPTION
        "True if installed in H/W, false if not. If not, the remaining fields
         are invalid."
    ::= { vtssMacsecStatusSecyEntry 49 }

vtssMacsecStatusSecyTxSa2InUse OBJECT-TYPE
    SYNTAX      TruthValue
    MAX-ACCESS  read-only
    STATUS      current
    DESCRIPTION
        "If true, this SA is currently in use."
    ::= { vtssMacsecStatusSecyEntry 50 }

vtssMacsecStatusSecyTxSa2NextPN OBJECT-TYPE
    SYNTAX      VTSSUnsigned64
    MAX-ACCESS  read-only
    STATUS      current
    DESCRIPTION
        "Next packet number."
    ::= { vtssMacsecStatusSecyEntry 51 }

vtssMacsecStatusSecyTxSa2CreatedTime OBJECT-TYPE
    SYNTAX      Unsigned32
    MAX-ACCESS  read-only
    STATUS      current
    DESCRIPTION
        "Time when this Tx SA was created measured in seconds since boot."
    ::= { vtssMacsecStatusSecyEntry 52 }

vtssMacsecStatusSecyTxSa2StartedTime OBJECT-TYPE
    SYNTAX      Unsigned32
    MAX-ACCESS  read-only
    STATUS      current
    DESCRIPTION
        "Time when this Tx SA was started measured in seconds since boot."
    ::= { vtssMacsecStatusSecyEntry 53 }

vtssMacsecStatusSecyTxSa2StoppedTime OBJECT-TYPE
    SYNTAX      Unsigned32
    MAX-ACCESS  read-only
    STATUS      current
    DESCRIPTION
        "Time when this Tx SA was stopped measured in seconds since boot."
    ::= { vtssMacsecStatusSecyEntry 54 }

vtssMacsecStatusSecyTxSa3Installed OBJECT-TYPE
    SYNTAX      TruthValue
    MAX-ACCESS  read-only
    STATUS      current
    DESCRIPTION
        "True if installed in H/W, false if not. If not, the remaining fields
         are invalid."
    ::= { vtssMacsecStatusSecyEntry 60 }

vtssMacsecStatusSecyTxSa3InUse OBJECT-TYPE
    SYNTAX      TruthValue
    MAX-ACCESS  read-only
    STATUS      current
    DESCRIPTION
        "If true, this SA is currently in use."
    ::= { vtssMacsecStatusSecyEntry 61 }

vtssMacsecStatusSecyTxSa3NextPN OBJECT-TYPE
    SYNTAX      VTSSUnsigned64
    MAX-ACCESS  read-only
    STATUS      current
    DESCRIPTION
        "Next packet number."
    ::= { vtssMacsecStatusSecyEntry 62 }

vtssMacsecStatusSecyTxSa3CreatedTime OBJECT-TYPE
    SYNTAX      Unsigned32
    MAX-ACCESS  read-only
    STATUS      current
    DESCRIPTION
        "Time when this Tx SA was created measured in seconds since boot."
    ::= { vtssMacsecStatusSecyEntry 63 }

vtssMacsecStatusSecyTxSa3StartedTime OBJECT-TYPE
    SYNTAX      Unsigned32
    MAX-ACCESS  read-only
    STATUS      current
    DESCRIPTION
        "Time when this Tx SA was started measured in seconds since boot."
    ::= { vtssMacsecStatusSecyEntry 64 }

vtssMacsecStatusSecyTxSa3StoppedTime OBJECT-TYPE
    SYNTAX      Unsigned32
    MAX-ACCESS  read-only
    STATUS      current
    DESCRIPTION
        "Time when this Tx SA was stopped measured in seconds since boot."
    ::= { vtssMacsecStatusSecyEntry 65 }

vtssMacsecStatusSecyTxSa4Installed OBJECT-TYPE
    SYNTAX      TruthValue
    MAX-ACCESS  read-only
    STATUS      current
    DESCRIPTION
        "True if installed in H/W, false if not. If not, the remaining fields
         are invalid."
    ::= { vtssMacsecStatusSecyEntry 71 }

vtssMacsecStatusSecyTxSa4InUse OBJECT-TYPE
    SYNTAX      TruthValue
    MAX-ACCESS  read-only
    STATUS      current
    DESCRIPTION
        "If true, this SA is currently in use."
    ::= { vtssMacsecStatusSecyEntry 72 }

vtssMacsecStatusSecyTxSa4NextPN OBJECT-TYPE
    SYNTAX      VTSSUnsigned64
    MAX-ACCESS  read-only
    STATUS      current
    DESCRIPTION
        "Next packet number."
    ::= { vtssMacsecStatusSecyEntry 73 }

vtssMacsecStatusSecyTxSa4CreatedTime OBJECT-TYPE
    SYNTAX      Unsigned32
    MAX-ACCESS  read-only
    STATUS      current
    DESCRIPTION
        "Time when this Tx SA was created measured in seconds since boot."
    ::= { vtssMacsecStatusSecyEntry 74 }

vtssMacsecStatusSecyTxSa4StartedTime OBJECT-TYPE
    SYNTAX      Unsigned32
    MAX-ACCESS  read-only
    STATUS      current
    DESCRIPTION
        "Time when this Tx SA was started measured in seconds since boot."
    ::= { vtssMacsecStatusSecyEntry 75 }

vtssMacsecStatusSecyTxSa4StoppedTime OBJECT-TYPE
    SYNTAX      Unsigned32
    MAX-ACCESS  read-only
    STATUS      current
    DESCRIPTION
        "Time when this Tx SA was stopped measured in seconds since boot."
    ::= { vtssMacsecStatusSecyEntry 76 }

vtssMacsecStatusSecyRxSc1Installed OBJECT-TYPE
    SYNTAX      TruthValue
    MAX-ACCESS  read-only
    STATUS      current
    DESCRIPTION
        "True if installed in H/W, false if not. If not, the remaining fields
         are invalid."
    ::= { vtssMacsecStatusSecyEntry 82 }

vtssMacsecStatusSecyRxSc1Receiving OBJECT-TYPE
    SYNTAX      TruthValue
    MAX-ACCESS  read-only
    STATUS      current
    DESCRIPTION
        "True if at least one of the SAs are in use."
    ::= { vtssMacsecStatusSecyEntry 83 }

vtssMacsecStatusSecyRxSc1ActiveSaIdx OBJECT-TYPE
    SYNTAX      Unsigned32
    MAX-ACCESS  read-only
    STATUS      current
    DESCRIPTION
        "Index of the SA within this Rx SC that is active. -1 if no SAs are
         active."
    ::= { vtssMacsecStatusSecyEntry 84 }

vtssMacsecStatusSecyRxSc1CreatedTime OBJECT-TYPE
    SYNTAX      Unsigned32
    MAX-ACCESS  read-only
    STATUS      current
    DESCRIPTION
        "Time when this Rx SC was created measured in seconds since boot."
    ::= { vtssMacsecStatusSecyEntry 85 }

vtssMacsecStatusSecyRxSc1StartedTime OBJECT-TYPE
    SYNTAX      Unsigned32
    MAX-ACCESS  read-only
    STATUS      current
    DESCRIPTION
        "Time when this Rx SC was started measured in seconds since boot."
    ::= { vtssMacsecStatusSecyEntry 86 }

vtssMacsecStatusSecyRxSc1StoppedTime OBJECT-TYPE
    SYNTAX      Unsigned32
    MAX-ACCESS  read-only
    STATUS      current
    DESCRIPTION
        "Time when this Rx SC was stopped measured in seconds since boot."
    ::= { vtssMacsecStatusSecyEntry 87 }

vtssMacsecStatusSecyRxSc1Sa1Installed OBJECT-TYPE
    SYNTAX      TruthValue
    MAX-ACCESS  read-only
    STATUS      current
    DESCRIPTION
        "True if installed in H/W, false if not. If not, the remaining fields
         are invalid."
    ::= { vtssMacsecStatusSecyEntry 100 }

vtssMacsecStatusSecyRxSc1Sa1InUse OBJECT-TYPE
    SYNTAX      TruthValue
    MAX-ACCESS  read-only
    STATUS      current
    DESCRIPTION
        "If true, this SA is currently in use."
    ::= { vtssMacsecStatusSecyEntry 101 }

vtssMacsecStatusSecyRxSc1Sa1NextPN OBJECT-TYPE
    SYNTAX      VTSSUnsigned64
    MAX-ACCESS  read-only
    STATUS      current
    DESCRIPTION
        "Next packet number."
    ::= { vtssMacsecStatusSecyEntry 102 }

vtssMacsecStatusSecyRxSc1Sa1LowestPN OBJECT-TYPE
    SYNTAX      VTSSUnsigned64
    MAX-ACCESS  read-only
    STATUS      current
    DESCRIPTION
        "Lowest packet number."
    ::= { vtssMacsecStatusSecyEntry 103 }

vtssMacsecStatusSecyRxSc1Sa1CreatedTime OBJECT-TYPE
    SYNTAX      Unsigned32
    MAX-ACCESS  read-only
    STATUS      current
    DESCRIPTION
        "Time when this Rx SC was created measured in seconds since boot."
    ::= { vtssMacsecStatusSecyEntry 104 }

vtssMacsecStatusSecyRxSc1Sa1StartedTime OBJECT-TYPE
    SYNTAX      Unsigned32
    MAX-ACCESS  read-only
    STATUS      current
    DESCRIPTION
        "Time when this Rx SC was started measured in seconds since boot."
    ::= { vtssMacsecStatusSecyEntry 105 }

vtssMacsecStatusSecyRxSc1Sa1StoppedTime OBJECT-TYPE
    SYNTAX      Unsigned32
    MAX-ACCESS  read-only
    STATUS      current
    DESCRIPTION
        "Time when this Rx SC was stopped measured in seconds since boot."
    ::= { vtssMacsecStatusSecyEntry 106 }

vtssMacsecStatusSecyRxSc1Sa2Installed OBJECT-TYPE
    SYNTAX      TruthValue
    MAX-ACCESS  read-only
    STATUS      current
    DESCRIPTION
        "True if installed in H/W, false if not. If not, the remaining fields
         are invalid."
    ::= { vtssMacsecStatusSecyEntry 112 }

vtssMacsecStatusSecyRxSc1Sa2InUse OBJECT-TYPE
    SYNTAX      TruthValue
    MAX-ACCESS  read-only
    STATUS      current
    DESCRIPTION
        "If true, this SA is currently in use."
    ::= { vtssMacsecStatusSecyEntry 113 }

vtssMacsecStatusSecyRxSc1Sa2NextPN OBJECT-TYPE
    SYNTAX      VTSSUnsigned64
    MAX-ACCESS  read-only
    STATUS      current
    DESCRIPTION
        "Next packet number."
    ::= { vtssMacsecStatusSecyEntry 114 }

vtssMacsecStatusSecyRxSc1Sa2LowestPN OBJECT-TYPE
    SYNTAX      VTSSUnsigned64
    MAX-ACCESS  read-only
    STATUS      current
    DESCRIPTION
        "Lowest packet number."
    ::= { vtssMacsecStatusSecyEntry 115 }

vtssMacsecStatusSecyRxSc1Sa2CreatedTime OBJECT-TYPE
    SYNTAX      Unsigned32
    MAX-ACCESS  read-only
    STATUS      current
    DESCRIPTION
        "Time when this Rx SC was created measured in seconds since boot."
    ::= { vtssMacsecStatusSecyEntry 116 }

vtssMacsecStatusSecyRxSc1Sa2StartedTime OBJECT-TYPE
    SYNTAX      Unsigned32
    MAX-ACCESS  read-only
    STATUS      current
    DESCRIPTION
        "Time when this Rx SC was started measured in seconds since boot."
    ::= { vtssMacsecStatusSecyEntry 117 }

vtssMacsecStatusSecyRxSc1Sa2StoppedTime OBJECT-TYPE
    SYNTAX      Unsigned32
    MAX-ACCESS  read-only
    STATUS      current
    DESCRIPTION
        "Time when this Rx SC was stopped measured in seconds since boot."
    ::= { vtssMacsecStatusSecyEntry 118 }

vtssMacsecStatusSecyRxSc1Sa3Installed OBJECT-TYPE
    SYNTAX      TruthValue
    MAX-ACCESS  read-only
    STATUS      current
    DESCRIPTION
        "True if installed in H/W, false if not. If not, the remaining fields
         are invalid."
    ::= { vtssMacsecStatusSecyEntry 124 }

vtssMacsecStatusSecyRxSc1Sa3InUse OBJECT-TYPE
    SYNTAX      TruthValue
    MAX-ACCESS  read-only
    STATUS      current
    DESCRIPTION
        "If true, this SA is currently in use."
    ::= { vtssMacsecStatusSecyEntry 125 }

vtssMacsecStatusSecyRxSc1Sa3NextPN OBJECT-TYPE
    SYNTAX      VTSSUnsigned64
    MAX-ACCESS  read-only
    STATUS      current
    DESCRIPTION
        "Next packet number."
    ::= { vtssMacsecStatusSecyEntry 126 }

vtssMacsecStatusSecyRxSc1Sa3LowestPN OBJECT-TYPE
    SYNTAX      VTSSUnsigned64
    MAX-ACCESS  read-only
    STATUS      current
    DESCRIPTION
        "Lowest packet number."
    ::= { vtssMacsecStatusSecyEntry 127 }

vtssMacsecStatusSecyRxSc1Sa3CreatedTime OBJECT-TYPE
    SYNTAX      Unsigned32
    MAX-ACCESS  read-only
    STATUS      current
    DESCRIPTION
        "Time when this Rx SC was created measured in seconds since boot."
    ::= { vtssMacsecStatusSecyEntry 128 }

vtssMacsecStatusSecyRxSc1Sa3StartedTime OBJECT-TYPE
    SYNTAX      Unsigned32
    MAX-ACCESS  read-only
    STATUS      current
    DESCRIPTION
        "Time when this Rx SC was started measured in seconds since boot."
    ::= { vtssMacsecStatusSecyEntry 129 }

vtssMacsecStatusSecyRxSc1Sa3StoppedTime OBJECT-TYPE
    SYNTAX      Unsigned32
    MAX-ACCESS  read-only
    STATUS      current
    DESCRIPTION
        "Time when this Rx SC was stopped measured in seconds since boot."
    ::= { vtssMacsecStatusSecyEntry 130 }

vtssMacsecStatusSecyRxSc1Sa4Installed OBJECT-TYPE
    SYNTAX      TruthValue
    MAX-ACCESS  read-only
    STATUS      current
    DESCRIPTION
        "True if installed in H/W, false if not. If not, the remaining fields
         are invalid."
    ::= { vtssMacsecStatusSecyEntry 136 }

vtssMacsecStatusSecyRxSc1Sa4InUse OBJECT-TYPE
    SYNTAX      TruthValue
    MAX-ACCESS  read-only
    STATUS      current
    DESCRIPTION
        "If true, this SA is currently in use."
    ::= { vtssMacsecStatusSecyEntry 137 }

vtssMacsecStatusSecyRxSc1Sa4NextPN OBJECT-TYPE
    SYNTAX      VTSSUnsigned64
    MAX-ACCESS  read-only
    STATUS      current
    DESCRIPTION
        "Next packet number."
    ::= { vtssMacsecStatusSecyEntry 138 }

vtssMacsecStatusSecyRxSc1Sa4LowestPN OBJECT-TYPE
    SYNTAX      VTSSUnsigned64
    MAX-ACCESS  read-only
    STATUS      current
    DESCRIPTION
        "Lowest packet number."
    ::= { vtssMacsecStatusSecyEntry 139 }

vtssMacsecStatusSecyRxSc1Sa4CreatedTime OBJECT-TYPE
    SYNTAX      Unsigned32
    MAX-ACCESS  read-only
    STATUS      current
    DESCRIPTION
        "Time when this Rx SC was created measured in seconds since boot."
    ::= { vtssMacsecStatusSecyEntry 140 }

vtssMacsecStatusSecyRxSc1Sa4StartedTime OBJECT-TYPE
    SYNTAX      Unsigned32
    MAX-ACCESS  read-only
    STATUS      current
    DESCRIPTION
        "Time when this Rx SC was started measured in seconds since boot."
    ::= { vtssMacsecStatusSecyEntry 141 }

vtssMacsecStatusSecyRxSc1Sa4StoppedTime OBJECT-TYPE
    SYNTAX      Unsigned32
    MAX-ACCESS  read-only
    STATUS      current
    DESCRIPTION
        "Time when this Rx SC was stopped measured in seconds since boot."
    ::= { vtssMacsecStatusSecyEntry 142 }

vtssMacsecStatusSecyRxSc2Installed OBJECT-TYPE
    SYNTAX      TruthValue
    MAX-ACCESS  read-only
    STATUS      current
    DESCRIPTION
        "True if installed in H/W, false if not. If not, the remaining fields
         are invalid."
    ::= { vtssMacsecStatusSecyEntry 148 }

vtssMacsecStatusSecyRxSc2Receiving OBJECT-TYPE
    SYNTAX      TruthValue
    MAX-ACCESS  read-only
    STATUS      current
    DESCRIPTION
        "True if at least one of the SAs are in use."
    ::= { vtssMacsecStatusSecyEntry 149 }

vtssMacsecStatusSecyRxSc2ActiveSaIdx OBJECT-TYPE
    SYNTAX      Unsigned32
    MAX-ACCESS  read-only
    STATUS      current
    DESCRIPTION
        "Index of the SA within this Rx SC that is active. -1 if no SAs are
         active."
    ::= { vtssMacsecStatusSecyEntry 150 }

vtssMacsecStatusSecyRxSc2CreatedTime OBJECT-TYPE
    SYNTAX      Unsigned32
    MAX-ACCESS  read-only
    STATUS      current
    DESCRIPTION
        "Time when this Rx SC was created measured in seconds since boot."
    ::= { vtssMacsecStatusSecyEntry 151 }

vtssMacsecStatusSecyRxSc2StartedTime OBJECT-TYPE
    SYNTAX      Unsigned32
    MAX-ACCESS  read-only
    STATUS      current
    DESCRIPTION
        "Time when this Rx SC was started measured in seconds since boot."
    ::= { vtssMacsecStatusSecyEntry 152 }

vtssMacsecStatusSecyRxSc2StoppedTime OBJECT-TYPE
    SYNTAX      Unsigned32
    MAX-ACCESS  read-only
    STATUS      current
    DESCRIPTION
        "Time when this Rx SC was stopped measured in seconds since boot."
    ::= { vtssMacsecStatusSecyEntry 153 }

vtssMacsecStatusSecyRxSc2Sa1Installed OBJECT-TYPE
    SYNTAX      TruthValue
    MAX-ACCESS  read-only
    STATUS      current
    DESCRIPTION
        "True if installed in H/W, false if not. If not, the remaining fields
         are invalid."
    ::= { vtssMacsecStatusSecyEntry 166 }

vtssMacsecStatusSecyRxSc2Sa1InUse OBJECT-TYPE
    SYNTAX      TruthValue
    MAX-ACCESS  read-only
    STATUS      current
    DESCRIPTION
        "If true, this SA is currently in use."
    ::= { vtssMacsecStatusSecyEntry 167 }

vtssMacsecStatusSecyRxSc2Sa1NextPN OBJECT-TYPE
    SYNTAX      VTSSUnsigned64
    MAX-ACCESS  read-only
    STATUS      current
    DESCRIPTION
        "Next packet number."
    ::= { vtssMacsecStatusSecyEntry 168 }

vtssMacsecStatusSecyRxSc2Sa1LowestPN OBJECT-TYPE
    SYNTAX      VTSSUnsigned64
    MAX-ACCESS  read-only
    STATUS      current
    DESCRIPTION
        "Lowest packet number."
    ::= { vtssMacsecStatusSecyEntry 169 }

vtssMacsecStatusSecyRxSc2Sa1CreatedTime OBJECT-TYPE
    SYNTAX      Unsigned32
    MAX-ACCESS  read-only
    STATUS      current
    DESCRIPTION
        "Time when this Rx SC was created measured in seconds since boot."
    ::= { vtssMacsecStatusSecyEntry 170 }

vtssMacsecStatusSecyRxSc2Sa1StartedTime OBJECT-TYPE
    SYNTAX      Unsigned32
    MAX-ACCESS  read-only
    STATUS      current
    DESCRIPTION
        "Time when this Rx SC was started measured in seconds since boot."
    ::= { vtssMacsecStatusSecyEntry 171 }

vtssMacsecStatusSecyRxSc2Sa1StoppedTime OBJECT-TYPE
    SYNTAX      Unsigned32
    MAX-ACCESS  read-only
    STATUS      current
    DESCRIPTION
        "Time when this Rx SC was stopped measured in seconds since boot."
    ::= { vtssMacsecStatusSecyEntry 172 }

vtssMacsecStatusSecyRxSc2Sa2Installed OBJECT-TYPE
    SYNTAX      TruthValue
    MAX-ACCESS  read-only
    STATUS      current
    DESCRIPTION
        "True if installed in H/W, false if not. If not, the remaining fields
         are invalid."
    ::= { vtssMacsecStatusSecyEntry 178 }

vtssMacsecStatusSecyRxSc2Sa2InUse OBJECT-TYPE
    SYNTAX      TruthValue
    MAX-ACCESS  read-only
    STATUS      current
    DESCRIPTION
        "If true, this SA is currently in use."
    ::= { vtssMacsecStatusSecyEntry 179 }

vtssMacsecStatusSecyRxSc2Sa2NextPN OBJECT-TYPE
    SYNTAX      VTSSUnsigned64
    MAX-ACCESS  read-only
    STATUS      current
    DESCRIPTION
        "Next packet number."
    ::= { vtssMacsecStatusSecyEntry 180 }

vtssMacsecStatusSecyRxSc2Sa2LowestPN OBJECT-TYPE
    SYNTAX      VTSSUnsigned64
    MAX-ACCESS  read-only
    STATUS      current
    DESCRIPTION
        "Lowest packet number."
    ::= { vtssMacsecStatusSecyEntry 181 }

vtssMacsecStatusSecyRxSc2Sa2CreatedTime OBJECT-TYPE
    SYNTAX      Unsigned32
    MAX-ACCESS  read-only
    STATUS      current
    DESCRIPTION
        "Time when this Rx SC was created measured in seconds since boot."
    ::= { vtssMacsecStatusSecyEntry 182 }

vtssMacsecStatusSecyRxSc2Sa2StartedTime OBJECT-TYPE
    SYNTAX      Unsigned32
    MAX-ACCESS  read-only
    STATUS      current
    DESCRIPTION
        "Time when this Rx SC was started measured in seconds since boot."
    ::= { vtssMacsecStatusSecyEntry 183 }

vtssMacsecStatusSecyRxSc2Sa2StoppedTime OBJECT-TYPE
    SYNTAX      Unsigned32
    MAX-ACCESS  read-only
    STATUS      current
    DESCRIPTION
        "Time when this Rx SC was stopped measured in seconds since boot."
    ::= { vtssMacsecStatusSecyEntry 184 }

vtssMacsecStatusSecyRxSc2Sa3Installed OBJECT-TYPE
    SYNTAX      TruthValue
    MAX-ACCESS  read-only
    STATUS      current
    DESCRIPTION
        "True if installed in H/W, false if not. If not, the remaining fields
         are invalid."
    ::= { vtssMacsecStatusSecyEntry 190 }

vtssMacsecStatusSecyRxSc2Sa3InUse OBJECT-TYPE
    SYNTAX      TruthValue
    MAX-ACCESS  read-only
    STATUS      current
    DESCRIPTION
        "If true, this SA is currently in use."
    ::= { vtssMacsecStatusSecyEntry 191 }

vtssMacsecStatusSecyRxSc2Sa3NextPN OBJECT-TYPE
    SYNTAX      VTSSUnsigned64
    MAX-ACCESS  read-only
    STATUS      current
    DESCRIPTION
        "Next packet number."
    ::= { vtssMacsecStatusSecyEntry 192 }

vtssMacsecStatusSecyRxSc2Sa3LowestPN OBJECT-TYPE
    SYNTAX      VTSSUnsigned64
    MAX-ACCESS  read-only
    STATUS      current
    DESCRIPTION
        "Lowest packet number."
    ::= { vtssMacsecStatusSecyEntry 193 }

vtssMacsecStatusSecyRxSc2Sa3CreatedTime OBJECT-TYPE
    SYNTAX      Unsigned32
    MAX-ACCESS  read-only
    STATUS      current
    DESCRIPTION
        "Time when this Rx SC was created measured in seconds since boot."
    ::= { vtssMacsecStatusSecyEntry 194 }

vtssMacsecStatusSecyRxSc2Sa3StartedTime OBJECT-TYPE
    SYNTAX      Unsigned32
    MAX-ACCESS  read-only
    STATUS      current
    DESCRIPTION
        "Time when this Rx SC was started measured in seconds since boot."
    ::= { vtssMacsecStatusSecyEntry 195 }

vtssMacsecStatusSecyRxSc2Sa3StoppedTime OBJECT-TYPE
    SYNTAX      Unsigned32
    MAX-ACCESS  read-only
    STATUS      current
    DESCRIPTION
        "Time when this Rx SC was stopped measured in seconds since boot."
    ::= { vtssMacsecStatusSecyEntry 196 }

vtssMacsecStatusSecyRxSc2Sa4Installed OBJECT-TYPE
    SYNTAX      TruthValue
    MAX-ACCESS  read-only
    STATUS      current
    DESCRIPTION
        "True if installed in H/W, false if not. If not, the remaining fields
         are invalid."
    ::= { vtssMacsecStatusSecyEntry 202 }

vtssMacsecStatusSecyRxSc2Sa4InUse OBJECT-TYPE
    SYNTAX      TruthValue
    MAX-ACCESS  read-only
    STATUS      current
    DESCRIPTION
        "If true, this SA is currently in use."
    ::= { vtssMacsecStatusSecyEntry 203 }

vtssMacsecStatusSecyRxSc2Sa4NextPN OBJECT-TYPE
    SYNTAX      VTSSUnsigned64
    MAX-ACCESS  read-only
    STATUS      current
    DESCRIPTION
        "Next packet number."
    ::= { vtssMacsecStatusSecyEntry 204 }

vtssMacsecStatusSecyRxSc2Sa4LowestPN OBJECT-TYPE
    SYNTAX      VTSSUnsigned64
    MAX-ACCESS  read-only
    STATUS      current
    DESCRIPTION
        "Lowest packet number."
    ::= { vtssMacsecStatusSecyEntry 205 }

vtssMacsecStatusSecyRxSc2Sa4CreatedTime OBJECT-TYPE
    SYNTAX      Unsigned32
    MAX-ACCESS  read-only
    STATUS      current
    DESCRIPTION
        "Time when this Rx SC was created measured in seconds since boot."
    ::= { vtssMacsecStatusSecyEntry 206 }

vtssMacsecStatusSecyRxSc2Sa4StartedTime OBJECT-TYPE
    SYNTAX      Unsigned32
    MAX-ACCESS  read-only
    STATUS      current
    DESCRIPTION
        "Time when this Rx SC was started measured in seconds since boot."
    ::= { vtssMacsecStatusSecyEntry 207 }

vtssMacsecStatusSecyRxSc2Sa4StoppedTime OBJECT-TYPE
    SYNTAX      Unsigned32
    MAX-ACCESS  read-only
    STATUS      current
    DESCRIPTION
        "Time when this Rx SC was stopped measured in seconds since boot."
    ::= { vtssMacsecStatusSecyEntry 208 }

vtssMacsecStatusSecyRxSc3Installed OBJECT-TYPE
    SYNTAX      TruthValue
    MAX-ACCESS  read-only
    STATUS      current
    DESCRIPTION
        "True if installed in H/W, false if not. If not, the remaining fields
         are invalid."
    ::= { vtssMacsecStatusSecyEntry 214 }

vtssMacsecStatusSecyRxSc3Receiving OBJECT-TYPE
    SYNTAX      TruthValue
    MAX-ACCESS  read-only
    STATUS      current
    DESCRIPTION
        "True if at least one of the SAs are in use."
    ::= { vtssMacsecStatusSecyEntry 215 }

vtssMacsecStatusSecyRxSc3ActiveSaIdx OBJECT-TYPE
    SYNTAX      Unsigned32
    MAX-ACCESS  read-only
    STATUS      current
    DESCRIPTION
        "Index of the SA within this Rx SC that is active. -1 if no SAs are
         active."
    ::= { vtssMacsecStatusSecyEntry 216 }

vtssMacsecStatusSecyRxSc3CreatedTime OBJECT-TYPE
    SYNTAX      Unsigned32
    MAX-ACCESS  read-only
    STATUS      current
    DESCRIPTION
        "Time when this Rx SC was created measured in seconds since boot."
    ::= { vtssMacsecStatusSecyEntry 217 }

vtssMacsecStatusSecyRxSc3StartedTime OBJECT-TYPE
    SYNTAX      Unsigned32
    MAX-ACCESS  read-only
    STATUS      current
    DESCRIPTION
        "Time when this Rx SC was started measured in seconds since boot."
    ::= { vtssMacsecStatusSecyEntry 218 }

vtssMacsecStatusSecyRxSc3StoppedTime OBJECT-TYPE
    SYNTAX      Unsigned32
    MAX-ACCESS  read-only
    STATUS      current
    DESCRIPTION
        "Time when this Rx SC was stopped measured in seconds since boot."
    ::= { vtssMacsecStatusSecyEntry 219 }

vtssMacsecStatusSecyRxSc3Sa1Installed OBJECT-TYPE
    SYNTAX      TruthValue
    MAX-ACCESS  read-only
    STATUS      current
    DESCRIPTION
        "True if installed in H/W, false if not. If not, the remaining fields
         are invalid."
    ::= { vtssMacsecStatusSecyEntry 232 }

vtssMacsecStatusSecyRxSc3Sa1InUse OBJECT-TYPE
    SYNTAX      TruthValue
    MAX-ACCESS  read-only
    STATUS      current
    DESCRIPTION
        "If true, this SA is currently in use."
    ::= { vtssMacsecStatusSecyEntry 233 }

vtssMacsecStatusSecyRxSc3Sa1NextPN OBJECT-TYPE
    SYNTAX      VTSSUnsigned64
    MAX-ACCESS  read-only
    STATUS      current
    DESCRIPTION
        "Next packet number."
    ::= { vtssMacsecStatusSecyEntry 234 }

vtssMacsecStatusSecyRxSc3Sa1LowestPN OBJECT-TYPE
    SYNTAX      VTSSUnsigned64
    MAX-ACCESS  read-only
    STATUS      current
    DESCRIPTION
        "Lowest packet number."
    ::= { vtssMacsecStatusSecyEntry 235 }

vtssMacsecStatusSecyRxSc3Sa1CreatedTime OBJECT-TYPE
    SYNTAX      Unsigned32
    MAX-ACCESS  read-only
    STATUS      current
    DESCRIPTION
        "Time when this Rx SC was created measured in seconds since boot."
    ::= { vtssMacsecStatusSecyEntry 236 }

vtssMacsecStatusSecyRxSc3Sa1StartedTime OBJECT-TYPE
    SYNTAX      Unsigned32
    MAX-ACCESS  read-only
    STATUS      current
    DESCRIPTION
        "Time when this Rx SC was started measured in seconds since boot."
    ::= { vtssMacsecStatusSecyEntry 237 }

vtssMacsecStatusSecyRxSc3Sa1StoppedTime OBJECT-TYPE
    SYNTAX      Unsigned32
    MAX-ACCESS  read-only
    STATUS      current
    DESCRIPTION
        "Time when this Rx SC was stopped measured in seconds since boot."
    ::= { vtssMacsecStatusSecyEntry 238 }

vtssMacsecStatusSecyRxSc3Sa2Installed OBJECT-TYPE
    SYNTAX      TruthValue
    MAX-ACCESS  read-only
    STATUS      current
    DESCRIPTION
        "True if installed in H/W, false if not. If not, the remaining fields
         are invalid."
    ::= { vtssMacsecStatusSecyEntry 244 }

vtssMacsecStatusSecyRxSc3Sa2InUse OBJECT-TYPE
    SYNTAX      TruthValue
    MAX-ACCESS  read-only
    STATUS      current
    DESCRIPTION
        "If true, this SA is currently in use."
    ::= { vtssMacsecStatusSecyEntry 245 }

vtssMacsecStatusSecyRxSc3Sa2NextPN OBJECT-TYPE
    SYNTAX      VTSSUnsigned64
    MAX-ACCESS  read-only
    STATUS      current
    DESCRIPTION
        "Next packet number."
    ::= { vtssMacsecStatusSecyEntry 246 }

vtssMacsecStatusSecyRxSc3Sa2LowestPN OBJECT-TYPE
    SYNTAX      VTSSUnsigned64
    MAX-ACCESS  read-only
    STATUS      current
    DESCRIPTION
        "Lowest packet number."
    ::= { vtssMacsecStatusSecyEntry 247 }

vtssMacsecStatusSecyRxSc3Sa2CreatedTime OBJECT-TYPE
    SYNTAX      Unsigned32
    MAX-ACCESS  read-only
    STATUS      current
    DESCRIPTION
        "Time when this Rx SC was created measured in seconds since boot."
    ::= { vtssMacsecStatusSecyEntry 248 }

vtssMacsecStatusSecyRxSc3Sa2StartedTime OBJECT-TYPE
    SYNTAX      Unsigned32
    MAX-ACCESS  read-only
    STATUS      current
    DESCRIPTION
        "Time when this Rx SC was started measured in seconds since boot."
    ::= { vtssMacsecStatusSecyEntry 249 }

vtssMacsecStatusSecyRxSc3Sa2StoppedTime OBJECT-TYPE
    SYNTAX      Unsigned32
    MAX-ACCESS  read-only
    STATUS      current
    DESCRIPTION
        "Time when this Rx SC was stopped measured in seconds since boot."
    ::= { vtssMacsecStatusSecyEntry 250 }

vtssMacsecStatusSecyRxSc3Sa3Installed OBJECT-TYPE
    SYNTAX      TruthValue
    MAX-ACCESS  read-only
    STATUS      current
    DESCRIPTION
        "True if installed in H/W, false if not. If not, the remaining fields
         are invalid."
    ::= { vtssMacsecStatusSecyEntry 256 }

vtssMacsecStatusSecyRxSc3Sa3InUse OBJECT-TYPE
    SYNTAX      TruthValue
    MAX-ACCESS  read-only
    STATUS      current
    DESCRIPTION
        "If true, this SA is currently in use."
    ::= { vtssMacsecStatusSecyEntry 257 }

vtssMacsecStatusSecyRxSc3Sa3NextPN OBJECT-TYPE
    SYNTAX      VTSSUnsigned64
    MAX-ACCESS  read-only
    STATUS      current
    DESCRIPTION
        "Next packet number."
    ::= { vtssMacsecStatusSecyEntry 258 }

vtssMacsecStatusSecyRxSc3Sa3LowestPN OBJECT-TYPE
    SYNTAX      VTSSUnsigned64
    MAX-ACCESS  read-only
    STATUS      current
    DESCRIPTION
        "Lowest packet number."
    ::= { vtssMacsecStatusSecyEntry 259 }

vtssMacsecStatusSecyRxSc3Sa3CreatedTime OBJECT-TYPE
    SYNTAX      Unsigned32
    MAX-ACCESS  read-only
    STATUS      current
    DESCRIPTION
        "Time when this Rx SC was created measured in seconds since boot."
    ::= { vtssMacsecStatusSecyEntry 260 }

vtssMacsecStatusSecyRxSc3Sa3StartedTime OBJECT-TYPE
    SYNTAX      Unsigned32
    MAX-ACCESS  read-only
    STATUS      current
    DESCRIPTION
        "Time when this Rx SC was started measured in seconds since boot."
    ::= { vtssMacsecStatusSecyEntry 261 }

vtssMacsecStatusSecyRxSc3Sa3StoppedTime OBJECT-TYPE
    SYNTAX      Unsigned32
    MAX-ACCESS  read-only
    STATUS      current
    DESCRIPTION
        "Time when this Rx SC was stopped measured in seconds since boot."
    ::= { vtssMacsecStatusSecyEntry 262 }

vtssMacsecStatusSecyRxSc3Sa4Installed OBJECT-TYPE
    SYNTAX      TruthValue
    MAX-ACCESS  read-only
    STATUS      current
    DESCRIPTION
        "True if installed in H/W, false if not. If not, the remaining fields
         are invalid."
    ::= { vtssMacsecStatusSecyEntry 268 }

vtssMacsecStatusSecyRxSc3Sa4InUse OBJECT-TYPE
    SYNTAX      TruthValue
    MAX-ACCESS  read-only
    STATUS      current
    DESCRIPTION
        "If true, this SA is currently in use."
    ::= { vtssMacsecStatusSecyEntry 269 }

vtssMacsecStatusSecyRxSc3Sa4NextPN OBJECT-TYPE
    SYNTAX      VTSSUnsigned64
    MAX-ACCESS  read-only
    STATUS      current
    DESCRIPTION
        "Next packet number."
    ::= { vtssMacsecStatusSecyEntry 270 }

vtssMacsecStatusSecyRxSc3Sa4LowestPN OBJECT-TYPE
    SYNTAX      VTSSUnsigned64
    MAX-ACCESS  read-only
    STATUS      current
    DESCRIPTION
        "Lowest packet number."
    ::= { vtssMacsecStatusSecyEntry 271 }

vtssMacsecStatusSecyRxSc3Sa4CreatedTime OBJECT-TYPE
    SYNTAX      Unsigned32
    MAX-ACCESS  read-only
    STATUS      current
    DESCRIPTION
        "Time when this Rx SC was created measured in seconds since boot."
    ::= { vtssMacsecStatusSecyEntry 272 }

vtssMacsecStatusSecyRxSc3Sa4StartedTime OBJECT-TYPE
    SYNTAX      Unsigned32
    MAX-ACCESS  read-only
    STATUS      current
    DESCRIPTION
        "Time when this Rx SC was started measured in seconds since boot."
    ::= { vtssMacsecStatusSecyEntry 273 }

vtssMacsecStatusSecyRxSc3Sa4StoppedTime OBJECT-TYPE
    SYNTAX      Unsigned32
    MAX-ACCESS  read-only
    STATUS      current
    DESCRIPTION
        "Time when this Rx SC was stopped measured in seconds since boot."
    ::= { vtssMacsecStatusSecyEntry 274 }

vtssMacsecStatusSecyRxSc4Installed OBJECT-TYPE
    SYNTAX      TruthValue
    MAX-ACCESS  read-only
    STATUS      current
    DESCRIPTION
        "True if installed in H/W, false if not. If not, the remaining fields
         are invalid."
    ::= { vtssMacsecStatusSecyEntry 280 }

vtssMacsecStatusSecyRxSc4Receiving OBJECT-TYPE
    SYNTAX      TruthValue
    MAX-ACCESS  read-only
    STATUS      current
    DESCRIPTION
        "True if at least one of the SAs are in use."
    ::= { vtssMacsecStatusSecyEntry 281 }

vtssMacsecStatusSecyRxSc4ActiveSaIdx OBJECT-TYPE
    SYNTAX      Unsigned32
    MAX-ACCESS  read-only
    STATUS      current
    DESCRIPTION
        "Index of the SA within this Rx SC that is active. -1 if no SAs are
         active."
    ::= { vtssMacsecStatusSecyEntry 282 }

vtssMacsecStatusSecyRxSc4CreatedTime OBJECT-TYPE
    SYNTAX      Unsigned32
    MAX-ACCESS  read-only
    STATUS      current
    DESCRIPTION
        "Time when this Rx SC was created measured in seconds since boot."
    ::= { vtssMacsecStatusSecyEntry 283 }

vtssMacsecStatusSecyRxSc4StartedTime OBJECT-TYPE
    SYNTAX      Unsigned32
    MAX-ACCESS  read-only
    STATUS      current
    DESCRIPTION
        "Time when this Rx SC was started measured in seconds since boot."
    ::= { vtssMacsecStatusSecyEntry 284 }

vtssMacsecStatusSecyRxSc4StoppedTime OBJECT-TYPE
    SYNTAX      Unsigned32
    MAX-ACCESS  read-only
    STATUS      current
    DESCRIPTION
        "Time when this Rx SC was stopped measured in seconds since boot."
    ::= { vtssMacsecStatusSecyEntry 285 }

vtssMacsecStatusSecyRxSc4Sa1Installed OBJECT-TYPE
    SYNTAX      TruthValue
    MAX-ACCESS  read-only
    STATUS      current
    DESCRIPTION
        "True if installed in H/W, false if not. If not, the remaining fields
         are invalid."
    ::= { vtssMacsecStatusSecyEntry 298 }

vtssMacsecStatusSecyRxSc4Sa1InUse OBJECT-TYPE
    SYNTAX      TruthValue
    MAX-ACCESS  read-only
    STATUS      current
    DESCRIPTION
        "If true, this SA is currently in use."
    ::= { vtssMacsecStatusSecyEntry 299 }

vtssMacsecStatusSecyRxSc4Sa1NextPN OBJECT-TYPE
    SYNTAX      VTSSUnsigned64
    MAX-ACCESS  read-only
    STATUS      current
    DESCRIPTION
        "Next packet number."
    ::= { vtssMacsecStatusSecyEntry 300 }

vtssMacsecStatusSecyRxSc4Sa1LowestPN OBJECT-TYPE
    SYNTAX      VTSSUnsigned64
    MAX-ACCESS  read-only
    STATUS      current
    DESCRIPTION
        "Lowest packet number."
    ::= { vtssMacsecStatusSecyEntry 301 }

vtssMacsecStatusSecyRxSc4Sa1CreatedTime OBJECT-TYPE
    SYNTAX      Unsigned32
    MAX-ACCESS  read-only
    STATUS      current
    DESCRIPTION
        "Time when this Rx SC was created measured in seconds since boot."
    ::= { vtssMacsecStatusSecyEntry 302 }

vtssMacsecStatusSecyRxSc4Sa1StartedTime OBJECT-TYPE
    SYNTAX      Unsigned32
    MAX-ACCESS  read-only
    STATUS      current
    DESCRIPTION
        "Time when this Rx SC was started measured in seconds since boot."
    ::= { vtssMacsecStatusSecyEntry 303 }

vtssMacsecStatusSecyRxSc4Sa1StoppedTime OBJECT-TYPE
    SYNTAX      Unsigned32
    MAX-ACCESS  read-only
    STATUS      current
    DESCRIPTION
        "Time when this Rx SC was stopped measured in seconds since boot."
    ::= { vtssMacsecStatusSecyEntry 304 }

vtssMacsecStatusSecyRxSc4Sa2Installed OBJECT-TYPE
    SYNTAX      TruthValue
    MAX-ACCESS  read-only
    STATUS      current
    DESCRIPTION
        "True if installed in H/W, false if not. If not, the remaining fields
         are invalid."
    ::= { vtssMacsecStatusSecyEntry 310 }

vtssMacsecStatusSecyRxSc4Sa2InUse OBJECT-TYPE
    SYNTAX      TruthValue
    MAX-ACCESS  read-only
    STATUS      current
    DESCRIPTION
        "If true, this SA is currently in use."
    ::= { vtssMacsecStatusSecyEntry 311 }

vtssMacsecStatusSecyRxSc4Sa2NextPN OBJECT-TYPE
    SYNTAX      VTSSUnsigned64
    MAX-ACCESS  read-only
    STATUS      current
    DESCRIPTION
        "Next packet number."
    ::= { vtssMacsecStatusSecyEntry 312 }

vtssMacsecStatusSecyRxSc4Sa2LowestPN OBJECT-TYPE
    SYNTAX      VTSSUnsigned64
    MAX-ACCESS  read-only
    STATUS      current
    DESCRIPTION
        "Lowest packet number."
    ::= { vtssMacsecStatusSecyEntry 313 }

vtssMacsecStatusSecyRxSc4Sa2CreatedTime OBJECT-TYPE
    SYNTAX      Unsigned32
    MAX-ACCESS  read-only
    STATUS      current
    DESCRIPTION
        "Time when this Rx SC was created measured in seconds since boot."
    ::= { vtssMacsecStatusSecyEntry 314 }

vtssMacsecStatusSecyRxSc4Sa2StartedTime OBJECT-TYPE
    SYNTAX      Unsigned32
    MAX-ACCESS  read-only
    STATUS      current
    DESCRIPTION
        "Time when this Rx SC was started measured in seconds since boot."
    ::= { vtssMacsecStatusSecyEntry 315 }

vtssMacsecStatusSecyRxSc4Sa2StoppedTime OBJECT-TYPE
    SYNTAX      Unsigned32
    MAX-ACCESS  read-only
    STATUS      current
    DESCRIPTION
        "Time when this Rx SC was stopped measured in seconds since boot."
    ::= { vtssMacsecStatusSecyEntry 316 }

vtssMacsecStatusSecyRxSc4Sa3Installed OBJECT-TYPE
    SYNTAX      TruthValue
    MAX-ACCESS  read-only
    STATUS      current
    DESCRIPTION
        "True if installed in H/W, false if not. If not, the remaining fields
         are invalid."
    ::= { vtssMacsecStatusSecyEntry 322 }

vtssMacsecStatusSecyRxSc4Sa3InUse OBJECT-TYPE
    SYNTAX      TruthValue
    MAX-ACCESS  read-only
    STATUS      current
    DESCRIPTION
        "If true, this SA is currently in use."
    ::= { vtssMacsecStatusSecyEntry 323 }

vtssMacsecStatusSecyRxSc4Sa3NextPN OBJECT-TYPE
    SYNTAX      VTSSUnsigned64
    MAX-ACCESS  read-only
    STATUS      current
    DESCRIPTION
        "Next packet number."
    ::= { vtssMacsecStatusSecyEntry 324 }

vtssMacsecStatusSecyRxSc4Sa3LowestPN OBJECT-TYPE
    SYNTAX      VTSSUnsigned64
    MAX-ACCESS  read-only
    STATUS      current
    DESCRIPTION
        "Lowest packet number."
    ::= { vtssMacsecStatusSecyEntry 325 }

vtssMacsecStatusSecyRxSc4Sa3CreatedTime OBJECT-TYPE
    SYNTAX      Unsigned32
    MAX-ACCESS  read-only
    STATUS      current
    DESCRIPTION
        "Time when this Rx SC was created measured in seconds since boot."
    ::= { vtssMacsecStatusSecyEntry 326 }

vtssMacsecStatusSecyRxSc4Sa3StartedTime OBJECT-TYPE
    SYNTAX      Unsigned32
    MAX-ACCESS  read-only
    STATUS      current
    DESCRIPTION
        "Time when this Rx SC was started measured in seconds since boot."
    ::= { vtssMacsecStatusSecyEntry 327 }

vtssMacsecStatusSecyRxSc4Sa3StoppedTime OBJECT-TYPE
    SYNTAX      Unsigned32
    MAX-ACCESS  read-only
    STATUS      current
    DESCRIPTION
        "Time when this Rx SC was stopped measured in seconds since boot."
    ::= { vtssMacsecStatusSecyEntry 328 }

vtssMacsecStatusSecyRxSc4Sa4Installed OBJECT-TYPE
    SYNTAX      TruthValue
    MAX-ACCESS  read-only
    STATUS      current
    DESCRIPTION
        "True if installed in H/W, false if not. If not, the remaining fields
         are invalid."
    ::= { vtssMacsecStatusSecyEntry 334 }

vtssMacsecStatusSecyRxSc4Sa4InUse OBJECT-TYPE
    SYNTAX      TruthValue
    MAX-ACCESS  read-only
    STATUS      current
    DESCRIPTION
        "If true, this SA is currently in use."
    ::= { vtssMacsecStatusSecyEntry 335 }

vtssMacsecStatusSecyRxSc4Sa4NextPN OBJECT-TYPE
    SYNTAX      VTSSUnsigned64
    MAX-ACCESS  read-only
    STATUS      current
    DESCRIPTION
        "Next packet number."
    ::= { vtssMacsecStatusSecyEntry 336 }

vtssMacsecStatusSecyRxSc4Sa4LowestPN OBJECT-TYPE
    SYNTAX      VTSSUnsigned64
    MAX-ACCESS  read-only
    STATUS      current
    DESCRIPTION
        "Lowest packet number."
    ::= { vtssMacsecStatusSecyEntry 337 }

vtssMacsecStatusSecyRxSc4Sa4CreatedTime OBJECT-TYPE
    SYNTAX      Unsigned32
    MAX-ACCESS  read-only
    STATUS      current
    DESCRIPTION
        "Time when this Rx SC was created measured in seconds since boot."
    ::= { vtssMacsecStatusSecyEntry 338 }

vtssMacsecStatusSecyRxSc4Sa4StartedTime OBJECT-TYPE
    SYNTAX      Unsigned32
    MAX-ACCESS  read-only
    STATUS      current
    DESCRIPTION
        "Time when this Rx SC was started measured in seconds since boot."
    ::= { vtssMacsecStatusSecyEntry 339 }

vtssMacsecStatusSecyRxSc4Sa4StoppedTime OBJECT-TYPE
    SYNTAX      Unsigned32
    MAX-ACCESS  read-only
    STATUS      current
    DESCRIPTION
        "Time when this Rx SC was stopped measured in seconds since boot."
    ::= { vtssMacsecStatusSecyEntry 340 }

vtssMacsecStatusSecyRxSc5Installed OBJECT-TYPE
    SYNTAX      TruthValue
    MAX-ACCESS  read-only
    STATUS      current
    DESCRIPTION
        "True if installed in H/W, false if not. If not, the remaining fields
         are invalid."
    ::= { vtssMacsecStatusSecyEntry 346 }

vtssMacsecStatusSecyRxSc5Receiving OBJECT-TYPE
    SYNTAX      TruthValue
    MAX-ACCESS  read-only
    STATUS      current
    DESCRIPTION
        "True if at least one of the SAs are in use."
    ::= { vtssMacsecStatusSecyEntry 347 }

vtssMacsecStatusSecyRxSc5ActiveSaIdx OBJECT-TYPE
    SYNTAX      Unsigned32
    MAX-ACCESS  read-only
    STATUS      current
    DESCRIPTION
        "Index of the SA within this Rx SC that is active. -1 if no SAs are
         active."
    ::= { vtssMacsecStatusSecyEntry 348 }

vtssMacsecStatusSecyRxSc5CreatedTime OBJECT-TYPE
    SYNTAX      Unsigned32
    MAX-ACCESS  read-only
    STATUS      current
    DESCRIPTION
        "Time when this Rx SC was created measured in seconds since boot."
    ::= { vtssMacsecStatusSecyEntry 349 }

vtssMacsecStatusSecyRxSc5StartedTime OBJECT-TYPE
    SYNTAX      Unsigned32
    MAX-ACCESS  read-only
    STATUS      current
    DESCRIPTION
        "Time when this Rx SC was started measured in seconds since boot."
    ::= { vtssMacsecStatusSecyEntry 350 }

vtssMacsecStatusSecyRxSc5StoppedTime OBJECT-TYPE
    SYNTAX      Unsigned32
    MAX-ACCESS  read-only
    STATUS      current
    DESCRIPTION
        "Time when this Rx SC was stopped measured in seconds since boot."
    ::= { vtssMacsecStatusSecyEntry 351 }

vtssMacsecStatusSecyRxSc5Sa1Installed OBJECT-TYPE
    SYNTAX      TruthValue
    MAX-ACCESS  read-only
    STATUS      current
    DESCRIPTION
        "True if installed in H/W, false if not. If not, the remaining fields
         are invalid."
    ::= { vtssMacsecStatusSecyEntry 364 }

vtssMacsecStatusSecyRxSc5Sa1InUse OBJECT-TYPE
    SYNTAX      TruthValue
    MAX-ACCESS  read-only
    STATUS      current
    DESCRIPTION
        "If true, this SA is currently in use."
    ::= { vtssMacsecStatusSecyEntry 365 }

vtssMacsecStatusSecyRxSc5Sa1NextPN OBJECT-TYPE
    SYNTAX      VTSSUnsigned64
    MAX-ACCESS  read-only
    STATUS      current
    DESCRIPTION
        "Next packet number."
    ::= { vtssMacsecStatusSecyEntry 366 }

vtssMacsecStatusSecyRxSc5Sa1LowestPN OBJECT-TYPE
    SYNTAX      VTSSUnsigned64
    MAX-ACCESS  read-only
    STATUS      current
    DESCRIPTION
        "Lowest packet number."
    ::= { vtssMacsecStatusSecyEntry 367 }

vtssMacsecStatusSecyRxSc5Sa1CreatedTime OBJECT-TYPE
    SYNTAX      Unsigned32
    MAX-ACCESS  read-only
    STATUS      current
    DESCRIPTION
        "Time when this Rx SC was created measured in seconds since boot."
    ::= { vtssMacsecStatusSecyEntry 368 }

vtssMacsecStatusSecyRxSc5Sa1StartedTime OBJECT-TYPE
    SYNTAX      Unsigned32
    MAX-ACCESS  read-only
    STATUS      current
    DESCRIPTION
        "Time when this Rx SC was started measured in seconds since boot."
    ::= { vtssMacsecStatusSecyEntry 369 }

vtssMacsecStatusSecyRxSc5Sa1StoppedTime OBJECT-TYPE
    SYNTAX      Unsigned32
    MAX-ACCESS  read-only
    STATUS      current
    DESCRIPTION
        "Time when this Rx SC was stopped measured in seconds since boot."
    ::= { vtssMacsecStatusSecyEntry 370 }

vtssMacsecStatusSecyRxSc5Sa2Installed OBJECT-TYPE
    SYNTAX      TruthValue
    MAX-ACCESS  read-only
    STATUS      current
    DESCRIPTION
        "True if installed in H/W, false if not. If not, the remaining fields
         are invalid."
    ::= { vtssMacsecStatusSecyEntry 376 }

vtssMacsecStatusSecyRxSc5Sa2InUse OBJECT-TYPE
    SYNTAX      TruthValue
    MAX-ACCESS  read-only
    STATUS      current
    DESCRIPTION
        "If true, this SA is currently in use."
    ::= { vtssMacsecStatusSecyEntry 377 }

vtssMacsecStatusSecyRxSc5Sa2NextPN OBJECT-TYPE
    SYNTAX      VTSSUnsigned64
    MAX-ACCESS  read-only
    STATUS      current
    DESCRIPTION
        "Next packet number."
    ::= { vtssMacsecStatusSecyEntry 378 }

vtssMacsecStatusSecyRxSc5Sa2LowestPN OBJECT-TYPE
    SYNTAX      VTSSUnsigned64
    MAX-ACCESS  read-only
    STATUS      current
    DESCRIPTION
        "Lowest packet number."
    ::= { vtssMacsecStatusSecyEntry 379 }

vtssMacsecStatusSecyRxSc5Sa2CreatedTime OBJECT-TYPE
    SYNTAX      Unsigned32
    MAX-ACCESS  read-only
    STATUS      current
    DESCRIPTION
        "Time when this Rx SC was created measured in seconds since boot."
    ::= { vtssMacsecStatusSecyEntry 380 }

vtssMacsecStatusSecyRxSc5Sa2StartedTime OBJECT-TYPE
    SYNTAX      Unsigned32
    MAX-ACCESS  read-only
    STATUS      current
    DESCRIPTION
        "Time when this Rx SC was started measured in seconds since boot."
    ::= { vtssMacsecStatusSecyEntry 381 }

vtssMacsecStatusSecyRxSc5Sa2StoppedTime OBJECT-TYPE
    SYNTAX      Unsigned32
    MAX-ACCESS  read-only
    STATUS      current
    DESCRIPTION
        "Time when this Rx SC was stopped measured in seconds since boot."
    ::= { vtssMacsecStatusSecyEntry 382 }

vtssMacsecStatusSecyRxSc5Sa3Installed OBJECT-TYPE
    SYNTAX      TruthValue
    MAX-ACCESS  read-only
    STATUS      current
    DESCRIPTION
        "True if installed in H/W, false if not. If not, the remaining fields
         are invalid."
    ::= { vtssMacsecStatusSecyEntry 388 }

vtssMacsecStatusSecyRxSc5Sa3InUse OBJECT-TYPE
    SYNTAX      TruthValue
    MAX-ACCESS  read-only
    STATUS      current
    DESCRIPTION
        "If true, this SA is currently in use."
    ::= { vtssMacsecStatusSecyEntry 389 }

vtssMacsecStatusSecyRxSc5Sa3NextPN OBJECT-TYPE
    SYNTAX      VTSSUnsigned64
    MAX-ACCESS  read-only
    STATUS      current
    DESCRIPTION
        "Next packet number."
    ::= { vtssMacsecStatusSecyEntry 390 }

vtssMacsecStatusSecyRxSc5Sa3LowestPN OBJECT-TYPE
    SYNTAX      VTSSUnsigned64
    MAX-ACCESS  read-only
    STATUS      current
    DESCRIPTION
        "Lowest packet number."
    ::= { vtssMacsecStatusSecyEntry 391 }

vtssMacsecStatusSecyRxSc5Sa3CreatedTime OBJECT-TYPE
    SYNTAX      Unsigned32
    MAX-ACCESS  read-only
    STATUS      current
    DESCRIPTION
        "Time when this Rx SC was created measured in seconds since boot."
    ::= { vtssMacsecStatusSecyEntry 392 }

vtssMacsecStatusSecyRxSc5Sa3StartedTime OBJECT-TYPE
    SYNTAX      Unsigned32
    MAX-ACCESS  read-only
    STATUS      current
    DESCRIPTION
        "Time when this Rx SC was started measured in seconds since boot."
    ::= { vtssMacsecStatusSecyEntry 393 }

vtssMacsecStatusSecyRxSc5Sa3StoppedTime OBJECT-TYPE
    SYNTAX      Unsigned32
    MAX-ACCESS  read-only
    STATUS      current
    DESCRIPTION
        "Time when this Rx SC was stopped measured in seconds since boot."
    ::= { vtssMacsecStatusSecyEntry 394 }

vtssMacsecStatusSecyRxSc5Sa4Installed OBJECT-TYPE
    SYNTAX      TruthValue
    MAX-ACCESS  read-only
    STATUS      current
    DESCRIPTION
        "True if installed in H/W, false if not. If not, the remaining fields
         are invalid."
    ::= { vtssMacsecStatusSecyEntry 400 }

vtssMacsecStatusSecyRxSc5Sa4InUse OBJECT-TYPE
    SYNTAX      TruthValue
    MAX-ACCESS  read-only
    STATUS      current
    DESCRIPTION
        "If true, this SA is currently in use."
    ::= { vtssMacsecStatusSecyEntry 401 }

vtssMacsecStatusSecyRxSc5Sa4NextPN OBJECT-TYPE
    SYNTAX      VTSSUnsigned64
    MAX-ACCESS  read-only
    STATUS      current
    DESCRIPTION
        "Next packet number."
    ::= { vtssMacsecStatusSecyEntry 402 }

vtssMacsecStatusSecyRxSc5Sa4LowestPN OBJECT-TYPE
    SYNTAX      VTSSUnsigned64
    MAX-ACCESS  read-only
    STATUS      current
    DESCRIPTION
        "Lowest packet number."
    ::= { vtssMacsecStatusSecyEntry 403 }

vtssMacsecStatusSecyRxSc5Sa4CreatedTime OBJECT-TYPE
    SYNTAX      Unsigned32
    MAX-ACCESS  read-only
    STATUS      current
    DESCRIPTION
        "Time when this Rx SC was created measured in seconds since boot."
    ::= { vtssMacsecStatusSecyEntry 404 }

vtssMacsecStatusSecyRxSc5Sa4StartedTime OBJECT-TYPE
    SYNTAX      Unsigned32
    MAX-ACCESS  read-only
    STATUS      current
    DESCRIPTION
        "Time when this Rx SC was started measured in seconds since boot."
    ::= { vtssMacsecStatusSecyEntry 405 }

vtssMacsecStatusSecyRxSc5Sa4StoppedTime OBJECT-TYPE
    SYNTAX      Unsigned32
    MAX-ACCESS  read-only
    STATUS      current
    DESCRIPTION
        "Time when this Rx SC was stopped measured in seconds since boot."
    ::= { vtssMacsecStatusSecyEntry 406 }

vtssMacsecStatusSecyRxSc6Installed OBJECT-TYPE
    SYNTAX      TruthValue
    MAX-ACCESS  read-only
    STATUS      current
    DESCRIPTION
        "True if installed in H/W, false if not. If not, the remaining fields
         are invalid."
    ::= { vtssMacsecStatusSecyEntry 412 }

vtssMacsecStatusSecyRxSc6Receiving OBJECT-TYPE
    SYNTAX      TruthValue
    MAX-ACCESS  read-only
    STATUS      current
    DESCRIPTION
        "True if at least one of the SAs are in use."
    ::= { vtssMacsecStatusSecyEntry 413 }

vtssMacsecStatusSecyRxSc6ActiveSaIdx OBJECT-TYPE
    SYNTAX      Unsigned32
    MAX-ACCESS  read-only
    STATUS      current
    DESCRIPTION
        "Index of the SA within this Rx SC that is active. -1 if no SAs are
         active."
    ::= { vtssMacsecStatusSecyEntry 414 }

vtssMacsecStatusSecyRxSc6CreatedTime OBJECT-TYPE
    SYNTAX      Unsigned32
    MAX-ACCESS  read-only
    STATUS      current
    DESCRIPTION
        "Time when this Rx SC was created measured in seconds since boot."
    ::= { vtssMacsecStatusSecyEntry 415 }

vtssMacsecStatusSecyRxSc6StartedTime OBJECT-TYPE
    SYNTAX      Unsigned32
    MAX-ACCESS  read-only
    STATUS      current
    DESCRIPTION
        "Time when this Rx SC was started measured in seconds since boot."
    ::= { vtssMacsecStatusSecyEntry 416 }

vtssMacsecStatusSecyRxSc6StoppedTime OBJECT-TYPE
    SYNTAX      Unsigned32
    MAX-ACCESS  read-only
    STATUS      current
    DESCRIPTION
        "Time when this Rx SC was stopped measured in seconds since boot."
    ::= { vtssMacsecStatusSecyEntry 417 }

vtssMacsecStatusSecyRxSc6Sa1Installed OBJECT-TYPE
    SYNTAX      TruthValue
    MAX-ACCESS  read-only
    STATUS      current
    DESCRIPTION
        "True if installed in H/W, false if not. If not, the remaining fields
         are invalid."
    ::= { vtssMacsecStatusSecyEntry 430 }

vtssMacsecStatusSecyRxSc6Sa1InUse OBJECT-TYPE
    SYNTAX      TruthValue
    MAX-ACCESS  read-only
    STATUS      current
    DESCRIPTION
        "If true, this SA is currently in use."
    ::= { vtssMacsecStatusSecyEntry 431 }

vtssMacsecStatusSecyRxSc6Sa1NextPN OBJECT-TYPE
    SYNTAX      VTSSUnsigned64
    MAX-ACCESS  read-only
    STATUS      current
    DESCRIPTION
        "Next packet number."
    ::= { vtssMacsecStatusSecyEntry 432 }

vtssMacsecStatusSecyRxSc6Sa1LowestPN OBJECT-TYPE
    SYNTAX      VTSSUnsigned64
    MAX-ACCESS  read-only
    STATUS      current
    DESCRIPTION
        "Lowest packet number."
    ::= { vtssMacsecStatusSecyEntry 433 }

vtssMacsecStatusSecyRxSc6Sa1CreatedTime OBJECT-TYPE
    SYNTAX      Unsigned32
    MAX-ACCESS  read-only
    STATUS      current
    DESCRIPTION
        "Time when this Rx SC was created measured in seconds since boot."
    ::= { vtssMacsecStatusSecyEntry 434 }

vtssMacsecStatusSecyRxSc6Sa1StartedTime OBJECT-TYPE
    SYNTAX      Unsigned32
    MAX-ACCESS  read-only
    STATUS      current
    DESCRIPTION
        "Time when this Rx SC was started measured in seconds since boot."
    ::= { vtssMacsecStatusSecyEntry 435 }

vtssMacsecStatusSecyRxSc6Sa1StoppedTime OBJECT-TYPE
    SYNTAX      Unsigned32
    MAX-ACCESS  read-only
    STATUS      current
    DESCRIPTION
        "Time when this Rx SC was stopped measured in seconds since boot."
    ::= { vtssMacsecStatusSecyEntry 436 }

vtssMacsecStatusSecyRxSc6Sa2Installed OBJECT-TYPE
    SYNTAX      TruthValue
    MAX-ACCESS  read-only
    STATUS      current
    DESCRIPTION
        "True if installed in H/W, false if not. If not, the remaining fields
         are invalid."
    ::= { vtssMacsecStatusSecyEntry 442 }

vtssMacsecStatusSecyRxSc6Sa2InUse OBJECT-TYPE
    SYNTAX      TruthValue
    MAX-ACCESS  read-only
    STATUS      current
    DESCRIPTION
        "If true, this SA is currently in use."
    ::= { vtssMacsecStatusSecyEntry 443 }

vtssMacsecStatusSecyRxSc6Sa2NextPN OBJECT-TYPE
    SYNTAX      VTSSUnsigned64
    MAX-ACCESS  read-only
    STATUS      current
    DESCRIPTION
        "Next packet number."
    ::= { vtssMacsecStatusSecyEntry 444 }

vtssMacsecStatusSecyRxSc6Sa2LowestPN OBJECT-TYPE
    SYNTAX      VTSSUnsigned64
    MAX-ACCESS  read-only
    STATUS      current
    DESCRIPTION
        "Lowest packet number."
    ::= { vtssMacsecStatusSecyEntry 445 }

vtssMacsecStatusSecyRxSc6Sa2CreatedTime OBJECT-TYPE
    SYNTAX      Unsigned32
    MAX-ACCESS  read-only
    STATUS      current
    DESCRIPTION
        "Time when this Rx SC was created measured in seconds since boot."
    ::= { vtssMacsecStatusSecyEntry 446 }

vtssMacsecStatusSecyRxSc6Sa2StartedTime OBJECT-TYPE
    SYNTAX      Unsigned32
    MAX-ACCESS  read-only
    STATUS      current
    DESCRIPTION
        "Time when this Rx SC was started measured in seconds since boot."
    ::= { vtssMacsecStatusSecyEntry 447 }

vtssMacsecStatusSecyRxSc6Sa2StoppedTime OBJECT-TYPE
    SYNTAX      Unsigned32
    MAX-ACCESS  read-only
    STATUS      current
    DESCRIPTION
        "Time when this Rx SC was stopped measured in seconds since boot."
    ::= { vtssMacsecStatusSecyEntry 448 }

vtssMacsecStatusSecyRxSc6Sa3Installed OBJECT-TYPE
    SYNTAX      TruthValue
    MAX-ACCESS  read-only
    STATUS      current
    DESCRIPTION
        "True if installed in H/W, false if not. If not, the remaining fields
         are invalid."
    ::= { vtssMacsecStatusSecyEntry 454 }

vtssMacsecStatusSecyRxSc6Sa3InUse OBJECT-TYPE
    SYNTAX      TruthValue
    MAX-ACCESS  read-only
    STATUS      current
    DESCRIPTION
        "If true, this SA is currently in use."
    ::= { vtssMacsecStatusSecyEntry 455 }

vtssMacsecStatusSecyRxSc6Sa3NextPN OBJECT-TYPE
    SYNTAX      VTSSUnsigned64
    MAX-ACCESS  read-only
    STATUS      current
    DESCRIPTION
        "Next packet number."
    ::= { vtssMacsecStatusSecyEntry 456 }

vtssMacsecStatusSecyRxSc6Sa3LowestPN OBJECT-TYPE
    SYNTAX      VTSSUnsigned64
    MAX-ACCESS  read-only
    STATUS      current
    DESCRIPTION
        "Lowest packet number."
    ::= { vtssMacsecStatusSecyEntry 457 }

vtssMacsecStatusSecyRxSc6Sa3CreatedTime OBJECT-TYPE
    SYNTAX      Unsigned32
    MAX-ACCESS  read-only
    STATUS      current
    DESCRIPTION
        "Time when this Rx SC was created measured in seconds since boot."
    ::= { vtssMacsecStatusSecyEntry 458 }

vtssMacsecStatusSecyRxSc6Sa3StartedTime OBJECT-TYPE
    SYNTAX      Unsigned32
    MAX-ACCESS  read-only
    STATUS      current
    DESCRIPTION
        "Time when this Rx SC was started measured in seconds since boot."
    ::= { vtssMacsecStatusSecyEntry 459 }

vtssMacsecStatusSecyRxSc6Sa3StoppedTime OBJECT-TYPE
    SYNTAX      Unsigned32
    MAX-ACCESS  read-only
    STATUS      current
    DESCRIPTION
        "Time when this Rx SC was stopped measured in seconds since boot."
    ::= { vtssMacsecStatusSecyEntry 460 }

vtssMacsecStatusSecyRxSc6Sa4Installed OBJECT-TYPE
    SYNTAX      TruthValue
    MAX-ACCESS  read-only
    STATUS      current
    DESCRIPTION
        "True if installed in H/W, false if not. If not, the remaining fields
         are invalid."
    ::= { vtssMacsecStatusSecyEntry 466 }

vtssMacsecStatusSecyRxSc6Sa4InUse OBJECT-TYPE
    SYNTAX      TruthValue
    MAX-ACCESS  read-only
    STATUS      current
    DESCRIPTION
        "If true, this SA is currently in use."
    ::= { vtssMacsecStatusSecyEntry 467 }

vtssMacsecStatusSecyRxSc6Sa4NextPN OBJECT-TYPE
    SYNTAX      VTSSUnsigned64
    MAX-ACCESS  read-only
    STATUS      current
    DESCRIPTION
        "Next packet number."
    ::= { vtssMacsecStatusSecyEntry 468 }

vtssMacsecStatusSecyRxSc6Sa4LowestPN OBJECT-TYPE
    SYNTAX      VTSSUnsigned64
    MAX-ACCESS  read-only
    STATUS      current
    DESCRIPTION
        "Lowest packet number."
    ::= { vtssMacsecStatusSecyEntry 469 }

vtssMacsecStatusSecyRxSc6Sa4CreatedTime OBJECT-TYPE
    SYNTAX      Unsigned32
    MAX-ACCESS  read-only
    STATUS      current
    DESCRIPTION
        "Time when this Rx SC was created measured in seconds since boot."
    ::= { vtssMacsecStatusSecyEntry 470 }

vtssMacsecStatusSecyRxSc6Sa4StartedTime OBJECT-TYPE
    SYNTAX      Unsigned32
    MAX-ACCESS  read-only
    STATUS      current
    DESCRIPTION
        "Time when this Rx SC was started measured in seconds since boot."
    ::= { vtssMacsecStatusSecyEntry 471 }

vtssMacsecStatusSecyRxSc6Sa4StoppedTime OBJECT-TYPE
    SYNTAX      Unsigned32
    MAX-ACCESS  read-only
    STATUS      current
    DESCRIPTION
        "Time when this Rx SC was stopped measured in seconds since boot."
    ::= { vtssMacsecStatusSecyEntry 472 }

vtssMacsecStatusSecyRxSc7Installed OBJECT-TYPE
    SYNTAX      TruthValue
    MAX-ACCESS  read-only
    STATUS      current
    DESCRIPTION
        "True if installed in H/W, false if not. If not, the remaining fields
         are invalid."
    ::= { vtssMacsecStatusSecyEntry 478 }

vtssMacsecStatusSecyRxSc7Receiving OBJECT-TYPE
    SYNTAX      TruthValue
    MAX-ACCESS  read-only
    STATUS      current
    DESCRIPTION
        "True if at least one of the SAs are in use."
    ::= { vtssMacsecStatusSecyEntry 479 }

vtssMacsecStatusSecyRxSc7ActiveSaIdx OBJECT-TYPE
    SYNTAX      Unsigned32
    MAX-ACCESS  read-only
    STATUS      current
    DESCRIPTION
        "Index of the SA within this Rx SC that is active. -1 if no SAs are
         active."
    ::= { vtssMacsecStatusSecyEntry 480 }

vtssMacsecStatusSecyRxSc7CreatedTime OBJECT-TYPE
    SYNTAX      Unsigned32
    MAX-ACCESS  read-only
    STATUS      current
    DESCRIPTION
        "Time when this Rx SC was created measured in seconds since boot."
    ::= { vtssMacsecStatusSecyEntry 481 }

vtssMacsecStatusSecyRxSc7StartedTime OBJECT-TYPE
    SYNTAX      Unsigned32
    MAX-ACCESS  read-only
    STATUS      current
    DESCRIPTION
        "Time when this Rx SC was started measured in seconds since boot."
    ::= { vtssMacsecStatusSecyEntry 482 }

vtssMacsecStatusSecyRxSc7StoppedTime OBJECT-TYPE
    SYNTAX      Unsigned32
    MAX-ACCESS  read-only
    STATUS      current
    DESCRIPTION
        "Time when this Rx SC was stopped measured in seconds since boot."
    ::= { vtssMacsecStatusSecyEntry 483 }

vtssMacsecStatusSecyRxSc7Sa1Installed OBJECT-TYPE
    SYNTAX      TruthValue
    MAX-ACCESS  read-only
    STATUS      current
    DESCRIPTION
        "True if installed in H/W, false if not. If not, the remaining fields
         are invalid."
    ::= { vtssMacsecStatusSecyEntry 496 }

vtssMacsecStatusSecyRxSc7Sa1InUse OBJECT-TYPE
    SYNTAX      TruthValue
    MAX-ACCESS  read-only
    STATUS      current
    DESCRIPTION
        "If true, this SA is currently in use."
    ::= { vtssMacsecStatusSecyEntry 497 }

vtssMacsecStatusSecyRxSc7Sa1NextPN OBJECT-TYPE
    SYNTAX      VTSSUnsigned64
    MAX-ACCESS  read-only
    STATUS      current
    DESCRIPTION
        "Next packet number."
    ::= { vtssMacsecStatusSecyEntry 498 }

vtssMacsecStatusSecyRxSc7Sa1LowestPN OBJECT-TYPE
    SYNTAX      VTSSUnsigned64
    MAX-ACCESS  read-only
    STATUS      current
    DESCRIPTION
        "Lowest packet number."
    ::= { vtssMacsecStatusSecyEntry 499 }

vtssMacsecStatusSecyRxSc7Sa1CreatedTime OBJECT-TYPE
    SYNTAX      Unsigned32
    MAX-ACCESS  read-only
    STATUS      current
    DESCRIPTION
        "Time when this Rx SC was created measured in seconds since boot."
    ::= { vtssMacsecStatusSecyEntry 500 }

vtssMacsecStatusSecyRxSc7Sa1StartedTime OBJECT-TYPE
    SYNTAX      Unsigned32
    MAX-ACCESS  read-only
    STATUS      current
    DESCRIPTION
        "Time when this Rx SC was started measured in seconds since boot."
    ::= { vtssMacsecStatusSecyEntry 501 }

vtssMacsecStatusSecyRxSc7Sa1StoppedTime OBJECT-TYPE
    SYNTAX      Unsigned32
    MAX-ACCESS  read-only
    STATUS      current
    DESCRIPTION
        "Time when this Rx SC was stopped measured in seconds since boot."
    ::= { vtssMacsecStatusSecyEntry 502 }

vtssMacsecStatusSecyRxSc7Sa2Installed OBJECT-TYPE
    SYNTAX      TruthValue
    MAX-ACCESS  read-only
    STATUS      current
    DESCRIPTION
        "True if installed in H/W, false if not. If not, the remaining fields
         are invalid."
    ::= { vtssMacsecStatusSecyEntry 508 }

vtssMacsecStatusSecyRxSc7Sa2InUse OBJECT-TYPE
    SYNTAX      TruthValue
    MAX-ACCESS  read-only
    STATUS      current
    DESCRIPTION
        "If true, this SA is currently in use."
    ::= { vtssMacsecStatusSecyEntry 509 }

vtssMacsecStatusSecyRxSc7Sa2NextPN OBJECT-TYPE
    SYNTAX      VTSSUnsigned64
    MAX-ACCESS  read-only
    STATUS      current
    DESCRIPTION
        "Next packet number."
    ::= { vtssMacsecStatusSecyEntry 510 }

vtssMacsecStatusSecyRxSc7Sa2LowestPN OBJECT-TYPE
    SYNTAX      VTSSUnsigned64
    MAX-ACCESS  read-only
    STATUS      current
    DESCRIPTION
        "Lowest packet number."
    ::= { vtssMacsecStatusSecyEntry 511 }

vtssMacsecStatusSecyRxSc7Sa2CreatedTime OBJECT-TYPE
    SYNTAX      Unsigned32
    MAX-ACCESS  read-only
    STATUS      current
    DESCRIPTION
        "Time when this Rx SC was created measured in seconds since boot."
    ::= { vtssMacsecStatusSecyEntry 512 }

vtssMacsecStatusSecyRxSc7Sa2StartedTime OBJECT-TYPE
    SYNTAX      Unsigned32
    MAX-ACCESS  read-only
    STATUS      current
    DESCRIPTION
        "Time when this Rx SC was started measured in seconds since boot."
    ::= { vtssMacsecStatusSecyEntry 513 }

vtssMacsecStatusSecyRxSc7Sa2StoppedTime OBJECT-TYPE
    SYNTAX      Unsigned32
    MAX-ACCESS  read-only
    STATUS      current
    DESCRIPTION
        "Time when this Rx SC was stopped measured in seconds since boot."
    ::= { vtssMacsecStatusSecyEntry 514 }

vtssMacsecStatusSecyRxSc7Sa3Installed OBJECT-TYPE
    SYNTAX      TruthValue
    MAX-ACCESS  read-only
    STATUS      current
    DESCRIPTION
        "True if installed in H/W, false if not. If not, the remaining fields
         are invalid."
    ::= { vtssMacsecStatusSecyEntry 520 }

vtssMacsecStatusSecyRxSc7Sa3InUse OBJECT-TYPE
    SYNTAX      TruthValue
    MAX-ACCESS  read-only
    STATUS      current
    DESCRIPTION
        "If true, this SA is currently in use."
    ::= { vtssMacsecStatusSecyEntry 521 }

vtssMacsecStatusSecyRxSc7Sa3NextPN OBJECT-TYPE
    SYNTAX      VTSSUnsigned64
    MAX-ACCESS  read-only
    STATUS      current
    DESCRIPTION
        "Next packet number."
    ::= { vtssMacsecStatusSecyEntry 522 }

vtssMacsecStatusSecyRxSc7Sa3LowestPN OBJECT-TYPE
    SYNTAX      VTSSUnsigned64
    MAX-ACCESS  read-only
    STATUS      current
    DESCRIPTION
        "Lowest packet number."
    ::= { vtssMacsecStatusSecyEntry 523 }

vtssMacsecStatusSecyRxSc7Sa3CreatedTime OBJECT-TYPE
    SYNTAX      Unsigned32
    MAX-ACCESS  read-only
    STATUS      current
    DESCRIPTION
        "Time when this Rx SC was created measured in seconds since boot."
    ::= { vtssMacsecStatusSecyEntry 524 }

vtssMacsecStatusSecyRxSc7Sa3StartedTime OBJECT-TYPE
    SYNTAX      Unsigned32
    MAX-ACCESS  read-only
    STATUS      current
    DESCRIPTION
        "Time when this Rx SC was started measured in seconds since boot."
    ::= { vtssMacsecStatusSecyEntry 525 }

vtssMacsecStatusSecyRxSc7Sa3StoppedTime OBJECT-TYPE
    SYNTAX      Unsigned32
    MAX-ACCESS  read-only
    STATUS      current
    DESCRIPTION
        "Time when this Rx SC was stopped measured in seconds since boot."
    ::= { vtssMacsecStatusSecyEntry 526 }

vtssMacsecStatusSecyRxSc7Sa4Installed OBJECT-TYPE
    SYNTAX      TruthValue
    MAX-ACCESS  read-only
    STATUS      current
    DESCRIPTION
        "True if installed in H/W, false if not. If not, the remaining fields
         are invalid."
    ::= { vtssMacsecStatusSecyEntry 532 }

vtssMacsecStatusSecyRxSc7Sa4InUse OBJECT-TYPE
    SYNTAX      TruthValue
    MAX-ACCESS  read-only
    STATUS      current
    DESCRIPTION
        "If true, this SA is currently in use."
    ::= { vtssMacsecStatusSecyEntry 533 }

vtssMacsecStatusSecyRxSc7Sa4NextPN OBJECT-TYPE
    SYNTAX      VTSSUnsigned64
    MAX-ACCESS  read-only
    STATUS      current
    DESCRIPTION
        "Next packet number."
    ::= { vtssMacsecStatusSecyEntry 534 }

vtssMacsecStatusSecyRxSc7Sa4LowestPN OBJECT-TYPE
    SYNTAX      VTSSUnsigned64
    MAX-ACCESS  read-only
    STATUS      current
    DESCRIPTION
        "Lowest packet number."
    ::= { vtssMacsecStatusSecyEntry 535 }

vtssMacsecStatusSecyRxSc7Sa4CreatedTime OBJECT-TYPE
    SYNTAX      Unsigned32
    MAX-ACCESS  read-only
    STATUS      current
    DESCRIPTION
        "Time when this Rx SC was created measured in seconds since boot."
    ::= { vtssMacsecStatusSecyEntry 536 }

vtssMacsecStatusSecyRxSc7Sa4StartedTime OBJECT-TYPE
    SYNTAX      Unsigned32
    MAX-ACCESS  read-only
    STATUS      current
    DESCRIPTION
        "Time when this Rx SC was started measured in seconds since boot."
    ::= { vtssMacsecStatusSecyEntry 537 }

vtssMacsecStatusSecyRxSc7Sa4StoppedTime OBJECT-TYPE
    SYNTAX      Unsigned32
    MAX-ACCESS  read-only
    STATUS      current
    DESCRIPTION
        "Time when this Rx SC was stopped measured in seconds since boot."
    ::= { vtssMacsecStatusSecyEntry 538 }

vtssMacsecStatusSecyRxSc8Installed OBJECT-TYPE
    SYNTAX      TruthValue
    MAX-ACCESS  read-only
    STATUS      current
    DESCRIPTION
        "True if installed in H/W, false if not. If not, the remaining fields
         are invalid."
    ::= { vtssMacsecStatusSecyEntry 544 }

vtssMacsecStatusSecyRxSc8Receiving OBJECT-TYPE
    SYNTAX      TruthValue
    MAX-ACCESS  read-only
    STATUS      current
    DESCRIPTION
        "True if at least one of the SAs are in use."
    ::= { vtssMacsecStatusSecyEntry 545 }

vtssMacsecStatusSecyRxSc8ActiveSaIdx OBJECT-TYPE
    SYNTAX      Unsigned32
    MAX-ACCESS  read-only
    STATUS      current
    DESCRIPTION
        "Index of the SA within this Rx SC that is active. -1 if no SAs are
         active."
    ::= { vtssMacsecStatusSecyEntry 546 }

vtssMacsecStatusSecyRxSc8CreatedTime OBJECT-TYPE
    SYNTAX      Unsigned32
    MAX-ACCESS  read-only
    STATUS      current
    DESCRIPTION
        "Time when this Rx SC was created measured in seconds since boot."
    ::= { vtssMacsecStatusSecyEntry 547 }

vtssMacsecStatusSecyRxSc8StartedTime OBJECT-TYPE
    SYNTAX      Unsigned32
    MAX-ACCESS  read-only
    STATUS      current
    DESCRIPTION
        "Time when this Rx SC was started measured in seconds since boot."
    ::= { vtssMacsecStatusSecyEntry 548 }

vtssMacsecStatusSecyRxSc8StoppedTime OBJECT-TYPE
    SYNTAX      Unsigned32
    MAX-ACCESS  read-only
    STATUS      current
    DESCRIPTION
        "Time when this Rx SC was stopped measured in seconds since boot."
    ::= { vtssMacsecStatusSecyEntry 549 }

vtssMacsecStatusSecyRxSc8Sa1Installed OBJECT-TYPE
    SYNTAX      TruthValue
    MAX-ACCESS  read-only
    STATUS      current
    DESCRIPTION
        "True if installed in H/W, false if not. If not, the remaining fields
         are invalid."
    ::= { vtssMacsecStatusSecyEntry 562 }

vtssMacsecStatusSecyRxSc8Sa1InUse OBJECT-TYPE
    SYNTAX      TruthValue
    MAX-ACCESS  read-only
    STATUS      current
    DESCRIPTION
        "If true, this SA is currently in use."
    ::= { vtssMacsecStatusSecyEntry 563 }

vtssMacsecStatusSecyRxSc8Sa1NextPN OBJECT-TYPE
    SYNTAX      VTSSUnsigned64
    MAX-ACCESS  read-only
    STATUS      current
    DESCRIPTION
        "Next packet number."
    ::= { vtssMacsecStatusSecyEntry 564 }

vtssMacsecStatusSecyRxSc8Sa1LowestPN OBJECT-TYPE
    SYNTAX      VTSSUnsigned64
    MAX-ACCESS  read-only
    STATUS      current
    DESCRIPTION
        "Lowest packet number."
    ::= { vtssMacsecStatusSecyEntry 565 }

vtssMacsecStatusSecyRxSc8Sa1CreatedTime OBJECT-TYPE
    SYNTAX      Unsigned32
    MAX-ACCESS  read-only
    STATUS      current
    DESCRIPTION
        "Time when this Rx SC was created measured in seconds since boot."
    ::= { vtssMacsecStatusSecyEntry 566 }

vtssMacsecStatusSecyRxSc8Sa1StartedTime OBJECT-TYPE
    SYNTAX      Unsigned32
    MAX-ACCESS  read-only
    STATUS      current
    DESCRIPTION
        "Time when this Rx SC was started measured in seconds since boot."
    ::= { vtssMacsecStatusSecyEntry 567 }

vtssMacsecStatusSecyRxSc8Sa1StoppedTime OBJECT-TYPE
    SYNTAX      Unsigned32
    MAX-ACCESS  read-only
    STATUS      current
    DESCRIPTION
        "Time when this Rx SC was stopped measured in seconds since boot."
    ::= { vtssMacsecStatusSecyEntry 568 }

vtssMacsecStatusSecyRxSc8Sa2Installed OBJECT-TYPE
    SYNTAX      TruthValue
    MAX-ACCESS  read-only
    STATUS      current
    DESCRIPTION
        "True if installed in H/W, false if not. If not, the remaining fields
         are invalid."
    ::= { vtssMacsecStatusSecyEntry 574 }

vtssMacsecStatusSecyRxSc8Sa2InUse OBJECT-TYPE
    SYNTAX      TruthValue
    MAX-ACCESS  read-only
    STATUS      current
    DESCRIPTION
        "If true, this SA is currently in use."
    ::= { vtssMacsecStatusSecyEntry 575 }

vtssMacsecStatusSecyRxSc8Sa2NextPN OBJECT-TYPE
    SYNTAX      VTSSUnsigned64
    MAX-ACCESS  read-only
    STATUS      current
    DESCRIPTION
        "Next packet number."
    ::= { vtssMacsecStatusSecyEntry 576 }

vtssMacsecStatusSecyRxSc8Sa2LowestPN OBJECT-TYPE
    SYNTAX      VTSSUnsigned64
    MAX-ACCESS  read-only
    STATUS      current
    DESCRIPTION
        "Lowest packet number."
    ::= { vtssMacsecStatusSecyEntry 577 }

vtssMacsecStatusSecyRxSc8Sa2CreatedTime OBJECT-TYPE
    SYNTAX      Unsigned32
    MAX-ACCESS  read-only
    STATUS      current
    DESCRIPTION
        "Time when this Rx SC was created measured in seconds since boot."
    ::= { vtssMacsecStatusSecyEntry 578 }

vtssMacsecStatusSecyRxSc8Sa2StartedTime OBJECT-TYPE
    SYNTAX      Unsigned32
    MAX-ACCESS  read-only
    STATUS      current
    DESCRIPTION
        "Time when this Rx SC was started measured in seconds since boot."
    ::= { vtssMacsecStatusSecyEntry 579 }

vtssMacsecStatusSecyRxSc8Sa2StoppedTime OBJECT-TYPE
    SYNTAX      Unsigned32
    MAX-ACCESS  read-only
    STATUS      current
    DESCRIPTION
        "Time when this Rx SC was stopped measured in seconds since boot."
    ::= { vtssMacsecStatusSecyEntry 580 }

vtssMacsecStatusSecyRxSc8Sa3Installed OBJECT-TYPE
    SYNTAX      TruthValue
    MAX-ACCESS  read-only
    STATUS      current
    DESCRIPTION
        "True if installed in H/W, false if not. If not, the remaining fields
         are invalid."
    ::= { vtssMacsecStatusSecyEntry 586 }

vtssMacsecStatusSecyRxSc8Sa3InUse OBJECT-TYPE
    SYNTAX      TruthValue
    MAX-ACCESS  read-only
    STATUS      current
    DESCRIPTION
        "If true, this SA is currently in use."
    ::= { vtssMacsecStatusSecyEntry 587 }

vtssMacsecStatusSecyRxSc8Sa3NextPN OBJECT-TYPE
    SYNTAX      VTSSUnsigned64
    MAX-ACCESS  read-only
    STATUS      current
    DESCRIPTION
        "Next packet number."
    ::= { vtssMacsecStatusSecyEntry 588 }

vtssMacsecStatusSecyRxSc8Sa3LowestPN OBJECT-TYPE
    SYNTAX      VTSSUnsigned64
    MAX-ACCESS  read-only
    STATUS      current
    DESCRIPTION
        "Lowest packet number."
    ::= { vtssMacsecStatusSecyEntry 589 }

vtssMacsecStatusSecyRxSc8Sa3CreatedTime OBJECT-TYPE
    SYNTAX      Unsigned32
    MAX-ACCESS  read-only
    STATUS      current
    DESCRIPTION
        "Time when this Rx SC was created measured in seconds since boot."
    ::= { vtssMacsecStatusSecyEntry 590 }

vtssMacsecStatusSecyRxSc8Sa3StartedTime OBJECT-TYPE
    SYNTAX      Unsigned32
    MAX-ACCESS  read-only
    STATUS      current
    DESCRIPTION
        "Time when this Rx SC was started measured in seconds since boot."
    ::= { vtssMacsecStatusSecyEntry 591 }

vtssMacsecStatusSecyRxSc8Sa3StoppedTime OBJECT-TYPE
    SYNTAX      Unsigned32
    MAX-ACCESS  read-only
    STATUS      current
    DESCRIPTION
        "Time when this Rx SC was stopped measured in seconds since boot."
    ::= { vtssMacsecStatusSecyEntry 592 }

vtssMacsecStatusSecyRxSc8Sa4Installed OBJECT-TYPE
    SYNTAX      TruthValue
    MAX-ACCESS  read-only
    STATUS      current
    DESCRIPTION
        "True if installed in H/W, false if not. If not, the remaining fields
         are invalid."
    ::= { vtssMacsecStatusSecyEntry 598 }

vtssMacsecStatusSecyRxSc8Sa4InUse OBJECT-TYPE
    SYNTAX      TruthValue
    MAX-ACCESS  read-only
    STATUS      current
    DESCRIPTION
        "If true, this SA is currently in use."
    ::= { vtssMacsecStatusSecyEntry 599 }

vtssMacsecStatusSecyRxSc8Sa4NextPN OBJECT-TYPE
    SYNTAX      VTSSUnsigned64
    MAX-ACCESS  read-only
    STATUS      current
    DESCRIPTION
        "Next packet number."
    ::= { vtssMacsecStatusSecyEntry 600 }

vtssMacsecStatusSecyRxSc8Sa4LowestPN OBJECT-TYPE
    SYNTAX      VTSSUnsigned64
    MAX-ACCESS  read-only
    STATUS      current
    DESCRIPTION
        "Lowest packet number."
    ::= { vtssMacsecStatusSecyEntry 601 }

vtssMacsecStatusSecyRxSc8Sa4CreatedTime OBJECT-TYPE
    SYNTAX      Unsigned32
    MAX-ACCESS  read-only
    STATUS      current
    DESCRIPTION
        "Time when this Rx SC was created measured in seconds since boot."
    ::= { vtssMacsecStatusSecyEntry 602 }

vtssMacsecStatusSecyRxSc8Sa4StartedTime OBJECT-TYPE
    SYNTAX      Unsigned32
    MAX-ACCESS  read-only
    STATUS      current
    DESCRIPTION
        "Time when this Rx SC was started measured in seconds since boot."
    ::= { vtssMacsecStatusSecyEntry 603 }

vtssMacsecStatusSecyRxSc8Sa4StoppedTime OBJECT-TYPE
    SYNTAX      Unsigned32
    MAX-ACCESS  read-only
    STATUS      current
    DESCRIPTION
        "Time when this Rx SC was stopped measured in seconds since boot."
    ::= { vtssMacsecStatusSecyEntry 604 }

vtssMacsecControl OBJECT IDENTIFIER
    ::= { vtssMacsecMibObjects 4 }

vtssMacsecControlStatisticsClearTable OBJECT-TYPE
    SYNTAX      SEQUENCE OF VTSSMacsecControlStatisticsClearEntry
    MAX-ACCESS  not-accessible
    STATUS      current
    DESCRIPTION
        "Clear MACsec statistics."
    ::= { vtssMacsecControl 1 }

vtssMacsecControlStatisticsClearEntry OBJECT-TYPE
    SYNTAX      VTSSMacsecControlStatisticsClearEntry
    MAX-ACCESS  not-accessible
    STATUS      current
    DESCRIPTION
        "Each entry in this table represents an interface whose statistics may
         be cleared. What is cleared is controlled with the remaining parameters
         of the row."
    INDEX       { vtssMacsecControlStatisticsClearIfIndex }
    ::= { vtssMacsecControlStatisticsClearTable 1 }

VTSSMacsecControlStatisticsClearEntry ::= SEQUENCE {
    vtssMacsecControlStatisticsClearIfIndex  VTSSInterfaceIndex,
    vtssMacsecControlStatisticsClearWhat     VTSSMacsecStatisticsClearWhat,
    vtssMacsecControlStatisticsClearSecyId   Unsigned32,
    vtssMacsecControlStatisticsClearRxScIdx  Unsigned32,
    vtssMacsecControlStatisticsClearSaIdx    Unsigned32
}

vtssMacsecControlStatisticsClearIfIndex OBJECT-TYPE
    SYNTAX      VTSSInterfaceIndex
    MAX-ACCESS  accessible-for-notify
    STATUS      current
    DESCRIPTION
        "Logical port interface number."
    ::= { vtssMacsecControlStatisticsClearEntry 1 }

vtssMacsecControlStatisticsClearWhat OBJECT-TYPE
    SYNTAX      VTSSMacsecStatisticsClearWhat
    MAX-ACCESS  read-write
    STATUS      current
    DESCRIPTION
        "Controls what statistics to clear."
    ::= { vtssMacsecControlStatisticsClearEntry 2 }

vtssMacsecControlStatisticsClearSecyId OBJECT-TYPE
    SYNTAX      Unsigned32
    MAX-ACCESS  read-write
    STATUS      current
    DESCRIPTION
        "Indicates which SecY to clear statistics for. Only used if What is
         controlled, controlledTx, or controlledRx."
    ::= { vtssMacsecControlStatisticsClearEntry 3 }

vtssMacsecControlStatisticsClearRxScIdx OBJECT-TYPE
    SYNTAX      Unsigned32
    MAX-ACCESS  read-write
    STATUS      current
    DESCRIPTION
        "Indicates the index (0-based) of the Rx SC to clear statistics for.
         Only used if What is controlledRx."
    ::= { vtssMacsecControlStatisticsClearEntry 4 }

vtssMacsecControlStatisticsClearSaIdx OBJECT-TYPE
    SYNTAX      Unsigned32
    MAX-ACCESS  read-write
    STATUS      current
    DESCRIPTION
        "Indicates the index (0-based) of the SA to clear statistics for. Only
         used if What is controlledTx or controlledRx."
    ::= { vtssMacsecControlStatisticsClearEntry 5 }

vtssMacsecStatistics OBJECT IDENTIFIER
    ::= { vtssMacsecMibObjects 5 }

vtssMacsecStatisticsPortTable OBJECT-TYPE
    SYNTAX      SEQUENCE OF VTSSMacsecStatisticsPortEntry
    MAX-ACCESS  not-accessible
    STATUS      current
    DESCRIPTION
        "MACsec interface statistics table."
    ::= { vtssMacsecStatistics 1 }

vtssMacsecStatisticsPortEntry OBJECT-TYPE
    SYNTAX      VTSSMacsecStatisticsPortEntry
    MAX-ACCESS  not-accessible
    STATUS      current
    DESCRIPTION
        "Each entry in this table represents a port's statistics."
    INDEX       { vtssMacsecStatisticsPortIfIndex }
    ::= { vtssMacsecStatisticsPortTable 1 }

VTSSMacsecStatisticsPortEntry ::= SEQUENCE {
    vtssMacsecStatisticsPortIfIndex                          VTSSInterfaceIndex,
    vtssMacsecStatisticsPortUncontrolledInPackets            VTSSUnsigned64,
    vtssMacsecStatisticsPortUncontrolledInOctets             VTSSUnsigned64,
    vtssMacsecStatisticsPortUncontrolledInUnicastPackets     VTSSUnsigned64,
    vtssMacsecStatisticsPortUncontrolledInMulticastPackets   VTSSUnsigned64,
    vtssMacsecStatisticsPortUncontrolledInBroadcastPackets   VTSSUnsigned64,
    vtssMacsecStatisticsPortUncontrolledInDiscards           VTSSUnsigned64,
    vtssMacsecStatisticsPortUncontrolledInErrors             VTSSUnsigned64,
    vtssMacsecStatisticsPortUncontrolledOutPackets           VTSSUnsigned64,
    vtssMacsecStatisticsPortUncontrolledOutOctets            VTSSUnsigned64,
    vtssMacsecStatisticsPortUncontrolledOutUnicastPackets    VTSSUnsigned64,
    vtssMacsecStatisticsPortUncontrolledOutMulticastPackets  VTSSUnsigned64,
    vtssMacsecStatisticsPortUncontrolledOutBroadcastPackets  VTSSUnsigned64,
    vtssMacsecStatisticsPortUncontrolledOutErrors            VTSSUnsigned64,
    vtssMacsecStatisticsPortCommonInPackets                  VTSSUnsigned64,
    vtssMacsecStatisticsPortCommonInOctets                   VTSSUnsigned64,
    vtssMacsecStatisticsPortCommonInUnicastPackets           VTSSUnsigned64,
    vtssMacsecStatisticsPortCommonInMulticastPackets         VTSSUnsigned64,
    vtssMacsecStatisticsPortCommonInBroadcastPackets         VTSSUnsigned64,
    vtssMacsecStatisticsPortCommonInDiscards                 VTSSUnsigned64,
    vtssMacsecStatisticsPortCommonInErrors                   VTSSUnsigned64,
    vtssMacsecStatisticsPortCommonOutPackets                 VTSSUnsigned64,
    vtssMacsecStatisticsPortCommonOutOctets                  VTSSUnsigned64,
    vtssMacsecStatisticsPortCommonOutUnicastPackets          VTSSUnsigned64,
    vtssMacsecStatisticsPortCommonOutMulticastPackets        VTSSUnsigned64,
    vtssMacsecStatisticsPortCommonOutBroadcastPackets        VTSSUnsigned64,
    vtssMacsecStatisticsPortCommonOutErrors                  VTSSUnsigned64
}

vtssMacsecStatisticsPortIfIndex OBJECT-TYPE
    SYNTAX      VTSSInterfaceIndex
    MAX-ACCESS  accessible-for-notify
    STATUS      current
    DESCRIPTION
        "Logical port interface number."
    ::= { vtssMacsecStatisticsPortEntry 1 }

vtssMacsecStatisticsPortUncontrolledInPackets OBJECT-TYPE
    SYNTAX      VTSSUnsigned64
    MAX-ACCESS  read-only
    STATUS      current
    DESCRIPTION
        "Number of packets received on the uncontrolled port."
    ::= { vtssMacsecStatisticsPortEntry 2 }

vtssMacsecStatisticsPortUncontrolledInOctets OBJECT-TYPE
    SYNTAX      VTSSUnsigned64
    MAX-ACCESS  read-only
    STATUS      current
    DESCRIPTION
        "Number of octets received on the uncontrolled port."
    ::= { vtssMacsecStatisticsPortEntry 3 }

vtssMacsecStatisticsPortUncontrolledInUnicastPackets OBJECT-TYPE
    SYNTAX      VTSSUnsigned64
    MAX-ACCESS  read-only
    STATUS      current
    DESCRIPTION
        "Number of unicast packets received on the uncontrolled port."
    ::= { vtssMacsecStatisticsPortEntry 4 }

vtssMacsecStatisticsPortUncontrolledInMulticastPackets OBJECT-TYPE
    SYNTAX      VTSSUnsigned64
    MAX-ACCESS  read-only
    STATUS      current
    DESCRIPTION
        "Number of multicast packets received on the uncontrolled port."
    ::= { vtssMacsecStatisticsPortEntry 5 }

vtssMacsecStatisticsPortUncontrolledInBroadcastPackets OBJECT-TYPE
    SYNTAX      VTSSUnsigned64
    MAX-ACCESS  read-only
    STATUS      current
    DESCRIPTION
        "Number of broadcast packets received on the uncontrolled port."
    ::= { vtssMacsecStatisticsPortEntry 6 }

vtssMacsecStatisticsPortUncontrolledInDiscards OBJECT-TYPE
    SYNTAX      VTSSUnsigned64
    MAX-ACCESS  read-only
    STATUS      current
    DESCRIPTION
        "Number of discarded packets received on the uncontrolled port."
    ::= { vtssMacsecStatisticsPortEntry 7 }

vtssMacsecStatisticsPortUncontrolledInErrors OBJECT-TYPE
    SYNTAX      VTSSUnsigned64
    MAX-ACCESS  read-only
    STATUS      current
    DESCRIPTION
        "Number of erroneous packets received on the uncontrolled port."
    ::= { vtssMacsecStatisticsPortEntry 8 }

vtssMacsecStatisticsPortUncontrolledOutPackets OBJECT-TYPE
    SYNTAX      VTSSUnsigned64
    MAX-ACCESS  read-only
    STATUS      current
    DESCRIPTION
        "Number of packets transmitted on the uncontrolled port."
    ::= { vtssMacsecStatisticsPortEntry 9 }

vtssMacsecStatisticsPortUncontrolledOutOctets OBJECT-TYPE
    SYNTAX      VTSSUnsigned64
    MAX-ACCESS  read-only
    STATUS      current
    DESCRIPTION
        "Number of octets transmitted on the uncontrolled port."
    ::= { vtssMacsecStatisticsPortEntry 10 }

vtssMacsecStatisticsPortUncontrolledOutUnicastPackets OBJECT-TYPE
    SYNTAX      VTSSUnsigned64
    MAX-ACCESS  read-only
    STATUS      current
    DESCRIPTION
        "Number of unicast packets transmitted on the uncontrolled port."
    ::= { vtssMacsecStatisticsPortEntry 11 }

vtssMacsecStatisticsPortUncontrolledOutMulticastPackets OBJECT-TYPE
    SYNTAX      VTSSUnsigned64
    MAX-ACCESS  read-only
    STATUS      current
    DESCRIPTION
        "Number of multicast packets transmitted on the uncontrolled port."
    ::= { vtssMacsecStatisticsPortEntry 12 }

vtssMacsecStatisticsPortUncontrolledOutBroadcastPackets OBJECT-TYPE
    SYNTAX      VTSSUnsigned64
    MAX-ACCESS  read-only
    STATUS      current
    DESCRIPTION
        "Number of broadcast packets transmitted on the uncontrolled port."
    ::= { vtssMacsecStatisticsPortEntry 13 }

vtssMacsecStatisticsPortUncontrolledOutErrors OBJECT-TYPE
    SYNTAX      VTSSUnsigned64
    MAX-ACCESS  read-only
    STATUS      current
    DESCRIPTION
        "Number of erroneous packets transmitted on the uncontrolled port."
    ::= { vtssMacsecStatisticsPortEntry 14 }

vtssMacsecStatisticsPortCommonInPackets OBJECT-TYPE
    SYNTAX      VTSSUnsigned64
    MAX-ACCESS  read-only
    STATUS      current
    DESCRIPTION
        "Number of packets received on the common port."
    ::= { vtssMacsecStatisticsPortEntry 25 }

vtssMacsecStatisticsPortCommonInOctets OBJECT-TYPE
    SYNTAX      VTSSUnsigned64
    MAX-ACCESS  read-only
    STATUS      current
    DESCRIPTION
        "Number of octets received on the common port."
    ::= { vtssMacsecStatisticsPortEntry 26 }

vtssMacsecStatisticsPortCommonInUnicastPackets OBJECT-TYPE
    SYNTAX      VTSSUnsigned64
    MAX-ACCESS  read-only
    STATUS      current
    DESCRIPTION
        "Number of unicast packets received on the common port."
    ::= { vtssMacsecStatisticsPortEntry 27 }

vtssMacsecStatisticsPortCommonInMulticastPackets OBJECT-TYPE
    SYNTAX      VTSSUnsigned64
    MAX-ACCESS  read-only
    STATUS      current
    DESCRIPTION
        "Number of multicast packets received on the common port."
    ::= { vtssMacsecStatisticsPortEntry 28 }

vtssMacsecStatisticsPortCommonInBroadcastPackets OBJECT-TYPE
    SYNTAX      VTSSUnsigned64
    MAX-ACCESS  read-only
    STATUS      current
    DESCRIPTION
        "Number of broadcast packets received on the common port."
    ::= { vtssMacsecStatisticsPortEntry 29 }

vtssMacsecStatisticsPortCommonInDiscards OBJECT-TYPE
    SYNTAX      VTSSUnsigned64
    MAX-ACCESS  read-only
    STATUS      current
    DESCRIPTION
        "Number of discarded packets received on the common port."
    ::= { vtssMacsecStatisticsPortEntry 30 }

vtssMacsecStatisticsPortCommonInErrors OBJECT-TYPE
    SYNTAX      VTSSUnsigned64
    MAX-ACCESS  read-only
    STATUS      current
    DESCRIPTION
        "Number of erroneous packets received on the common port."
    ::= { vtssMacsecStatisticsPortEntry 31 }

vtssMacsecStatisticsPortCommonOutPackets OBJECT-TYPE
    SYNTAX      VTSSUnsigned64
    MAX-ACCESS  read-only
    STATUS      current
    DESCRIPTION
        "Number of packets transmitted on the common port."
    ::= { vtssMacsecStatisticsPortEntry 32 }

vtssMacsecStatisticsPortCommonOutOctets OBJECT-TYPE
    SYNTAX      VTSSUnsigned64
    MAX-ACCESS  read-only
    STATUS      current
    DESCRIPTION
        "Number of octets transmitted on the common port."
    ::= { vtssMacsecStatisticsPortEntry 33 }

vtssMacsecStatisticsPortCommonOutUnicastPackets OBJECT-TYPE
    SYNTAX      VTSSUnsigned64
    MAX-ACCESS  read-only
    STATUS      current
    DESCRIPTION
        "Number of unicast packets transmitted on the common port."
    ::= { vtssMacsecStatisticsPortEntry 34 }

vtssMacsecStatisticsPortCommonOutMulticastPackets OBJECT-TYPE
    SYNTAX      VTSSUnsigned64
    MAX-ACCESS  read-only
    STATUS      current
    DESCRIPTION
        "Number of multicast packets transmitted on the common port."
    ::= { vtssMacsecStatisticsPortEntry 35 }

vtssMacsecStatisticsPortCommonOutBroadcastPackets OBJECT-TYPE
    SYNTAX      VTSSUnsigned64
    MAX-ACCESS  read-only
    STATUS      current
    DESCRIPTION
        "Number of broadcast packets transmitted on the common port."
    ::= { vtssMacsecStatisticsPortEntry 36 }

vtssMacsecStatisticsPortCommonOutErrors OBJECT-TYPE
    SYNTAX      VTSSUnsigned64
    MAX-ACCESS  read-only
    STATUS      current
    DESCRIPTION
        "Number of erroneous packets transmitted on the common port."
    ::= { vtssMacsecStatisticsPortEntry 37 }

vtssMacsecStatisticsSecyTable OBJECT-TYPE
    SYNTAX      SEQUENCE OF VTSSMacsecStatisticsSecyEntry
    MAX-ACCESS  not-accessible
    STATUS      current
    DESCRIPTION
        "MACsec SecY statistics table."
    ::= { vtssMacsecStatistics 2 }

vtssMacsecStatisticsSecyEntry OBJECT-TYPE
    SYNTAX      VTSSMacsecStatisticsSecyEntry
    MAX-ACCESS  not-accessible
    STATUS      current
    DESCRIPTION
        "Each entry in this table represents a SecY's statistics."
    INDEX       { vtssMacsecStatisticsSecyIfIndex,
                  vtssMacsecStatisticsSecySecyId }
    ::= { vtssMacsecStatisticsSecyTable 1 }

VTSSMacsecStatisticsSecyEntry ::= SEQUENCE {
    vtssMacsecStatisticsSecyIfIndex                        VTSSInterfaceIndex,
    vtssMacsecStatisticsSecySecyId                         Unsigned32,
    vtssMacsecStatisticsSecyControlledInPackets            VTSSUnsigned64,
    vtssMacsecStatisticsSecyControlledInOctets             VTSSUnsigned64,
    vtssMacsecStatisticsSecyControlledInUnicastPackets     VTSSUnsigned64,
    vtssMacsecStatisticsSecyControlledInMulticastPackets   VTSSUnsigned64,
    vtssMacsecStatisticsSecyControlledInBroadcastPackets   VTSSUnsigned64,
    vtssMacsecStatisticsSecyControlledInDiscards           VTSSUnsigned64,
    vtssMacsecStatisticsSecyControlledInErrors             VTSSUnsigned64,
    vtssMacsecStatisticsSecyControlledOutPackets           VTSSUnsigned64,
    vtssMacsecStatisticsSecyControlledOutOctets            VTSSUnsigned64,
    vtssMacsecStatisticsSecyControlledOutUnicastPackets    VTSSUnsigned64,
    vtssMacsecStatisticsSecyControlledOutMulticastPackets  VTSSUnsigned64,
    vtssMacsecStatisticsSecyControlledOutBroadcastPackets  VTSSUnsigned64,
    vtssMacsecStatisticsSecyControlledOutErrors            VTSSUnsigned64,
    vtssMacsecStatisticsSecySecyInPacketsUntagged          VTSSUnsigned64,
    vtssMacsecStatisticsSecySecyInPacketsNoTag             VTSSUnsigned64,
    vtssMacsecStatisticsSecySecyInPacketsBadTag            VTSSUnsigned64,
    vtssMacsecStatisticsSecySecyInPacketsUnknownSci        VTSSUnsigned64,
    vtssMacsecStatisticsSecySecyInPacketsNoSci             VTSSUnsigned64,
    vtssMacsecStatisticsSecySecyInPacketsOverrun           VTSSUnsigned64,
    vtssMacsecStatisticsSecySecyInOctetsValidated          VTSSUnsigned64,
    vtssMacsecStatisticsSecySecyInOctetsDecrypted          VTSSUnsigned64,
    vtssMacsecStatisticsSecySecyOutPacketsUntagged         VTSSUnsigned64,
    vtssMacsecStatisticsSecySecyOutPacketsTooLong          VTSSUnsigned64,
    vtssMacsecStatisticsSecySecyOutOctetsProtected         VTSSUnsigned64,
    vtssMacsecStatisticsSecySecyOutOctetsEncrypted         VTSSUnsigned64,
    vtssMacsecStatisticsSecyTxScOutPacketsProtected        VTSSUnsigned64,
    vtssMacsecStatisticsSecyTxScOutPacketsEncrypted        VTSSUnsigned64,
    vtssMacsecStatisticsSecyTxScOutOctetsProtected         VTSSUnsigned64,
    vtssMacsecStatisticsSecyTxScOutOctetsEncrypted         VTSSUnsigned64,
    vtssMacsecStatisticsSecyTxSa1OutPacketsProtected       VTSSUnsigned64,
    vtssMacsecStatisticsSecyTxSa1OutPacketsEncrypted       VTSSUnsigned64,
    vtssMacsecStatisticsSecyTxSa2OutPacketsProtected       VTSSUnsigned64,
    vtssMacsecStatisticsSecyTxSa2OutPacketsEncrypted       VTSSUnsigned64,
    vtssMacsecStatisticsSecyTxSa3OutPacketsProtected       VTSSUnsigned64,
    vtssMacsecStatisticsSecyTxSa3OutPacketsEncrypted       VTSSUnsigned64,
    vtssMacsecStatisticsSecyTxSa4OutPacketsProtected       VTSSUnsigned64,
    vtssMacsecStatisticsSecyTxSa4OutPacketsEncrypted       VTSSUnsigned64,
    vtssMacsecStatisticsSecyRxSc1InPacketsUnchecked        VTSSUnsigned64,
    vtssMacsecStatisticsSecyRxSc1InPacketsDelayed          VTSSUnsigned64,
    vtssMacsecStatisticsSecyRxSc1InPacketsLate             VTSSUnsigned64,
    vtssMacsecStatisticsSecyRxSc1InPacketsOk               VTSSUnsigned64,
    vtssMacsecStatisticsSecyRxSc1InPacketsInvalid          VTSSUnsigned64,
    vtssMacsecStatisticsSecyRxSc1InPacketsNotValid         VTSSUnsigned64,
    vtssMacsecStatisticsSecyRxSc1InPacketsNotUsingSa       VTSSUnsigned64,
    vtssMacsecStatisticsSecyRxSc1InPacketsUnusedSa         VTSSUnsigned64,
    vtssMacsecStatisticsSecyRxSc1InOctetsValidated         VTSSUnsigned64,
    vtssMacsecStatisticsSecyRxSc1InOctetsDecrypted         VTSSUnsigned64,
    vtssMacsecStatisticsSecyRxSc1Sa1InPacketsOk            VTSSUnsigned64,
    vtssMacsecStatisticsSecyRxSc1Sa1InPacketsInvalid       VTSSUnsigned64,
    vtssMacsecStatisticsSecyRxSc1Sa1InPacketsNotValid      VTSSUnsigned64,
    vtssMacsecStatisticsSecyRxSc1Sa1InPacketsNotUsingSa    VTSSUnsigned64,
    vtssMacsecStatisticsSecyRxSc1Sa1InPacketsUnusedSa      VTSSUnsigned64,
    vtssMacsecStatisticsSecyRxSc1Sa1InPacketsUnchecked     VTSSUnsigned64,
    vtssMacsecStatisticsSecyRxSc1Sa1InPacketsDelayed       VTSSUnsigned64,
    vtssMacsecStatisticsSecyRxSc1Sa1InPacketsLate          VTSSUnsigned64,
    vtssMacsecStatisticsSecyRxSc1Sa2InPacketsOk            VTSSUnsigned64,
    vtssMacsecStatisticsSecyRxSc1Sa2InPacketsInvalid       VTSSUnsigned64,
    vtssMacsecStatisticsSecyRxSc1Sa2InPacketsNotValid      VTSSUnsigned64,
    vtssMacsecStatisticsSecyRxSc1Sa2InPacketsNotUsingSa    VTSSUnsigned64,
    vtssMacsecStatisticsSecyRxSc1Sa2InPacketsUnusedSa      VTSSUnsigned64,
    vtssMacsecStatisticsSecyRxSc1Sa2InPacketsUnchecked     VTSSUnsigned64,
    vtssMacsecStatisticsSecyRxSc1Sa2InPacketsDelayed       VTSSUnsigned64,
    vtssMacsecStatisticsSecyRxSc1Sa2InPacketsLate          VTSSUnsigned64,
    vtssMacsecStatisticsSecyRxSc1Sa3InPacketsOk            VTSSUnsigned64,
    vtssMacsecStatisticsSecyRxSc1Sa3InPacketsInvalid       VTSSUnsigned64,
    vtssMacsecStatisticsSecyRxSc1Sa3InPacketsNotValid      VTSSUnsigned64,
    vtssMacsecStatisticsSecyRxSc1Sa3InPacketsNotUsingSa    VTSSUnsigned64,
    vtssMacsecStatisticsSecyRxSc1Sa3InPacketsUnusedSa      VTSSUnsigned64,
    vtssMacsecStatisticsSecyRxSc1Sa3InPacketsUnchecked     VTSSUnsigned64,
    vtssMacsecStatisticsSecyRxSc1Sa3InPacketsDelayed       VTSSUnsigned64,
    vtssMacsecStatisticsSecyRxSc1Sa3InPacketsLate          VTSSUnsigned64,
    vtssMacsecStatisticsSecyRxSc1Sa4InPacketsOk            VTSSUnsigned64,
    vtssMacsecStatisticsSecyRxSc1Sa4InPacketsInvalid       VTSSUnsigned64,
    vtssMacsecStatisticsSecyRxSc1Sa4InPacketsNotValid      VTSSUnsigned64,
    vtssMacsecStatisticsSecyRxSc1Sa4InPacketsNotUsingSa    VTSSUnsigned64,
    vtssMacsecStatisticsSecyRxSc1Sa4InPacketsUnusedSa      VTSSUnsigned64,
    vtssMacsecStatisticsSecyRxSc1Sa4InPacketsUnchecked     VTSSUnsigned64,
    vtssMacsecStatisticsSecyRxSc1Sa4InPacketsDelayed       VTSSUnsigned64,
    vtssMacsecStatisticsSecyRxSc1Sa4InPacketsLate          VTSSUnsigned64,
    vtssMacsecStatisticsSecyRxSc2InPacketsUnchecked        VTSSUnsigned64,
    vtssMacsecStatisticsSecyRxSc2InPacketsDelayed          VTSSUnsigned64,
    vtssMacsecStatisticsSecyRxSc2InPacketsLate             VTSSUnsigned64,
    vtssMacsecStatisticsSecyRxSc2InPacketsOk               VTSSUnsigned64,
    vtssMacsecStatisticsSecyRxSc2InPacketsInvalid          VTSSUnsigned64,
    vtssMacsecStatisticsSecyRxSc2InPacketsNotValid         VTSSUnsigned64,
    vtssMacsecStatisticsSecyRxSc2InPacketsNotUsingSa       VTSSUnsigned64,
    vtssMacsecStatisticsSecyRxSc2InPacketsUnusedSa         VTSSUnsigned64,
    vtssMacsecStatisticsSecyRxSc2InOctetsValidated         VTSSUnsigned64,
    vtssMacsecStatisticsSecyRxSc2InOctetsDecrypted         VTSSUnsigned64,
    vtssMacsecStatisticsSecyRxSc2Sa1InPacketsOk            VTSSUnsigned64,
    vtssMacsecStatisticsSecyRxSc2Sa1InPacketsInvalid       VTSSUnsigned64,
    vtssMacsecStatisticsSecyRxSc2Sa1InPacketsNotValid      VTSSUnsigned64,
    vtssMacsecStatisticsSecyRxSc2Sa1InPacketsNotUsingSa    VTSSUnsigned64,
    vtssMacsecStatisticsSecyRxSc2Sa1InPacketsUnusedSa      VTSSUnsigned64,
    vtssMacsecStatisticsSecyRxSc2Sa1InPacketsUnchecked     VTSSUnsigned64,
    vtssMacsecStatisticsSecyRxSc2Sa1InPacketsDelayed       VTSSUnsigned64,
    vtssMacsecStatisticsSecyRxSc2Sa1InPacketsLate          VTSSUnsigned64,
    vtssMacsecStatisticsSecyRxSc2Sa2InPacketsOk            VTSSUnsigned64,
    vtssMacsecStatisticsSecyRxSc2Sa2InPacketsInvalid       VTSSUnsigned64,
    vtssMacsecStatisticsSecyRxSc2Sa2InPacketsNotValid      VTSSUnsigned64,
    vtssMacsecStatisticsSecyRxSc2Sa2InPacketsNotUsingSa    VTSSUnsigned64,
    vtssMacsecStatisticsSecyRxSc2Sa2InPacketsUnusedSa      VTSSUnsigned64,
    vtssMacsecStatisticsSecyRxSc2Sa2InPacketsUnchecked     VTSSUnsigned64,
    vtssMacsecStatisticsSecyRxSc2Sa2InPacketsDelayed       VTSSUnsigned64,
    vtssMacsecStatisticsSecyRxSc2Sa2InPacketsLate          VTSSUnsigned64,
    vtssMacsecStatisticsSecyRxSc2Sa3InPacketsOk            VTSSUnsigned64,
    vtssMacsecStatisticsSecyRxSc2Sa3InPacketsInvalid       VTSSUnsigned64,
    vtssMacsecStatisticsSecyRxSc2Sa3InPacketsNotValid      VTSSUnsigned64,
    vtssMacsecStatisticsSecyRxSc2Sa3InPacketsNotUsingSa    VTSSUnsigned64,
    vtssMacsecStatisticsSecyRxSc2Sa3InPacketsUnusedSa      VTSSUnsigned64,
    vtssMacsecStatisticsSecyRxSc2Sa3InPacketsUnchecked     VTSSUnsigned64,
    vtssMacsecStatisticsSecyRxSc2Sa3InPacketsDelayed       VTSSUnsigned64,
    vtssMacsecStatisticsSecyRxSc2Sa3InPacketsLate          VTSSUnsigned64,
    vtssMacsecStatisticsSecyRxSc2Sa4InPacketsOk            VTSSUnsigned64,
    vtssMacsecStatisticsSecyRxSc2Sa4InPacketsInvalid       VTSSUnsigned64,
    vtssMacsecStatisticsSecyRxSc2Sa4InPacketsNotValid      VTSSUnsigned64,
    vtssMacsecStatisticsSecyRxSc2Sa4InPacketsNotUsingSa    VTSSUnsigned64,
    vtssMacsecStatisticsSecyRxSc2Sa4InPacketsUnusedSa      VTSSUnsigned64,
    vtssMacsecStatisticsSecyRxSc2Sa4InPacketsUnchecked     VTSSUnsigned64,
    vtssMacsecStatisticsSecyRxSc2Sa4InPacketsDelayed       VTSSUnsigned64,
    vtssMacsecStatisticsSecyRxSc2Sa4InPacketsLate          VTSSUnsigned64,
    vtssMacsecStatisticsSecyRxSc3InPacketsUnchecked        VTSSUnsigned64,
    vtssMacsecStatisticsSecyRxSc3InPacketsDelayed          VTSSUnsigned64,
    vtssMacsecStatisticsSecyRxSc3InPacketsLate             VTSSUnsigned64,
    vtssMacsecStatisticsSecyRxSc3InPacketsOk               VTSSUnsigned64,
    vtssMacsecStatisticsSecyRxSc3InPacketsInvalid          VTSSUnsigned64,
    vtssMacsecStatisticsSecyRxSc3InPacketsNotValid         VTSSUnsigned64,
    vtssMacsecStatisticsSecyRxSc3InPacketsNotUsingSa       VTSSUnsigned64,
    vtssMacsecStatisticsSecyRxSc3InPacketsUnusedSa         VTSSUnsigned64,
    vtssMacsecStatisticsSecyRxSc3InOctetsValidated         VTSSUnsigned64,
    vtssMacsecStatisticsSecyRxSc3InOctetsDecrypted         VTSSUnsigned64,
    vtssMacsecStatisticsSecyRxSc3Sa1InPacketsOk            VTSSUnsigned64,
    vtssMacsecStatisticsSecyRxSc3Sa1InPacketsInvalid       VTSSUnsigned64,
    vtssMacsecStatisticsSecyRxSc3Sa1InPacketsNotValid      VTSSUnsigned64,
    vtssMacsecStatisticsSecyRxSc3Sa1InPacketsNotUsingSa    VTSSUnsigned64,
    vtssMacsecStatisticsSecyRxSc3Sa1InPacketsUnusedSa      VTSSUnsigned64,
    vtssMacsecStatisticsSecyRxSc3Sa1InPacketsUnchecked     VTSSUnsigned64,
    vtssMacsecStatisticsSecyRxSc3Sa1InPacketsDelayed       VTSSUnsigned64,
    vtssMacsecStatisticsSecyRxSc3Sa1InPacketsLate          VTSSUnsigned64,
    vtssMacsecStatisticsSecyRxSc3Sa2InPacketsOk            VTSSUnsigned64,
    vtssMacsecStatisticsSecyRxSc3Sa2InPacketsInvalid       VTSSUnsigned64,
    vtssMacsecStatisticsSecyRxSc3Sa2InPacketsNotValid      VTSSUnsigned64,
    vtssMacsecStatisticsSecyRxSc3Sa2InPacketsNotUsingSa    VTSSUnsigned64,
    vtssMacsecStatisticsSecyRxSc3Sa2InPacketsUnusedSa      VTSSUnsigned64,
    vtssMacsecStatisticsSecyRxSc3Sa2InPacketsUnchecked     VTSSUnsigned64,
    vtssMacsecStatisticsSecyRxSc3Sa2InPacketsDelayed       VTSSUnsigned64,
    vtssMacsecStatisticsSecyRxSc3Sa2InPacketsLate          VTSSUnsigned64,
    vtssMacsecStatisticsSecyRxSc3Sa3InPacketsOk            VTSSUnsigned64,
    vtssMacsecStatisticsSecyRxSc3Sa3InPacketsInvalid       VTSSUnsigned64,
    vtssMacsecStatisticsSecyRxSc3Sa3InPacketsNotValid      VTSSUnsigned64,
    vtssMacsecStatisticsSecyRxSc3Sa3InPacketsNotUsingSa    VTSSUnsigned64,
    vtssMacsecStatisticsSecyRxSc3Sa3InPacketsUnusedSa      VTSSUnsigned64,
    vtssMacsecStatisticsSecyRxSc3Sa3InPacketsUnchecked     VTSSUnsigned64,
    vtssMacsecStatisticsSecyRxSc3Sa3InPacketsDelayed       VTSSUnsigned64,
    vtssMacsecStatisticsSecyRxSc3Sa3InPacketsLate          VTSSUnsigned64,
    vtssMacsecStatisticsSecyRxSc3Sa4InPacketsOk            VTSSUnsigned64,
    vtssMacsecStatisticsSecyRxSc3Sa4InPacketsInvalid       VTSSUnsigned64,
    vtssMacsecStatisticsSecyRxSc3Sa4InPacketsNotValid      VTSSUnsigned64,
    vtssMacsecStatisticsSecyRxSc3Sa4InPacketsNotUsingSa    VTSSUnsigned64,
    vtssMacsecStatisticsSecyRxSc3Sa4InPacketsUnusedSa      VTSSUnsigned64,
    vtssMacsecStatisticsSecyRxSc3Sa4InPacketsUnchecked     VTSSUnsigned64,
    vtssMacsecStatisticsSecyRxSc3Sa4InPacketsDelayed       VTSSUnsigned64,
    vtssMacsecStatisticsSecyRxSc3Sa4InPacketsLate          VTSSUnsigned64,
    vtssMacsecStatisticsSecyRxSc4InPacketsUnchecked        VTSSUnsigned64,
    vtssMacsecStatisticsSecyRxSc4InPacketsDelayed          VTSSUnsigned64,
    vtssMacsecStatisticsSecyRxSc4InPacketsLate             VTSSUnsigned64,
    vtssMacsecStatisticsSecyRxSc4InPacketsOk               VTSSUnsigned64,
    vtssMacsecStatisticsSecyRxSc4InPacketsInvalid          VTSSUnsigned64,
    vtssMacsecStatisticsSecyRxSc4InPacketsNotValid         VTSSUnsigned64,
    vtssMacsecStatisticsSecyRxSc4InPacketsNotUsingSa       VTSSUnsigned64,
    vtssMacsecStatisticsSecyRxSc4InPacketsUnusedSa         VTSSUnsigned64,
    vtssMacsecStatisticsSecyRxSc4InOctetsValidated         VTSSUnsigned64,
    vtssMacsecStatisticsSecyRxSc4InOctetsDecrypted         VTSSUnsigned64,
    vtssMacsecStatisticsSecyRxSc4Sa1InPacketsOk            VTSSUnsigned64,
    vtssMacsecStatisticsSecyRxSc4Sa1InPacketsInvalid       VTSSUnsigned64,
    vtssMacsecStatisticsSecyRxSc4Sa1InPacketsNotValid      VTSSUnsigned64,
    vtssMacsecStatisticsSecyRxSc4Sa1InPacketsNotUsingSa    VTSSUnsigned64,
    vtssMacsecStatisticsSecyRxSc4Sa1InPacketsUnusedSa      VTSSUnsigned64,
    vtssMacsecStatisticsSecyRxSc4Sa1InPacketsUnchecked     VTSSUnsigned64,
    vtssMacsecStatisticsSecyRxSc4Sa1InPacketsDelayed       VTSSUnsigned64,
    vtssMacsecStatisticsSecyRxSc4Sa1InPacketsLate          VTSSUnsigned64,
    vtssMacsecStatisticsSecyRxSc4Sa2InPacketsOk            VTSSUnsigned64,
    vtssMacsecStatisticsSecyRxSc4Sa2InPacketsInvalid       VTSSUnsigned64,
    vtssMacsecStatisticsSecyRxSc4Sa2InPacketsNotValid      VTSSUnsigned64,
    vtssMacsecStatisticsSecyRxSc4Sa2InPacketsNotUsingSa    VTSSUnsigned64,
    vtssMacsecStatisticsSecyRxSc4Sa2InPacketsUnusedSa      VTSSUnsigned64,
    vtssMacsecStatisticsSecyRxSc4Sa2InPacketsUnchecked     VTSSUnsigned64,
    vtssMacsecStatisticsSecyRxSc4Sa2InPacketsDelayed       VTSSUnsigned64,
    vtssMacsecStatisticsSecyRxSc4Sa2InPacketsLate          VTSSUnsigned64,
    vtssMacsecStatisticsSecyRxSc4Sa3InPacketsOk            VTSSUnsigned64,
    vtssMacsecStatisticsSecyRxSc4Sa3InPacketsInvalid       VTSSUnsigned64,
    vtssMacsecStatisticsSecyRxSc4Sa3InPacketsNotValid      VTSSUnsigned64,
    vtssMacsecStatisticsSecyRxSc4Sa3InPacketsNotUsingSa    VTSSUnsigned64,
    vtssMacsecStatisticsSecyRxSc4Sa3InPacketsUnusedSa      VTSSUnsigned64,
    vtssMacsecStatisticsSecyRxSc4Sa3InPacketsUnchecked     VTSSUnsigned64,
    vtssMacsecStatisticsSecyRxSc4Sa3InPacketsDelayed       VTSSUnsigned64,
    vtssMacsecStatisticsSecyRxSc4Sa3InPacketsLate          VTSSUnsigned64,
    vtssMacsecStatisticsSecyRxSc4Sa4InPacketsOk            VTSSUnsigned64,
    vtssMacsecStatisticsSecyRxSc4Sa4InPacketsInvalid       VTSSUnsigned64,
    vtssMacsecStatisticsSecyRxSc4Sa4InPacketsNotValid      VTSSUnsigned64,
    vtssMacsecStatisticsSecyRxSc4Sa4InPacketsNotUsingSa    VTSSUnsigned64,
    vtssMacsecStatisticsSecyRxSc4Sa4InPacketsUnusedSa      VTSSUnsigned64,
    vtssMacsecStatisticsSecyRxSc4Sa4InPacketsUnchecked     VTSSUnsigned64,
    vtssMacsecStatisticsSecyRxSc4Sa4InPacketsDelayed       VTSSUnsigned64,
    vtssMacsecStatisticsSecyRxSc4Sa4InPacketsLate          VTSSUnsigned64,
    vtssMacsecStatisticsSecyRxSc5InPacketsUnchecked        VTSSUnsigned64,
    vtssMacsecStatisticsSecyRxSc5InPacketsDelayed          VTSSUnsigned64,
    vtssMacsecStatisticsSecyRxSc5InPacketsLate             VTSSUnsigned64,
    vtssMacsecStatisticsSecyRxSc5InPacketsOk               VTSSUnsigned64,
    vtssMacsecStatisticsSecyRxSc5InPacketsInvalid          VTSSUnsigned64,
    vtssMacsecStatisticsSecyRxSc5InPacketsNotValid         VTSSUnsigned64,
    vtssMacsecStatisticsSecyRxSc5InPacketsNotUsingSa       VTSSUnsigned64,
    vtssMacsecStatisticsSecyRxSc5InPacketsUnusedSa         VTSSUnsigned64,
    vtssMacsecStatisticsSecyRxSc5InOctetsValidated         VTSSUnsigned64,
    vtssMacsecStatisticsSecyRxSc5InOctetsDecrypted         VTSSUnsigned64,
    vtssMacsecStatisticsSecyRxSc5Sa1InPacketsOk            VTSSUnsigned64,
    vtssMacsecStatisticsSecyRxSc5Sa1InPacketsInvalid       VTSSUnsigned64,
    vtssMacsecStatisticsSecyRxSc5Sa1InPacketsNotValid      VTSSUnsigned64,
    vtssMacsecStatisticsSecyRxSc5Sa1InPacketsNotUsingSa    VTSSUnsigned64,
    vtssMacsecStatisticsSecyRxSc5Sa1InPacketsUnusedSa      VTSSUnsigned64,
    vtssMacsecStatisticsSecyRxSc5Sa1InPacketsUnchecked     VTSSUnsigned64,
    vtssMacsecStatisticsSecyRxSc5Sa1InPacketsDelayed       VTSSUnsigned64,
    vtssMacsecStatisticsSecyRxSc5Sa1InPacketsLate          VTSSUnsigned64,
    vtssMacsecStatisticsSecyRxSc5Sa2InPacketsOk            VTSSUnsigned64,
    vtssMacsecStatisticsSecyRxSc5Sa2InPacketsInvalid       VTSSUnsigned64,
    vtssMacsecStatisticsSecyRxSc5Sa2InPacketsNotValid      VTSSUnsigned64,
    vtssMacsecStatisticsSecyRxSc5Sa2InPacketsNotUsingSa    VTSSUnsigned64,
    vtssMacsecStatisticsSecyRxSc5Sa2InPacketsUnusedSa      VTSSUnsigned64,
    vtssMacsecStatisticsSecyRxSc5Sa2InPacketsUnchecked     VTSSUnsigned64,
    vtssMacsecStatisticsSecyRxSc5Sa2InPacketsDelayed       VTSSUnsigned64,
    vtssMacsecStatisticsSecyRxSc5Sa2InPacketsLate          VTSSUnsigned64,
    vtssMacsecStatisticsSecyRxSc5Sa3InPacketsOk            VTSSUnsigned64,
    vtssMacsecStatisticsSecyRxSc5Sa3InPacketsInvalid       VTSSUnsigned64,
    vtssMacsecStatisticsSecyRxSc5Sa3InPacketsNotValid      VTSSUnsigned64,
    vtssMacsecStatisticsSecyRxSc5Sa3InPacketsNotUsingSa    VTSSUnsigned64,
    vtssMacsecStatisticsSecyRxSc5Sa3InPacketsUnusedSa      VTSSUnsigned64,
    vtssMacsecStatisticsSecyRxSc5Sa3InPacketsUnchecked     VTSSUnsigned64,
    vtssMacsecStatisticsSecyRxSc5Sa3InPacketsDelayed       VTSSUnsigned64,
    vtssMacsecStatisticsSecyRxSc5Sa3InPacketsLate          VTSSUnsigned64,
    vtssMacsecStatisticsSecyRxSc5Sa4InPacketsOk            VTSSUnsigned64,
    vtssMacsecStatisticsSecyRxSc5Sa4InPacketsInvalid       VTSSUnsigned64,
    vtssMacsecStatisticsSecyRxSc5Sa4InPacketsNotValid      VTSSUnsigned64,
    vtssMacsecStatisticsSecyRxSc5Sa4InPacketsNotUsingSa    VTSSUnsigned64,
    vtssMacsecStatisticsSecyRxSc5Sa4InPacketsUnusedSa      VTSSUnsigned64,
    vtssMacsecStatisticsSecyRxSc5Sa4InPacketsUnchecked     VTSSUnsigned64,
    vtssMacsecStatisticsSecyRxSc5Sa4InPacketsDelayed       VTSSUnsigned64,
    vtssMacsecStatisticsSecyRxSc5Sa4InPacketsLate          VTSSUnsigned64,
    vtssMacsecStatisticsSecyRxSc6InPacketsUnchecked        VTSSUnsigned64,
    vtssMacsecStatisticsSecyRxSc6InPacketsDelayed          VTSSUnsigned64,
    vtssMacsecStatisticsSecyRxSc6InPacketsLate             VTSSUnsigned64,
    vtssMacsecStatisticsSecyRxSc6InPacketsOk               VTSSUnsigned64,
    vtssMacsecStatisticsSecyRxSc6InPacketsInvalid          VTSSUnsigned64,
    vtssMacsecStatisticsSecyRxSc6InPacketsNotValid         VTSSUnsigned64,
    vtssMacsecStatisticsSecyRxSc6InPacketsNotUsingSa       VTSSUnsigned64,
    vtssMacsecStatisticsSecyRxSc6InPacketsUnusedSa         VTSSUnsigned64,
    vtssMacsecStatisticsSecyRxSc6InOctetsValidated         VTSSUnsigned64,
    vtssMacsecStatisticsSecyRxSc6InOctetsDecrypted         VTSSUnsigned64,
    vtssMacsecStatisticsSecyRxSc6Sa1InPacketsOk            VTSSUnsigned64,
    vtssMacsecStatisticsSecyRxSc6Sa1InPacketsInvalid       VTSSUnsigned64,
    vtssMacsecStatisticsSecyRxSc6Sa1InPacketsNotValid      VTSSUnsigned64,
    vtssMacsecStatisticsSecyRxSc6Sa1InPacketsNotUsingSa    VTSSUnsigned64,
    vtssMacsecStatisticsSecyRxSc6Sa1InPacketsUnusedSa      VTSSUnsigned64,
    vtssMacsecStatisticsSecyRxSc6Sa1InPacketsUnchecked     VTSSUnsigned64,
    vtssMacsecStatisticsSecyRxSc6Sa1InPacketsDelayed       VTSSUnsigned64,
    vtssMacsecStatisticsSecyRxSc6Sa1InPacketsLate          VTSSUnsigned64,
    vtssMacsecStatisticsSecyRxSc6Sa2InPacketsOk            VTSSUnsigned64,
    vtssMacsecStatisticsSecyRxSc6Sa2InPacketsInvalid       VTSSUnsigned64,
    vtssMacsecStatisticsSecyRxSc6Sa2InPacketsNotValid      VTSSUnsigned64,
    vtssMacsecStatisticsSecyRxSc6Sa2InPacketsNotUsingSa    VTSSUnsigned64,
    vtssMacsecStatisticsSecyRxSc6Sa2InPacketsUnusedSa      VTSSUnsigned64,
    vtssMacsecStatisticsSecyRxSc6Sa2InPacketsUnchecked     VTSSUnsigned64,
    vtssMacsecStatisticsSecyRxSc6Sa2InPacketsDelayed       VTSSUnsigned64,
    vtssMacsecStatisticsSecyRxSc6Sa2InPacketsLate          VTSSUnsigned64,
    vtssMacsecStatisticsSecyRxSc6Sa3InPacketsOk            VTSSUnsigned64,
    vtssMacsecStatisticsSecyRxSc6Sa3InPacketsInvalid       VTSSUnsigned64,
    vtssMacsecStatisticsSecyRxSc6Sa3InPacketsNotValid      VTSSUnsigned64,
    vtssMacsecStatisticsSecyRxSc6Sa3InPacketsNotUsingSa    VTSSUnsigned64,
    vtssMacsecStatisticsSecyRxSc6Sa3InPacketsUnusedSa      VTSSUnsigned64,
    vtssMacsecStatisticsSecyRxSc6Sa3InPacketsUnchecked     VTSSUnsigned64,
    vtssMacsecStatisticsSecyRxSc6Sa3InPacketsDelayed       VTSSUnsigned64,
    vtssMacsecStatisticsSecyRxSc6Sa3InPacketsLate          VTSSUnsigned64,
    vtssMacsecStatisticsSecyRxSc6Sa4InPacketsOk            VTSSUnsigned64,
    vtssMacsecStatisticsSecyRxSc6Sa4InPacketsInvalid       VTSSUnsigned64,
    vtssMacsecStatisticsSecyRxSc6Sa4InPacketsNotValid      VTSSUnsigned64,
    vtssMacsecStatisticsSecyRxSc6Sa4InPacketsNotUsingSa    VTSSUnsigned64,
    vtssMacsecStatisticsSecyRxSc6Sa4InPacketsUnusedSa      VTSSUnsigned64,
    vtssMacsecStatisticsSecyRxSc6Sa4InPacketsUnchecked     VTSSUnsigned64,
    vtssMacsecStatisticsSecyRxSc6Sa4InPacketsDelayed       VTSSUnsigned64,
    vtssMacsecStatisticsSecyRxSc6Sa4InPacketsLate          VTSSUnsigned64,
    vtssMacsecStatisticsSecyRxSc7InPacketsUnchecked        VTSSUnsigned64,
    vtssMacsecStatisticsSecyRxSc7InPacketsDelayed          VTSSUnsigned64,
    vtssMacsecStatisticsSecyRxSc7InPacketsLate             VTSSUnsigned64,
    vtssMacsecStatisticsSecyRxSc7InPacketsOk               VTSSUnsigned64,
    vtssMacsecStatisticsSecyRxSc7InPacketsInvalid          VTSSUnsigned64,
    vtssMacsecStatisticsSecyRxSc7InPacketsNotValid         VTSSUnsigned64,
    vtssMacsecStatisticsSecyRxSc7InPacketsNotUsingSa       VTSSUnsigned64,
    vtssMacsecStatisticsSecyRxSc7InPacketsUnusedSa         VTSSUnsigned64,
    vtssMacsecStatisticsSecyRxSc7InOctetsValidated         VTSSUnsigned64,
    vtssMacsecStatisticsSecyRxSc7InOctetsDecrypted         VTSSUnsigned64,
    vtssMacsecStatisticsSecyRxSc7Sa1InPacketsOk            VTSSUnsigned64,
    vtssMacsecStatisticsSecyRxSc7Sa1InPacketsInvalid       VTSSUnsigned64,
    vtssMacsecStatisticsSecyRxSc7Sa1InPacketsNotValid      VTSSUnsigned64,
    vtssMacsecStatisticsSecyRxSc7Sa1InPacketsNotUsingSa    VTSSUnsigned64,
    vtssMacsecStatisticsSecyRxSc7Sa1InPacketsUnusedSa      VTSSUnsigned64,
    vtssMacsecStatisticsSecyRxSc7Sa1InPacketsUnchecked     VTSSUnsigned64,
    vtssMacsecStatisticsSecyRxSc7Sa1InPacketsDelayed       VTSSUnsigned64,
    vtssMacsecStatisticsSecyRxSc7Sa1InPacketsLate          VTSSUnsigned64,
    vtssMacsecStatisticsSecyRxSc7Sa2InPacketsOk            VTSSUnsigned64,
    vtssMacsecStatisticsSecyRxSc7Sa2InPacketsInvalid       VTSSUnsigned64,
    vtssMacsecStatisticsSecyRxSc7Sa2InPacketsNotValid      VTSSUnsigned64,
    vtssMacsecStatisticsSecyRxSc7Sa2InPacketsNotUsingSa    VTSSUnsigned64,
    vtssMacsecStatisticsSecyRxSc7Sa2InPacketsUnusedSa      VTSSUnsigned64,
    vtssMacsecStatisticsSecyRxSc7Sa2InPacketsUnchecked     VTSSUnsigned64,
    vtssMacsecStatisticsSecyRxSc7Sa2InPacketsDelayed       VTSSUnsigned64,
    vtssMacsecStatisticsSecyRxSc7Sa2InPacketsLate          VTSSUnsigned64,
    vtssMacsecStatisticsSecyRxSc7Sa3InPacketsOk            VTSSUnsigned64,
    vtssMacsecStatisticsSecyRxSc7Sa3InPacketsInvalid       VTSSUnsigned64,
    vtssMacsecStatisticsSecyRxSc7Sa3InPacketsNotValid      VTSSUnsigned64,
    vtssMacsecStatisticsSecyRxSc7Sa3InPacketsNotUsingSa    VTSSUnsigned64,
    vtssMacsecStatisticsSecyRxSc7Sa3InPacketsUnusedSa      VTSSUnsigned64,
    vtssMacsecStatisticsSecyRxSc7Sa3InPacketsUnchecked     VTSSUnsigned64,
    vtssMacsecStatisticsSecyRxSc7Sa3InPacketsDelayed       VTSSUnsigned64,
    vtssMacsecStatisticsSecyRxSc7Sa3InPacketsLate          VTSSUnsigned64,
    vtssMacsecStatisticsSecyRxSc7Sa4InPacketsOk            VTSSUnsigned64,
    vtssMacsecStatisticsSecyRxSc7Sa4InPacketsInvalid       VTSSUnsigned64,
    vtssMacsecStatisticsSecyRxSc7Sa4InPacketsNotValid      VTSSUnsigned64,
    vtssMacsecStatisticsSecyRxSc7Sa4InPacketsNotUsingSa    VTSSUnsigned64,
    vtssMacsecStatisticsSecyRxSc7Sa4InPacketsUnusedSa      VTSSUnsigned64,
    vtssMacsecStatisticsSecyRxSc7Sa4InPacketsUnchecked     VTSSUnsigned64,
    vtssMacsecStatisticsSecyRxSc7Sa4InPacketsDelayed       VTSSUnsigned64,
    vtssMacsecStatisticsSecyRxSc7Sa4InPacketsLate          VTSSUnsigned64,
    vtssMacsecStatisticsSecyRxSc8InPacketsUnchecked        VTSSUnsigned64,
    vtssMacsecStatisticsSecyRxSc8InPacketsDelayed          VTSSUnsigned64,
    vtssMacsecStatisticsSecyRxSc8InPacketsLate             VTSSUnsigned64,
    vtssMacsecStatisticsSecyRxSc8InPacketsOk               VTSSUnsigned64,
    vtssMacsecStatisticsSecyRxSc8InPacketsInvalid          VTSSUnsigned64,
    vtssMacsecStatisticsSecyRxSc8InPacketsNotValid         VTSSUnsigned64,
    vtssMacsecStatisticsSecyRxSc8InPacketsNotUsingSa       VTSSUnsigned64,
    vtssMacsecStatisticsSecyRxSc8InPacketsUnusedSa         VTSSUnsigned64,
    vtssMacsecStatisticsSecyRxSc8InOctetsValidated         VTSSUnsigned64,
    vtssMacsecStatisticsSecyRxSc8InOctetsDecrypted         VTSSUnsigned64,
    vtssMacsecStatisticsSecyRxSc8Sa1InPacketsOk            VTSSUnsigned64,
    vtssMacsecStatisticsSecyRxSc8Sa1InPacketsInvalid       VTSSUnsigned64,
    vtssMacsecStatisticsSecyRxSc8Sa1InPacketsNotValid      VTSSUnsigned64,
    vtssMacsecStatisticsSecyRxSc8Sa1InPacketsNotUsingSa    VTSSUnsigned64,
    vtssMacsecStatisticsSecyRxSc8Sa1InPacketsUnusedSa      VTSSUnsigned64,
    vtssMacsecStatisticsSecyRxSc8Sa1InPacketsUnchecked     VTSSUnsigned64,
    vtssMacsecStatisticsSecyRxSc8Sa1InPacketsDelayed       VTSSUnsigned64,
    vtssMacsecStatisticsSecyRxSc8Sa1InPacketsLate          VTSSUnsigned64,
    vtssMacsecStatisticsSecyRxSc8Sa2InPacketsOk            VTSSUnsigned64,
    vtssMacsecStatisticsSecyRxSc8Sa2InPacketsInvalid       VTSSUnsigned64,
    vtssMacsecStatisticsSecyRxSc8Sa2InPacketsNotValid      VTSSUnsigned64,
    vtssMacsecStatisticsSecyRxSc8Sa2InPacketsNotUsingSa    VTSSUnsigned64,
    vtssMacsecStatisticsSecyRxSc8Sa2InPacketsUnusedSa      VTSSUnsigned64,
    vtssMacsecStatisticsSecyRxSc8Sa2InPacketsUnchecked     VTSSUnsigned64,
    vtssMacsecStatisticsSecyRxSc8Sa2InPacketsDelayed       VTSSUnsigned64,
    vtssMacsecStatisticsSecyRxSc8Sa2InPacketsLate          VTSSUnsigned64,
    vtssMacsecStatisticsSecyRxSc8Sa3InPacketsOk            VTSSUnsigned64,
    vtssMacsecStatisticsSecyRxSc8Sa3InPacketsInvalid       VTSSUnsigned64,
    vtssMacsecStatisticsSecyRxSc8Sa3InPacketsNotValid      VTSSUnsigned64,
    vtssMacsecStatisticsSecyRxSc8Sa3InPacketsNotUsingSa    VTSSUnsigned64,
    vtssMacsecStatisticsSecyRxSc8Sa3InPacketsUnusedSa      VTSSUnsigned64,
    vtssMacsecStatisticsSecyRxSc8Sa3InPacketsUnchecked     VTSSUnsigned64,
    vtssMacsecStatisticsSecyRxSc8Sa3InPacketsDelayed       VTSSUnsigned64,
    vtssMacsecStatisticsSecyRxSc8Sa3InPacketsLate          VTSSUnsigned64,
    vtssMacsecStatisticsSecyRxSc8Sa4InPacketsOk            VTSSUnsigned64,
    vtssMacsecStatisticsSecyRxSc8Sa4InPacketsInvalid       VTSSUnsigned64,
    vtssMacsecStatisticsSecyRxSc8Sa4InPacketsNotValid      VTSSUnsigned64,
    vtssMacsecStatisticsSecyRxSc8Sa4InPacketsNotUsingSa    VTSSUnsigned64,
    vtssMacsecStatisticsSecyRxSc8Sa4InPacketsUnusedSa      VTSSUnsigned64,
    vtssMacsecStatisticsSecyRxSc8Sa4InPacketsUnchecked     VTSSUnsigned64,
    vtssMacsecStatisticsSecyRxSc8Sa4InPacketsDelayed       VTSSUnsigned64,
    vtssMacsecStatisticsSecyRxSc8Sa4InPacketsLate          VTSSUnsigned64
}

vtssMacsecStatisticsSecyIfIndex OBJECT-TYPE
    SYNTAX      VTSSInterfaceIndex
    MAX-ACCESS  accessible-for-notify
    STATUS      current
    DESCRIPTION
        "Logical port interface index."
    ::= { vtssMacsecStatisticsSecyEntry 1 }

vtssMacsecStatisticsSecySecyId OBJECT-TYPE
    SYNTAX      Unsigned32
    MAX-ACCESS  accessible-for-notify
    STATUS      current
    DESCRIPTION
        "SecY IDs are numbered 1 through maximum number of SecYs support on an
         interface."
    ::= { vtssMacsecStatisticsSecyEntry 2 }

vtssMacsecStatisticsSecyControlledInPackets OBJECT-TYPE
    SYNTAX      VTSSUnsigned64
    MAX-ACCESS  read-only
    STATUS      current
    DESCRIPTION
        "Number of packets received on the controlled port."
    ::= { vtssMacsecStatisticsSecyEntry 3 }

vtssMacsecStatisticsSecyControlledInOctets OBJECT-TYPE
    SYNTAX      VTSSUnsigned64
    MAX-ACCESS  read-only
    STATUS      current
    DESCRIPTION
        "Number of octets received on the controlled port."
    ::= { vtssMacsecStatisticsSecyEntry 4 }

vtssMacsecStatisticsSecyControlledInUnicastPackets OBJECT-TYPE
    SYNTAX      VTSSUnsigned64
    MAX-ACCESS  read-only
    STATUS      current
    DESCRIPTION
        "Number of unicast packets received on the controlled port."
    ::= { vtssMacsecStatisticsSecyEntry 5 }

vtssMacsecStatisticsSecyControlledInMulticastPackets OBJECT-TYPE
    SYNTAX      VTSSUnsigned64
    MAX-ACCESS  read-only
    STATUS      current
    DESCRIPTION
        "Number of multicast packets received on the controlled port."
    ::= { vtssMacsecStatisticsSecyEntry 6 }

vtssMacsecStatisticsSecyControlledInBroadcastPackets OBJECT-TYPE
    SYNTAX      VTSSUnsigned64
    MAX-ACCESS  read-only
    STATUS      current
    DESCRIPTION
        "Number of broadcast packets received on the controlled port."
    ::= { vtssMacsecStatisticsSecyEntry 7 }

vtssMacsecStatisticsSecyControlledInDiscards OBJECT-TYPE
    SYNTAX      VTSSUnsigned64
    MAX-ACCESS  read-only
    STATUS      current
    DESCRIPTION
        "Number of discarded packets received on the controlled port."
    ::= { vtssMacsecStatisticsSecyEntry 8 }

vtssMacsecStatisticsSecyControlledInErrors OBJECT-TYPE
    SYNTAX      VTSSUnsigned64
    MAX-ACCESS  read-only
    STATUS      current
    DESCRIPTION
        "Number of erroneous packets received on the controlled port."
    ::= { vtssMacsecStatisticsSecyEntry 9 }

vtssMacsecStatisticsSecyControlledOutPackets OBJECT-TYPE
    SYNTAX      VTSSUnsigned64
    MAX-ACCESS  read-only
    STATUS      current
    DESCRIPTION
        "Number of packets transmitted on the controlled port."
    ::= { vtssMacsecStatisticsSecyEntry 10 }

vtssMacsecStatisticsSecyControlledOutOctets OBJECT-TYPE
    SYNTAX      VTSSUnsigned64
    MAX-ACCESS  read-only
    STATUS      current
    DESCRIPTION
        "Number of octets transmitted on the controlled port."
    ::= { vtssMacsecStatisticsSecyEntry 11 }

vtssMacsecStatisticsSecyControlledOutUnicastPackets OBJECT-TYPE
    SYNTAX      VTSSUnsigned64
    MAX-ACCESS  read-only
    STATUS      current
    DESCRIPTION
        "Number of unicast packets transmitted on the controlled port."
    ::= { vtssMacsecStatisticsSecyEntry 12 }

vtssMacsecStatisticsSecyControlledOutMulticastPackets OBJECT-TYPE
    SYNTAX      VTSSUnsigned64
    MAX-ACCESS  read-only
    STATUS      current
    DESCRIPTION
        "Number of multicast packets transmitted on the controlled port."
    ::= { vtssMacsecStatisticsSecyEntry 13 }

vtssMacsecStatisticsSecyControlledOutBroadcastPackets OBJECT-TYPE
    SYNTAX      VTSSUnsigned64
    MAX-ACCESS  read-only
    STATUS      current
    DESCRIPTION
        "Number of broadcast packets transmitted on the controlled port."
    ::= { vtssMacsecStatisticsSecyEntry 14 }

vtssMacsecStatisticsSecyControlledOutErrors OBJECT-TYPE
    SYNTAX      VTSSUnsigned64
    MAX-ACCESS  read-only
    STATUS      current
    DESCRIPTION
        "Number of erroneous packets transmitted on the controlled port."
    ::= { vtssMacsecStatisticsSecyEntry 15 }

vtssMacsecStatisticsSecySecyInPacketsUntagged OBJECT-TYPE
    SYNTAX      VTSSUnsigned64
    MAX-ACCESS  read-only
    STATUS      current
    DESCRIPTION
        "Number of packets received without secTAG on this SecY (not in strict
         mode)."
    ::= { vtssMacsecStatisticsSecyEntry 26 }

vtssMacsecStatisticsSecySecyInPacketsNoTag OBJECT-TYPE
    SYNTAX      VTSSUnsigned64
    MAX-ACCESS  read-only
    STATUS      current
    DESCRIPTION
        "Number of packets received and discared, because of no secTAG on this
         SecY (in strict mode)."
    ::= { vtssMacsecStatisticsSecyEntry 27 }

vtssMacsecStatisticsSecySecyInPacketsBadTag OBJECT-TYPE
    SYNTAX      VTSSUnsigned64
    MAX-ACCESS  read-only
    STATUS      current
    DESCRIPTION
        "Number of packets received and discarded, because of an invalid secTAG
         or zero or invalid packet number on this SecY."
    ::= { vtssMacsecStatisticsSecyEntry 28 }

vtssMacsecStatisticsSecySecyInPacketsUnknownSci OBJECT-TYPE
    SYNTAX      VTSSUnsigned64
    MAX-ACCESS  read-only
    STATUS      current
    DESCRIPTION
        "Number of received packets with unknown SCI (not in strict mode) and
         the C-bit in the secTAG is not set."
    ::= { vtssMacsecStatisticsSecyEntry 29 }

vtssMacsecStatisticsSecySecyInPacketsNoSci OBJECT-TYPE
    SYNTAX      VTSSUnsigned64
    MAX-ACCESS  read-only
    STATUS      current
    DESCRIPTION
        "Number of packets received and discarded on this SecY, because of an
         unknown SCI (in strict mode) or the C-bit in the secTAG is set."
    ::= { vtssMacsecStatisticsSecyEntry 30 }

vtssMacsecStatisticsSecySecyInPacketsOverrun OBJECT-TYPE
    SYNTAX      VTSSUnsigned64
    MAX-ACCESS  read-only
    STATUS      current
    DESCRIPTION
        "Number of packets received and discarded, because the number of
         received packets exceeded the cryptographic performance capabilities on
         this SecY."
    ::= { vtssMacsecStatisticsSecyEntry 31 }

vtssMacsecStatisticsSecySecyInOctetsValidated OBJECT-TYPE
    SYNTAX      VTSSUnsigned64
    MAX-ACCESS  read-only
    STATUS      current
    DESCRIPTION
        "Number of octets received and validated on this SecY."
    ::= { vtssMacsecStatisticsSecyEntry 32 }

vtssMacsecStatisticsSecySecyInOctetsDecrypted OBJECT-TYPE
    SYNTAX      VTSSUnsigned64
    MAX-ACCESS  read-only
    STATUS      current
    DESCRIPTION
        "Number of octets received and decrypted on this SecY."
    ::= { vtssMacsecStatisticsSecyEntry 33 }

vtssMacsecStatisticsSecySecyOutPacketsUntagged OBJECT-TYPE
    SYNTAX      VTSSUnsigned64
    MAX-ACCESS  read-only
    STATUS      current
    DESCRIPTION
        "Number of packets transmitted without the secTAG on this SecY."
    ::= { vtssMacsecStatisticsSecyEntry 34 }

vtssMacsecStatisticsSecySecyOutPacketsTooLong OBJECT-TYPE
    SYNTAX      VTSSUnsigned64
    MAX-ACCESS  read-only
    STATUS      current
    DESCRIPTION
        "Number of packets meant for transmission that were discarded because
         the packet length is larger than the interface MTU on this SecY."
    ::= { vtssMacsecStatisticsSecyEntry 35 }

vtssMacsecStatisticsSecySecyOutOctetsProtected OBJECT-TYPE
    SYNTAX      VTSSUnsigned64
    MAX-ACCESS  read-only
    STATUS      current
    DESCRIPTION
        "Number of integrity, but not encrypted octets on this SecY."
    ::= { vtssMacsecStatisticsSecyEntry 36 }

vtssMacsecStatisticsSecySecyOutOctetsEncrypted OBJECT-TYPE
    SYNTAX      VTSSUnsigned64
    MAX-ACCESS  read-only
    STATUS      current
    DESCRIPTION
        "Number of octets integrity and encrypted octets on this SecY."
    ::= { vtssMacsecStatisticsSecyEntry 37 }

vtssMacsecStatisticsSecyTxScOutPacketsProtected OBJECT-TYPE
    SYNTAX      VTSSUnsigned64
    MAX-ACCESS  read-only
    STATUS      current
    DESCRIPTION
        "Number of protected packets transmitted on this SecY."
    ::= { vtssMacsecStatisticsSecyEntry 48 }

vtssMacsecStatisticsSecyTxScOutPacketsEncrypted OBJECT-TYPE
    SYNTAX      VTSSUnsigned64
    MAX-ACCESS  read-only
    STATUS      current
    DESCRIPTION
        "Number of encrypted packets transmitted on this SecY."
    ::= { vtssMacsecStatisticsSecyEntry 49 }

vtssMacsecStatisticsSecyTxScOutOctetsProtected OBJECT-TYPE
    SYNTAX      VTSSUnsigned64
    MAX-ACCESS  read-only
    STATUS      current
    DESCRIPTION
        "Number of protected octets transmitted on this SecY."
    ::= { vtssMacsecStatisticsSecyEntry 50 }

vtssMacsecStatisticsSecyTxScOutOctetsEncrypted OBJECT-TYPE
    SYNTAX      VTSSUnsigned64
    MAX-ACCESS  read-only
    STATUS      current
    DESCRIPTION
        "Number of encrypted octets transmitted on this SecY."
    ::= { vtssMacsecStatisticsSecyEntry 51 }

vtssMacsecStatisticsSecyTxSa1OutPacketsProtected OBJECT-TYPE
    SYNTAX      VTSSUnsigned64
    MAX-ACCESS  read-only
    STATUS      current
    DESCRIPTION
        "Number of protected packets transmitted by this SA."
    ::= { vtssMacsecStatisticsSecyEntry 62 }

vtssMacsecStatisticsSecyTxSa1OutPacketsEncrypted OBJECT-TYPE
    SYNTAX      VTSSUnsigned64
    MAX-ACCESS  read-only
    STATUS      current
    DESCRIPTION
        "Number of encrypted packets transmitted by this SA."
    ::= { vtssMacsecStatisticsSecyEntry 63 }

vtssMacsecStatisticsSecyTxSa2OutPacketsProtected OBJECT-TYPE
    SYNTAX      VTSSUnsigned64
    MAX-ACCESS  read-only
    STATUS      current
    DESCRIPTION
        "Number of protected packets transmitted by this SA."
    ::= { vtssMacsecStatisticsSecyEntry 69 }

vtssMacsecStatisticsSecyTxSa2OutPacketsEncrypted OBJECT-TYPE
    SYNTAX      VTSSUnsigned64
    MAX-ACCESS  read-only
    STATUS      current
    DESCRIPTION
        "Number of encrypted packets transmitted by this SA."
    ::= { vtssMacsecStatisticsSecyEntry 70 }

vtssMacsecStatisticsSecyTxSa3OutPacketsProtected OBJECT-TYPE
    SYNTAX      VTSSUnsigned64
    MAX-ACCESS  read-only
    STATUS      current
    DESCRIPTION
        "Number of protected packets transmitted by this SA."
    ::= { vtssMacsecStatisticsSecyEntry 76 }

vtssMacsecStatisticsSecyTxSa3OutPacketsEncrypted OBJECT-TYPE
    SYNTAX      VTSSUnsigned64
    MAX-ACCESS  read-only
    STATUS      current
    DESCRIPTION
        "Number of encrypted packets transmitted by this SA."
    ::= { vtssMacsecStatisticsSecyEntry 77 }

vtssMacsecStatisticsSecyTxSa4OutPacketsProtected OBJECT-TYPE
    SYNTAX      VTSSUnsigned64
    MAX-ACCESS  read-only
    STATUS      current
    DESCRIPTION
        "Number of protected packets transmitted by this SA."
    ::= { vtssMacsecStatisticsSecyEntry 83 }

vtssMacsecStatisticsSecyTxSa4OutPacketsEncrypted OBJECT-TYPE
    SYNTAX      VTSSUnsigned64
    MAX-ACCESS  read-only
    STATUS      current
    DESCRIPTION
        "Number of encrypted packets transmitted by this SA."
    ::= { vtssMacsecStatisticsSecyEntry 84 }

vtssMacsecStatisticsSecyRxSc1InPacketsUnchecked OBJECT-TYPE
    SYNTAX      VTSSUnsigned64
    MAX-ACCESS  read-only
    STATUS      current
    DESCRIPTION
        "Number of unchecked packets received on this Rx SC."
    ::= { vtssMacsecStatisticsSecyEntry 90 }

vtssMacsecStatisticsSecyRxSc1InPacketsDelayed OBJECT-TYPE
    SYNTAX      VTSSUnsigned64
    MAX-ACCESS  read-only
    STATUS      current
    DESCRIPTION
        "Number of delayed packets received on this Rx SC."
    ::= { vtssMacsecStatisticsSecyEntry 91 }

vtssMacsecStatisticsSecyRxSc1InPacketsLate OBJECT-TYPE
    SYNTAX      VTSSUnsigned64
    MAX-ACCESS  read-only
    STATUS      current
    DESCRIPTION
        "Number of late packets received on this Rx SC."
    ::= { vtssMacsecStatisticsSecyEntry 92 }

vtssMacsecStatisticsSecyRxSc1InPacketsOk OBJECT-TYPE
    SYNTAX      VTSSUnsigned64
    MAX-ACCESS  read-only
    STATUS      current
    DESCRIPTION
        "Number of OK packets received on this Rx SC."
    ::= { vtssMacsecStatisticsSecyEntry 93 }

vtssMacsecStatisticsSecyRxSc1InPacketsInvalid OBJECT-TYPE
    SYNTAX      VTSSUnsigned64
    MAX-ACCESS  read-only
    STATUS      current
    DESCRIPTION
        "Number of invalid packets received on this Rx SC."
    ::= { vtssMacsecStatisticsSecyEntry 94 }

vtssMacsecStatisticsSecyRxSc1InPacketsNotValid OBJECT-TYPE
    SYNTAX      VTSSUnsigned64
    MAX-ACCESS  read-only
    STATUS      current
    DESCRIPTION
        "Number of not valid packets received on this Rx SC."
    ::= { vtssMacsecStatisticsSecyEntry 95 }

vtssMacsecStatisticsSecyRxSc1InPacketsNotUsingSa OBJECT-TYPE
    SYNTAX      VTSSUnsigned64
    MAX-ACCESS  read-only
    STATUS      current
    DESCRIPTION
        "Number of packets not using SA received on this Rx SC."
    ::= { vtssMacsecStatisticsSecyEntry 96 }

vtssMacsecStatisticsSecyRxSc1InPacketsUnusedSa OBJECT-TYPE
    SYNTAX      VTSSUnsigned64
    MAX-ACCESS  read-only
    STATUS      current
    DESCRIPTION
        "Number of packets with unused SA received on this Rx SC."
    ::= { vtssMacsecStatisticsSecyEntry 97 }

vtssMacsecStatisticsSecyRxSc1InOctetsValidated OBJECT-TYPE
    SYNTAX      VTSSUnsigned64
    MAX-ACCESS  read-only
    STATUS      current
    DESCRIPTION
        "Number of validated octets received on this Rx SC."
    ::= { vtssMacsecStatisticsSecyEntry 98 }

vtssMacsecStatisticsSecyRxSc1InOctetsDecrypted OBJECT-TYPE
    SYNTAX      VTSSUnsigned64
    MAX-ACCESS  read-only
    STATUS      current
    DESCRIPTION
        "Number of decrypted octets received on this Rx SC."
    ::= { vtssMacsecStatisticsSecyEntry 99 }

vtssMacsecStatisticsSecyRxSc1Sa1InPacketsOk OBJECT-TYPE
    SYNTAX      VTSSUnsigned64
    MAX-ACCESS  read-only
    STATUS      current
    DESCRIPTION
        "Number of OK packets received on this Rx SA."
    ::= { vtssMacsecStatisticsSecyEntry 110 }

vtssMacsecStatisticsSecyRxSc1Sa1InPacketsInvalid OBJECT-TYPE
    SYNTAX      VTSSUnsigned64
    MAX-ACCESS  read-only
    STATUS      current
    DESCRIPTION
        "Number of invalid packets received on this Rx SA."
    ::= { vtssMacsecStatisticsSecyEntry 111 }

vtssMacsecStatisticsSecyRxSc1Sa1InPacketsNotValid OBJECT-TYPE
    SYNTAX      VTSSUnsigned64
    MAX-ACCESS  read-only
    STATUS      current
    DESCRIPTION
        "Number of not valid packets received on this Rx SA."
    ::= { vtssMacsecStatisticsSecyEntry 112 }

vtssMacsecStatisticsSecyRxSc1Sa1InPacketsNotUsingSa OBJECT-TYPE
    SYNTAX      VTSSUnsigned64
    MAX-ACCESS  read-only
    STATUS      current
    DESCRIPTION
        "Number of packets not using SA received on this Rx SA."
    ::= { vtssMacsecStatisticsSecyEntry 113 }

vtssMacsecStatisticsSecyRxSc1Sa1InPacketsUnusedSa OBJECT-TYPE
    SYNTAX      VTSSUnsigned64
    MAX-ACCESS  read-only
    STATUS      current
    DESCRIPTION
        "Number of packets with unused SA received on this Rx SA."
    ::= { vtssMacsecStatisticsSecyEntry 114 }

vtssMacsecStatisticsSecyRxSc1Sa1InPacketsUnchecked OBJECT-TYPE
    SYNTAX      VTSSUnsigned64
    MAX-ACCESS  read-only
    STATUS      current
    DESCRIPTION
        "Number of unchecked packets received on this Rx SA."
    ::= { vtssMacsecStatisticsSecyEntry 115 }

vtssMacsecStatisticsSecyRxSc1Sa1InPacketsDelayed OBJECT-TYPE
    SYNTAX      VTSSUnsigned64
    MAX-ACCESS  read-only
    STATUS      current
    DESCRIPTION
        "Number of delayed packets received on this Rx SA."
    ::= { vtssMacsecStatisticsSecyEntry 116 }

vtssMacsecStatisticsSecyRxSc1Sa1InPacketsLate OBJECT-TYPE
    SYNTAX      VTSSUnsigned64
    MAX-ACCESS  read-only
    STATUS      current
    DESCRIPTION
        "Number of late packets received on this Rx SA."
    ::= { vtssMacsecStatisticsSecyEntry 117 }

vtssMacsecStatisticsSecyRxSc1Sa2InPacketsOk OBJECT-TYPE
    SYNTAX      VTSSUnsigned64
    MAX-ACCESS  read-only
    STATUS      current
    DESCRIPTION
        "Number of OK packets received on this Rx SA."
    ::= { vtssMacsecStatisticsSecyEntry 128 }

vtssMacsecStatisticsSecyRxSc1Sa2InPacketsInvalid OBJECT-TYPE
    SYNTAX      VTSSUnsigned64
    MAX-ACCESS  read-only
    STATUS      current
    DESCRIPTION
        "Number of invalid packets received on this Rx SA."
    ::= { vtssMacsecStatisticsSecyEntry 129 }

vtssMacsecStatisticsSecyRxSc1Sa2InPacketsNotValid OBJECT-TYPE
    SYNTAX      VTSSUnsigned64
    MAX-ACCESS  read-only
    STATUS      current
    DESCRIPTION
        "Number of not valid packets received on this Rx SA."
    ::= { vtssMacsecStatisticsSecyEntry 130 }

vtssMacsecStatisticsSecyRxSc1Sa2InPacketsNotUsingSa OBJECT-TYPE
    SYNTAX      VTSSUnsigned64
    MAX-ACCESS  read-only
    STATUS      current
    DESCRIPTION
        "Number of packets not using SA received on this Rx SA."
    ::= { vtssMacsecStatisticsSecyEntry 131 }

vtssMacsecStatisticsSecyRxSc1Sa2InPacketsUnusedSa OBJECT-TYPE
    SYNTAX      VTSSUnsigned64
    MAX-ACCESS  read-only
    STATUS      current
    DESCRIPTION
        "Number of packets with unused SA received on this Rx SA."
    ::= { vtssMacsecStatisticsSecyEntry 132 }

vtssMacsecStatisticsSecyRxSc1Sa2InPacketsUnchecked OBJECT-TYPE
    SYNTAX      VTSSUnsigned64
    MAX-ACCESS  read-only
    STATUS      current
    DESCRIPTION
        "Number of unchecked packets received on this Rx SA."
    ::= { vtssMacsecStatisticsSecyEntry 133 }

vtssMacsecStatisticsSecyRxSc1Sa2InPacketsDelayed OBJECT-TYPE
    SYNTAX      VTSSUnsigned64
    MAX-ACCESS  read-only
    STATUS      current
    DESCRIPTION
        "Number of delayed packets received on this Rx SA."
    ::= { vtssMacsecStatisticsSecyEntry 134 }

vtssMacsecStatisticsSecyRxSc1Sa2InPacketsLate OBJECT-TYPE
    SYNTAX      VTSSUnsigned64
    MAX-ACCESS  read-only
    STATUS      current
    DESCRIPTION
        "Number of late packets received on this Rx SA."
    ::= { vtssMacsecStatisticsSecyEntry 135 }

vtssMacsecStatisticsSecyRxSc1Sa3InPacketsOk OBJECT-TYPE
    SYNTAX      VTSSUnsigned64
    MAX-ACCESS  read-only
    STATUS      current
    DESCRIPTION
        "Number of OK packets received on this Rx SA."
    ::= { vtssMacsecStatisticsSecyEntry 146 }

vtssMacsecStatisticsSecyRxSc1Sa3InPacketsInvalid OBJECT-TYPE
    SYNTAX      VTSSUnsigned64
    MAX-ACCESS  read-only
    STATUS      current
    DESCRIPTION
        "Number of invalid packets received on this Rx SA."
    ::= { vtssMacsecStatisticsSecyEntry 147 }

vtssMacsecStatisticsSecyRxSc1Sa3InPacketsNotValid OBJECT-TYPE
    SYNTAX      VTSSUnsigned64
    MAX-ACCESS  read-only
    STATUS      current
    DESCRIPTION
        "Number of not valid packets received on this Rx SA."
    ::= { vtssMacsecStatisticsSecyEntry 148 }

vtssMacsecStatisticsSecyRxSc1Sa3InPacketsNotUsingSa OBJECT-TYPE
    SYNTAX      VTSSUnsigned64
    MAX-ACCESS  read-only
    STATUS      current
    DESCRIPTION
        "Number of packets not using SA received on this Rx SA."
    ::= { vtssMacsecStatisticsSecyEntry 149 }

vtssMacsecStatisticsSecyRxSc1Sa3InPacketsUnusedSa OBJECT-TYPE
    SYNTAX      VTSSUnsigned64
    MAX-ACCESS  read-only
    STATUS      current
    DESCRIPTION
        "Number of packets with unused SA received on this Rx SA."
    ::= { vtssMacsecStatisticsSecyEntry 150 }

vtssMacsecStatisticsSecyRxSc1Sa3InPacketsUnchecked OBJECT-TYPE
    SYNTAX      VTSSUnsigned64
    MAX-ACCESS  read-only
    STATUS      current
    DESCRIPTION
        "Number of unchecked packets received on this Rx SA."
    ::= { vtssMacsecStatisticsSecyEntry 151 }

vtssMacsecStatisticsSecyRxSc1Sa3InPacketsDelayed OBJECT-TYPE
    SYNTAX      VTSSUnsigned64
    MAX-ACCESS  read-only
    STATUS      current
    DESCRIPTION
        "Number of delayed packets received on this Rx SA."
    ::= { vtssMacsecStatisticsSecyEntry 152 }

vtssMacsecStatisticsSecyRxSc1Sa3InPacketsLate OBJECT-TYPE
    SYNTAX      VTSSUnsigned64
    MAX-ACCESS  read-only
    STATUS      current
    DESCRIPTION
        "Number of late packets received on this Rx SA."
    ::= { vtssMacsecStatisticsSecyEntry 153 }

vtssMacsecStatisticsSecyRxSc1Sa4InPacketsOk OBJECT-TYPE
    SYNTAX      VTSSUnsigned64
    MAX-ACCESS  read-only
    STATUS      current
    DESCRIPTION
        "Number of OK packets received on this Rx SA."
    ::= { vtssMacsecStatisticsSecyEntry 164 }

vtssMacsecStatisticsSecyRxSc1Sa4InPacketsInvalid OBJECT-TYPE
    SYNTAX      VTSSUnsigned64
    MAX-ACCESS  read-only
    STATUS      current
    DESCRIPTION
        "Number of invalid packets received on this Rx SA."
    ::= { vtssMacsecStatisticsSecyEntry 165 }

vtssMacsecStatisticsSecyRxSc1Sa4InPacketsNotValid OBJECT-TYPE
    SYNTAX      VTSSUnsigned64
    MAX-ACCESS  read-only
    STATUS      current
    DESCRIPTION
        "Number of not valid packets received on this Rx SA."
    ::= { vtssMacsecStatisticsSecyEntry 166 }

vtssMacsecStatisticsSecyRxSc1Sa4InPacketsNotUsingSa OBJECT-TYPE
    SYNTAX      VTSSUnsigned64
    MAX-ACCESS  read-only
    STATUS      current
    DESCRIPTION
        "Number of packets not using SA received on this Rx SA."
    ::= { vtssMacsecStatisticsSecyEntry 167 }

vtssMacsecStatisticsSecyRxSc1Sa4InPacketsUnusedSa OBJECT-TYPE
    SYNTAX      VTSSUnsigned64
    MAX-ACCESS  read-only
    STATUS      current
    DESCRIPTION
        "Number of packets with unused SA received on this Rx SA."
    ::= { vtssMacsecStatisticsSecyEntry 168 }

vtssMacsecStatisticsSecyRxSc1Sa4InPacketsUnchecked OBJECT-TYPE
    SYNTAX      VTSSUnsigned64
    MAX-ACCESS  read-only
    STATUS      current
    DESCRIPTION
        "Number of unchecked packets received on this Rx SA."
    ::= { vtssMacsecStatisticsSecyEntry 169 }

vtssMacsecStatisticsSecyRxSc1Sa4InPacketsDelayed OBJECT-TYPE
    SYNTAX      VTSSUnsigned64
    MAX-ACCESS  read-only
    STATUS      current
    DESCRIPTION
        "Number of delayed packets received on this Rx SA."
    ::= { vtssMacsecStatisticsSecyEntry 170 }

vtssMacsecStatisticsSecyRxSc1Sa4InPacketsLate OBJECT-TYPE
    SYNTAX      VTSSUnsigned64
    MAX-ACCESS  read-only
    STATUS      current
    DESCRIPTION
        "Number of late packets received on this Rx SA."
    ::= { vtssMacsecStatisticsSecyEntry 171 }

vtssMacsecStatisticsSecyRxSc2InPacketsUnchecked OBJECT-TYPE
    SYNTAX      VTSSUnsigned64
    MAX-ACCESS  read-only
    STATUS      current
    DESCRIPTION
        "Number of unchecked packets received on this Rx SC."
    ::= { vtssMacsecStatisticsSecyEntry 182 }

vtssMacsecStatisticsSecyRxSc2InPacketsDelayed OBJECT-TYPE
    SYNTAX      VTSSUnsigned64
    MAX-ACCESS  read-only
    STATUS      current
    DESCRIPTION
        "Number of delayed packets received on this Rx SC."
    ::= { vtssMacsecStatisticsSecyEntry 183 }

vtssMacsecStatisticsSecyRxSc2InPacketsLate OBJECT-TYPE
    SYNTAX      VTSSUnsigned64
    MAX-ACCESS  read-only
    STATUS      current
    DESCRIPTION
        "Number of late packets received on this Rx SC."
    ::= { vtssMacsecStatisticsSecyEntry 184 }

vtssMacsecStatisticsSecyRxSc2InPacketsOk OBJECT-TYPE
    SYNTAX      VTSSUnsigned64
    MAX-ACCESS  read-only
    STATUS      current
    DESCRIPTION
        "Number of OK packets received on this Rx SC."
    ::= { vtssMacsecStatisticsSecyEntry 185 }

vtssMacsecStatisticsSecyRxSc2InPacketsInvalid OBJECT-TYPE
    SYNTAX      VTSSUnsigned64
    MAX-ACCESS  read-only
    STATUS      current
    DESCRIPTION
        "Number of invalid packets received on this Rx SC."
    ::= { vtssMacsecStatisticsSecyEntry 186 }

vtssMacsecStatisticsSecyRxSc2InPacketsNotValid OBJECT-TYPE
    SYNTAX      VTSSUnsigned64
    MAX-ACCESS  read-only
    STATUS      current
    DESCRIPTION
        "Number of not valid packets received on this Rx SC."
    ::= { vtssMacsecStatisticsSecyEntry 187 }

vtssMacsecStatisticsSecyRxSc2InPacketsNotUsingSa OBJECT-TYPE
    SYNTAX      VTSSUnsigned64
    MAX-ACCESS  read-only
    STATUS      current
    DESCRIPTION
        "Number of packets not using SA received on this Rx SC."
    ::= { vtssMacsecStatisticsSecyEntry 188 }

vtssMacsecStatisticsSecyRxSc2InPacketsUnusedSa OBJECT-TYPE
    SYNTAX      VTSSUnsigned64
    MAX-ACCESS  read-only
    STATUS      current
    DESCRIPTION
        "Number of packets with unused SA received on this Rx SC."
    ::= { vtssMacsecStatisticsSecyEntry 189 }

vtssMacsecStatisticsSecyRxSc2InOctetsValidated OBJECT-TYPE
    SYNTAX      VTSSUnsigned64
    MAX-ACCESS  read-only
    STATUS      current
    DESCRIPTION
        "Number of validated octets received on this Rx SC."
    ::= { vtssMacsecStatisticsSecyEntry 190 }

vtssMacsecStatisticsSecyRxSc2InOctetsDecrypted OBJECT-TYPE
    SYNTAX      VTSSUnsigned64
    MAX-ACCESS  read-only
    STATUS      current
    DESCRIPTION
        "Number of decrypted octets received on this Rx SC."
    ::= { vtssMacsecStatisticsSecyEntry 191 }

vtssMacsecStatisticsSecyRxSc2Sa1InPacketsOk OBJECT-TYPE
    SYNTAX      VTSSUnsigned64
    MAX-ACCESS  read-only
    STATUS      current
    DESCRIPTION
        "Number of OK packets received on this Rx SA."
    ::= { vtssMacsecStatisticsSecyEntry 202 }

vtssMacsecStatisticsSecyRxSc2Sa1InPacketsInvalid OBJECT-TYPE
    SYNTAX      VTSSUnsigned64
    MAX-ACCESS  read-only
    STATUS      current
    DESCRIPTION
        "Number of invalid packets received on this Rx SA."
    ::= { vtssMacsecStatisticsSecyEntry 203 }

vtssMacsecStatisticsSecyRxSc2Sa1InPacketsNotValid OBJECT-TYPE
    SYNTAX      VTSSUnsigned64
    MAX-ACCESS  read-only
    STATUS      current
    DESCRIPTION
        "Number of not valid packets received on this Rx SA."
    ::= { vtssMacsecStatisticsSecyEntry 204 }

vtssMacsecStatisticsSecyRxSc2Sa1InPacketsNotUsingSa OBJECT-TYPE
    SYNTAX      VTSSUnsigned64
    MAX-ACCESS  read-only
    STATUS      current
    DESCRIPTION
        "Number of packets not using SA received on this Rx SA."
    ::= { vtssMacsecStatisticsSecyEntry 205 }

vtssMacsecStatisticsSecyRxSc2Sa1InPacketsUnusedSa OBJECT-TYPE
    SYNTAX      VTSSUnsigned64
    MAX-ACCESS  read-only
    STATUS      current
    DESCRIPTION
        "Number of packets with unused SA received on this Rx SA."
    ::= { vtssMacsecStatisticsSecyEntry 206 }

vtssMacsecStatisticsSecyRxSc2Sa1InPacketsUnchecked OBJECT-TYPE
    SYNTAX      VTSSUnsigned64
    MAX-ACCESS  read-only
    STATUS      current
    DESCRIPTION
        "Number of unchecked packets received on this Rx SA."
    ::= { vtssMacsecStatisticsSecyEntry 207 }

vtssMacsecStatisticsSecyRxSc2Sa1InPacketsDelayed OBJECT-TYPE
    SYNTAX      VTSSUnsigned64
    MAX-ACCESS  read-only
    STATUS      current
    DESCRIPTION
        "Number of delayed packets received on this Rx SA."
    ::= { vtssMacsecStatisticsSecyEntry 208 }

vtssMacsecStatisticsSecyRxSc2Sa1InPacketsLate OBJECT-TYPE
    SYNTAX      VTSSUnsigned64
    MAX-ACCESS  read-only
    STATUS      current
    DESCRIPTION
        "Number of late packets received on this Rx SA."
    ::= { vtssMacsecStatisticsSecyEntry 209 }

vtssMacsecStatisticsSecyRxSc2Sa2InPacketsOk OBJECT-TYPE
    SYNTAX      VTSSUnsigned64
    MAX-ACCESS  read-only
    STATUS      current
    DESCRIPTION
        "Number of OK packets received on this Rx SA."
    ::= { vtssMacsecStatisticsSecyEntry 220 }

vtssMacsecStatisticsSecyRxSc2Sa2InPacketsInvalid OBJECT-TYPE
    SYNTAX      VTSSUnsigned64
    MAX-ACCESS  read-only
    STATUS      current
    DESCRIPTION
        "Number of invalid packets received on this Rx SA."
    ::= { vtssMacsecStatisticsSecyEntry 221 }

vtssMacsecStatisticsSecyRxSc2Sa2InPacketsNotValid OBJECT-TYPE
    SYNTAX      VTSSUnsigned64
    MAX-ACCESS  read-only
    STATUS      current
    DESCRIPTION
        "Number of not valid packets received on this Rx SA."
    ::= { vtssMacsecStatisticsSecyEntry 222 }

vtssMacsecStatisticsSecyRxSc2Sa2InPacketsNotUsingSa OBJECT-TYPE
    SYNTAX      VTSSUnsigned64
    MAX-ACCESS  read-only
    STATUS      current
    DESCRIPTION
        "Number of packets not using SA received on this Rx SA."
    ::= { vtssMacsecStatisticsSecyEntry 223 }

vtssMacsecStatisticsSecyRxSc2Sa2InPacketsUnusedSa OBJECT-TYPE
    SYNTAX      VTSSUnsigned64
    MAX-ACCESS  read-only
    STATUS      current
    DESCRIPTION
        "Number of packets with unused SA received on this Rx SA."
    ::= { vtssMacsecStatisticsSecyEntry 224 }

vtssMacsecStatisticsSecyRxSc2Sa2InPacketsUnchecked OBJECT-TYPE
    SYNTAX      VTSSUnsigned64
    MAX-ACCESS  read-only
    STATUS      current
    DESCRIPTION
        "Number of unchecked packets received on this Rx SA."
    ::= { vtssMacsecStatisticsSecyEntry 225 }

vtssMacsecStatisticsSecyRxSc2Sa2InPacketsDelayed OBJECT-TYPE
    SYNTAX      VTSSUnsigned64
    MAX-ACCESS  read-only
    STATUS      current
    DESCRIPTION
        "Number of delayed packets received on this Rx SA."
    ::= { vtssMacsecStatisticsSecyEntry 226 }

vtssMacsecStatisticsSecyRxSc2Sa2InPacketsLate OBJECT-TYPE
    SYNTAX      VTSSUnsigned64
    MAX-ACCESS  read-only
    STATUS      current
    DESCRIPTION
        "Number of late packets received on this Rx SA."
    ::= { vtssMacsecStatisticsSecyEntry 227 }

vtssMacsecStatisticsSecyRxSc2Sa3InPacketsOk OBJECT-TYPE
    SYNTAX      VTSSUnsigned64
    MAX-ACCESS  read-only
    STATUS      current
    DESCRIPTION
        "Number of OK packets received on this Rx SA."
    ::= { vtssMacsecStatisticsSecyEntry 238 }

vtssMacsecStatisticsSecyRxSc2Sa3InPacketsInvalid OBJECT-TYPE
    SYNTAX      VTSSUnsigned64
    MAX-ACCESS  read-only
    STATUS      current
    DESCRIPTION
        "Number of invalid packets received on this Rx SA."
    ::= { vtssMacsecStatisticsSecyEntry 239 }

vtssMacsecStatisticsSecyRxSc2Sa3InPacketsNotValid OBJECT-TYPE
    SYNTAX      VTSSUnsigned64
    MAX-ACCESS  read-only
    STATUS      current
    DESCRIPTION
        "Number of not valid packets received on this Rx SA."
    ::= { vtssMacsecStatisticsSecyEntry 240 }

vtssMacsecStatisticsSecyRxSc2Sa3InPacketsNotUsingSa OBJECT-TYPE
    SYNTAX      VTSSUnsigned64
    MAX-ACCESS  read-only
    STATUS      current
    DESCRIPTION
        "Number of packets not using SA received on this Rx SA."
    ::= { vtssMacsecStatisticsSecyEntry 241 }

vtssMacsecStatisticsSecyRxSc2Sa3InPacketsUnusedSa OBJECT-TYPE
    SYNTAX      VTSSUnsigned64
    MAX-ACCESS  read-only
    STATUS      current
    DESCRIPTION
        "Number of packets with unused SA received on this Rx SA."
    ::= { vtssMacsecStatisticsSecyEntry 242 }

vtssMacsecStatisticsSecyRxSc2Sa3InPacketsUnchecked OBJECT-TYPE
    SYNTAX      VTSSUnsigned64
    MAX-ACCESS  read-only
    STATUS      current
    DESCRIPTION
        "Number of unchecked packets received on this Rx SA."
    ::= { vtssMacsecStatisticsSecyEntry 243 }

vtssMacsecStatisticsSecyRxSc2Sa3InPacketsDelayed OBJECT-TYPE
    SYNTAX      VTSSUnsigned64
    MAX-ACCESS  read-only
    STATUS      current
    DESCRIPTION
        "Number of delayed packets received on this Rx SA."
    ::= { vtssMacsecStatisticsSecyEntry 244 }

vtssMacsecStatisticsSecyRxSc2Sa3InPacketsLate OBJECT-TYPE
    SYNTAX      VTSSUnsigned64
    MAX-ACCESS  read-only
    STATUS      current
    DESCRIPTION
        "Number of late packets received on this Rx SA."
    ::= { vtssMacsecStatisticsSecyEntry 245 }

vtssMacsecStatisticsSecyRxSc2Sa4InPacketsOk OBJECT-TYPE
    SYNTAX      VTSSUnsigned64
    MAX-ACCESS  read-only
    STATUS      current
    DESCRIPTION
        "Number of OK packets received on this Rx SA."
    ::= { vtssMacsecStatisticsSecyEntry 256 }

vtssMacsecStatisticsSecyRxSc2Sa4InPacketsInvalid OBJECT-TYPE
    SYNTAX      VTSSUnsigned64
    MAX-ACCESS  read-only
    STATUS      current
    DESCRIPTION
        "Number of invalid packets received on this Rx SA."
    ::= { vtssMacsecStatisticsSecyEntry 257 }

vtssMacsecStatisticsSecyRxSc2Sa4InPacketsNotValid OBJECT-TYPE
    SYNTAX      VTSSUnsigned64
    MAX-ACCESS  read-only
    STATUS      current
    DESCRIPTION
        "Number of not valid packets received on this Rx SA."
    ::= { vtssMacsecStatisticsSecyEntry 258 }

vtssMacsecStatisticsSecyRxSc2Sa4InPacketsNotUsingSa OBJECT-TYPE
    SYNTAX      VTSSUnsigned64
    MAX-ACCESS  read-only
    STATUS      current
    DESCRIPTION
        "Number of packets not using SA received on this Rx SA."
    ::= { vtssMacsecStatisticsSecyEntry 259 }

vtssMacsecStatisticsSecyRxSc2Sa4InPacketsUnusedSa OBJECT-TYPE
    SYNTAX      VTSSUnsigned64
    MAX-ACCESS  read-only
    STATUS      current
    DESCRIPTION
        "Number of packets with unused SA received on this Rx SA."
    ::= { vtssMacsecStatisticsSecyEntry 260 }

vtssMacsecStatisticsSecyRxSc2Sa4InPacketsUnchecked OBJECT-TYPE
    SYNTAX      VTSSUnsigned64
    MAX-ACCESS  read-only
    STATUS      current
    DESCRIPTION
        "Number of unchecked packets received on this Rx SA."
    ::= { vtssMacsecStatisticsSecyEntry 261 }

vtssMacsecStatisticsSecyRxSc2Sa4InPacketsDelayed OBJECT-TYPE
    SYNTAX      VTSSUnsigned64
    MAX-ACCESS  read-only
    STATUS      current
    DESCRIPTION
        "Number of delayed packets received on this Rx SA."
    ::= { vtssMacsecStatisticsSecyEntry 262 }

vtssMacsecStatisticsSecyRxSc2Sa4InPacketsLate OBJECT-TYPE
    SYNTAX      VTSSUnsigned64
    MAX-ACCESS  read-only
    STATUS      current
    DESCRIPTION
        "Number of late packets received on this Rx SA."
    ::= { vtssMacsecStatisticsSecyEntry 263 }

vtssMacsecStatisticsSecyRxSc3InPacketsUnchecked OBJECT-TYPE
    SYNTAX      VTSSUnsigned64
    MAX-ACCESS  read-only
    STATUS      current
    DESCRIPTION
        "Number of unchecked packets received on this Rx SC."
    ::= { vtssMacsecStatisticsSecyEntry 274 }

vtssMacsecStatisticsSecyRxSc3InPacketsDelayed OBJECT-TYPE
    SYNTAX      VTSSUnsigned64
    MAX-ACCESS  read-only
    STATUS      current
    DESCRIPTION
        "Number of delayed packets received on this Rx SC."
    ::= { vtssMacsecStatisticsSecyEntry 275 }

vtssMacsecStatisticsSecyRxSc3InPacketsLate OBJECT-TYPE
    SYNTAX      VTSSUnsigned64
    MAX-ACCESS  read-only
    STATUS      current
    DESCRIPTION
        "Number of late packets received on this Rx SC."
    ::= { vtssMacsecStatisticsSecyEntry 276 }

vtssMacsecStatisticsSecyRxSc3InPacketsOk OBJECT-TYPE
    SYNTAX      VTSSUnsigned64
    MAX-ACCESS  read-only
    STATUS      current
    DESCRIPTION
        "Number of OK packets received on this Rx SC."
    ::= { vtssMacsecStatisticsSecyEntry 277 }

vtssMacsecStatisticsSecyRxSc3InPacketsInvalid OBJECT-TYPE
    SYNTAX      VTSSUnsigned64
    MAX-ACCESS  read-only
    STATUS      current
    DESCRIPTION
        "Number of invalid packets received on this Rx SC."
    ::= { vtssMacsecStatisticsSecyEntry 278 }

vtssMacsecStatisticsSecyRxSc3InPacketsNotValid OBJECT-TYPE
    SYNTAX      VTSSUnsigned64
    MAX-ACCESS  read-only
    STATUS      current
    DESCRIPTION
        "Number of not valid packets received on this Rx SC."
    ::= { vtssMacsecStatisticsSecyEntry 279 }

vtssMacsecStatisticsSecyRxSc3InPacketsNotUsingSa OBJECT-TYPE
    SYNTAX      VTSSUnsigned64
    MAX-ACCESS  read-only
    STATUS      current
    DESCRIPTION
        "Number of packets not using SA received on this Rx SC."
    ::= { vtssMacsecStatisticsSecyEntry 280 }

vtssMacsecStatisticsSecyRxSc3InPacketsUnusedSa OBJECT-TYPE
    SYNTAX      VTSSUnsigned64
    MAX-ACCESS  read-only
    STATUS      current
    DESCRIPTION
        "Number of packets with unused SA received on this Rx SC."
    ::= { vtssMacsecStatisticsSecyEntry 281 }

vtssMacsecStatisticsSecyRxSc3InOctetsValidated OBJECT-TYPE
    SYNTAX      VTSSUnsigned64
    MAX-ACCESS  read-only
    STATUS      current
    DESCRIPTION
        "Number of validated octets received on this Rx SC."
    ::= { vtssMacsecStatisticsSecyEntry 282 }

vtssMacsecStatisticsSecyRxSc3InOctetsDecrypted OBJECT-TYPE
    SYNTAX      VTSSUnsigned64
    MAX-ACCESS  read-only
    STATUS      current
    DESCRIPTION
        "Number of decrypted octets received on this Rx SC."
    ::= { vtssMacsecStatisticsSecyEntry 283 }

vtssMacsecStatisticsSecyRxSc3Sa1InPacketsOk OBJECT-TYPE
    SYNTAX      VTSSUnsigned64
    MAX-ACCESS  read-only
    STATUS      current
    DESCRIPTION
        "Number of OK packets received on this Rx SA."
    ::= { vtssMacsecStatisticsSecyEntry 294 }

vtssMacsecStatisticsSecyRxSc3Sa1InPacketsInvalid OBJECT-TYPE
    SYNTAX      VTSSUnsigned64
    MAX-ACCESS  read-only
    STATUS      current
    DESCRIPTION
        "Number of invalid packets received on this Rx SA."
    ::= { vtssMacsecStatisticsSecyEntry 295 }

vtssMacsecStatisticsSecyRxSc3Sa1InPacketsNotValid OBJECT-TYPE
    SYNTAX      VTSSUnsigned64
    MAX-ACCESS  read-only
    STATUS      current
    DESCRIPTION
        "Number of not valid packets received on this Rx SA."
    ::= { vtssMacsecStatisticsSecyEntry 296 }

vtssMacsecStatisticsSecyRxSc3Sa1InPacketsNotUsingSa OBJECT-TYPE
    SYNTAX      VTSSUnsigned64
    MAX-ACCESS  read-only
    STATUS      current
    DESCRIPTION
        "Number of packets not using SA received on this Rx SA."
    ::= { vtssMacsecStatisticsSecyEntry 297 }

vtssMacsecStatisticsSecyRxSc3Sa1InPacketsUnusedSa OBJECT-TYPE
    SYNTAX      VTSSUnsigned64
    MAX-ACCESS  read-only
    STATUS      current
    DESCRIPTION
        "Number of packets with unused SA received on this Rx SA."
    ::= { vtssMacsecStatisticsSecyEntry 298 }

vtssMacsecStatisticsSecyRxSc3Sa1InPacketsUnchecked OBJECT-TYPE
    SYNTAX      VTSSUnsigned64
    MAX-ACCESS  read-only
    STATUS      current
    DESCRIPTION
        "Number of unchecked packets received on this Rx SA."
    ::= { vtssMacsecStatisticsSecyEntry 299 }

vtssMacsecStatisticsSecyRxSc3Sa1InPacketsDelayed OBJECT-TYPE
    SYNTAX      VTSSUnsigned64
    MAX-ACCESS  read-only
    STATUS      current
    DESCRIPTION
        "Number of delayed packets received on this Rx SA."
    ::= { vtssMacsecStatisticsSecyEntry 300 }

vtssMacsecStatisticsSecyRxSc3Sa1InPacketsLate OBJECT-TYPE
    SYNTAX      VTSSUnsigned64
    MAX-ACCESS  read-only
    STATUS      current
    DESCRIPTION
        "Number of late packets received on this Rx SA."
    ::= { vtssMacsecStatisticsSecyEntry 301 }

vtssMacsecStatisticsSecyRxSc3Sa2InPacketsOk OBJECT-TYPE
    SYNTAX      VTSSUnsigned64
    MAX-ACCESS  read-only
    STATUS      current
    DESCRIPTION
        "Number of OK packets received on this Rx SA."
    ::= { vtssMacsecStatisticsSecyEntry 312 }

vtssMacsecStatisticsSecyRxSc3Sa2InPacketsInvalid OBJECT-TYPE
    SYNTAX      VTSSUnsigned64
    MAX-ACCESS  read-only
    STATUS      current
    DESCRIPTION
        "Number of invalid packets received on this Rx SA."
    ::= { vtssMacsecStatisticsSecyEntry 313 }

vtssMacsecStatisticsSecyRxSc3Sa2InPacketsNotValid OBJECT-TYPE
    SYNTAX      VTSSUnsigned64
    MAX-ACCESS  read-only
    STATUS      current
    DESCRIPTION
        "Number of not valid packets received on this Rx SA."
    ::= { vtssMacsecStatisticsSecyEntry 314 }

vtssMacsecStatisticsSecyRxSc3Sa2InPacketsNotUsingSa OBJECT-TYPE
    SYNTAX      VTSSUnsigned64
    MAX-ACCESS  read-only
    STATUS      current
    DESCRIPTION
        "Number of packets not using SA received on this Rx SA."
    ::= { vtssMacsecStatisticsSecyEntry 315 }

vtssMacsecStatisticsSecyRxSc3Sa2InPacketsUnusedSa OBJECT-TYPE
    SYNTAX      VTSSUnsigned64
    MAX-ACCESS  read-only
    STATUS      current
    DESCRIPTION
        "Number of packets with unused SA received on this Rx SA."
    ::= { vtssMacsecStatisticsSecyEntry 316 }

vtssMacsecStatisticsSecyRxSc3Sa2InPacketsUnchecked OBJECT-TYPE
    SYNTAX      VTSSUnsigned64
    MAX-ACCESS  read-only
    STATUS      current
    DESCRIPTION
        "Number of unchecked packets received on this Rx SA."
    ::= { vtssMacsecStatisticsSecyEntry 317 }

vtssMacsecStatisticsSecyRxSc3Sa2InPacketsDelayed OBJECT-TYPE
    SYNTAX      VTSSUnsigned64
    MAX-ACCESS  read-only
    STATUS      current
    DESCRIPTION
        "Number of delayed packets received on this Rx SA."
    ::= { vtssMacsecStatisticsSecyEntry 318 }

vtssMacsecStatisticsSecyRxSc3Sa2InPacketsLate OBJECT-TYPE
    SYNTAX      VTSSUnsigned64
    MAX-ACCESS  read-only
    STATUS      current
    DESCRIPTION
        "Number of late packets received on this Rx SA."
    ::= { vtssMacsecStatisticsSecyEntry 319 }

vtssMacsecStatisticsSecyRxSc3Sa3InPacketsOk OBJECT-TYPE
    SYNTAX      VTSSUnsigned64
    MAX-ACCESS  read-only
    STATUS      current
    DESCRIPTION
        "Number of OK packets received on this Rx SA."
    ::= { vtssMacsecStatisticsSecyEntry 330 }

vtssMacsecStatisticsSecyRxSc3Sa3InPacketsInvalid OBJECT-TYPE
    SYNTAX      VTSSUnsigned64
    MAX-ACCESS  read-only
    STATUS      current
    DESCRIPTION
        "Number of invalid packets received on this Rx SA."
    ::= { vtssMacsecStatisticsSecyEntry 331 }

vtssMacsecStatisticsSecyRxSc3Sa3InPacketsNotValid OBJECT-TYPE
    SYNTAX      VTSSUnsigned64
    MAX-ACCESS  read-only
    STATUS      current
    DESCRIPTION
        "Number of not valid packets received on this Rx SA."
    ::= { vtssMacsecStatisticsSecyEntry 332 }

vtssMacsecStatisticsSecyRxSc3Sa3InPacketsNotUsingSa OBJECT-TYPE
    SYNTAX      VTSSUnsigned64
    MAX-ACCESS  read-only
    STATUS      current
    DESCRIPTION
        "Number of packets not using SA received on this Rx SA."
    ::= { vtssMacsecStatisticsSecyEntry 333 }

vtssMacsecStatisticsSecyRxSc3Sa3InPacketsUnusedSa OBJECT-TYPE
    SYNTAX      VTSSUnsigned64
    MAX-ACCESS  read-only
    STATUS      current
    DESCRIPTION
        "Number of packets with unused SA received on this Rx SA."
    ::= { vtssMacsecStatisticsSecyEntry 334 }

vtssMacsecStatisticsSecyRxSc3Sa3InPacketsUnchecked OBJECT-TYPE
    SYNTAX      VTSSUnsigned64
    MAX-ACCESS  read-only
    STATUS      current
    DESCRIPTION
        "Number of unchecked packets received on this Rx SA."
    ::= { vtssMacsecStatisticsSecyEntry 335 }

vtssMacsecStatisticsSecyRxSc3Sa3InPacketsDelayed OBJECT-TYPE
    SYNTAX      VTSSUnsigned64
    MAX-ACCESS  read-only
    STATUS      current
    DESCRIPTION
        "Number of delayed packets received on this Rx SA."
    ::= { vtssMacsecStatisticsSecyEntry 336 }

vtssMacsecStatisticsSecyRxSc3Sa3InPacketsLate OBJECT-TYPE
    SYNTAX      VTSSUnsigned64
    MAX-ACCESS  read-only
    STATUS      current
    DESCRIPTION
        "Number of late packets received on this Rx SA."
    ::= { vtssMacsecStatisticsSecyEntry 337 }

vtssMacsecStatisticsSecyRxSc3Sa4InPacketsOk OBJECT-TYPE
    SYNTAX      VTSSUnsigned64
    MAX-ACCESS  read-only
    STATUS      current
    DESCRIPTION
        "Number of OK packets received on this Rx SA."
    ::= { vtssMacsecStatisticsSecyEntry 348 }

vtssMacsecStatisticsSecyRxSc3Sa4InPacketsInvalid OBJECT-TYPE
    SYNTAX      VTSSUnsigned64
    MAX-ACCESS  read-only
    STATUS      current
    DESCRIPTION
        "Number of invalid packets received on this Rx SA."
    ::= { vtssMacsecStatisticsSecyEntry 349 }

vtssMacsecStatisticsSecyRxSc3Sa4InPacketsNotValid OBJECT-TYPE
    SYNTAX      VTSSUnsigned64
    MAX-ACCESS  read-only
    STATUS      current
    DESCRIPTION
        "Number of not valid packets received on this Rx SA."
    ::= { vtssMacsecStatisticsSecyEntry 350 }

vtssMacsecStatisticsSecyRxSc3Sa4InPacketsNotUsingSa OBJECT-TYPE
    SYNTAX      VTSSUnsigned64
    MAX-ACCESS  read-only
    STATUS      current
    DESCRIPTION
        "Number of packets not using SA received on this Rx SA."
    ::= { vtssMacsecStatisticsSecyEntry 351 }

vtssMacsecStatisticsSecyRxSc3Sa4InPacketsUnusedSa OBJECT-TYPE
    SYNTAX      VTSSUnsigned64
    MAX-ACCESS  read-only
    STATUS      current
    DESCRIPTION
        "Number of packets with unused SA received on this Rx SA."
    ::= { vtssMacsecStatisticsSecyEntry 352 }

vtssMacsecStatisticsSecyRxSc3Sa4InPacketsUnchecked OBJECT-TYPE
    SYNTAX      VTSSUnsigned64
    MAX-ACCESS  read-only
    STATUS      current
    DESCRIPTION
        "Number of unchecked packets received on this Rx SA."
    ::= { vtssMacsecStatisticsSecyEntry 353 }

vtssMacsecStatisticsSecyRxSc3Sa4InPacketsDelayed OBJECT-TYPE
    SYNTAX      VTSSUnsigned64
    MAX-ACCESS  read-only
    STATUS      current
    DESCRIPTION
        "Number of delayed packets received on this Rx SA."
    ::= { vtssMacsecStatisticsSecyEntry 354 }

vtssMacsecStatisticsSecyRxSc3Sa4InPacketsLate OBJECT-TYPE
    SYNTAX      VTSSUnsigned64
    MAX-ACCESS  read-only
    STATUS      current
    DESCRIPTION
        "Number of late packets received on this Rx SA."
    ::= { vtssMacsecStatisticsSecyEntry 355 }

vtssMacsecStatisticsSecyRxSc4InPacketsUnchecked OBJECT-TYPE
    SYNTAX      VTSSUnsigned64
    MAX-ACCESS  read-only
    STATUS      current
    DESCRIPTION
        "Number of unchecked packets received on this Rx SC."
    ::= { vtssMacsecStatisticsSecyEntry 366 }

vtssMacsecStatisticsSecyRxSc4InPacketsDelayed OBJECT-TYPE
    SYNTAX      VTSSUnsigned64
    MAX-ACCESS  read-only
    STATUS      current
    DESCRIPTION
        "Number of delayed packets received on this Rx SC."
    ::= { vtssMacsecStatisticsSecyEntry 367 }

vtssMacsecStatisticsSecyRxSc4InPacketsLate OBJECT-TYPE
    SYNTAX      VTSSUnsigned64
    MAX-ACCESS  read-only
    STATUS      current
    DESCRIPTION
        "Number of late packets received on this Rx SC."
    ::= { vtssMacsecStatisticsSecyEntry 368 }

vtssMacsecStatisticsSecyRxSc4InPacketsOk OBJECT-TYPE
    SYNTAX      VTSSUnsigned64
    MAX-ACCESS  read-only
    STATUS      current
    DESCRIPTION
        "Number of OK packets received on this Rx SC."
    ::= { vtssMacsecStatisticsSecyEntry 369 }

vtssMacsecStatisticsSecyRxSc4InPacketsInvalid OBJECT-TYPE
    SYNTAX      VTSSUnsigned64
    MAX-ACCESS  read-only
    STATUS      current
    DESCRIPTION
        "Number of invalid packets received on this Rx SC."
    ::= { vtssMacsecStatisticsSecyEntry 370 }

vtssMacsecStatisticsSecyRxSc4InPacketsNotValid OBJECT-TYPE
    SYNTAX      VTSSUnsigned64
    MAX-ACCESS  read-only
    STATUS      current
    DESCRIPTION
        "Number of not valid packets received on this Rx SC."
    ::= { vtssMacsecStatisticsSecyEntry 371 }

vtssMacsecStatisticsSecyRxSc4InPacketsNotUsingSa OBJECT-TYPE
    SYNTAX      VTSSUnsigned64
    MAX-ACCESS  read-only
    STATUS      current
    DESCRIPTION
        "Number of packets not using SA received on this Rx SC."
    ::= { vtssMacsecStatisticsSecyEntry 372 }

vtssMacsecStatisticsSecyRxSc4InPacketsUnusedSa OBJECT-TYPE
    SYNTAX      VTSSUnsigned64
    MAX-ACCESS  read-only
    STATUS      current
    DESCRIPTION
        "Number of packets with unused SA received on this Rx SC."
    ::= { vtssMacsecStatisticsSecyEntry 373 }

vtssMacsecStatisticsSecyRxSc4InOctetsValidated OBJECT-TYPE
    SYNTAX      VTSSUnsigned64
    MAX-ACCESS  read-only
    STATUS      current
    DESCRIPTION
        "Number of validated octets received on this Rx SC."
    ::= { vtssMacsecStatisticsSecyEntry 374 }

vtssMacsecStatisticsSecyRxSc4InOctetsDecrypted OBJECT-TYPE
    SYNTAX      VTSSUnsigned64
    MAX-ACCESS  read-only
    STATUS      current
    DESCRIPTION
        "Number of decrypted octets received on this Rx SC."
    ::= { vtssMacsecStatisticsSecyEntry 375 }

vtssMacsecStatisticsSecyRxSc4Sa1InPacketsOk OBJECT-TYPE
    SYNTAX      VTSSUnsigned64
    MAX-ACCESS  read-only
    STATUS      current
    DESCRIPTION
        "Number of OK packets received on this Rx SA."
    ::= { vtssMacsecStatisticsSecyEntry 386 }

vtssMacsecStatisticsSecyRxSc4Sa1InPacketsInvalid OBJECT-TYPE
    SYNTAX      VTSSUnsigned64
    MAX-ACCESS  read-only
    STATUS      current
    DESCRIPTION
        "Number of invalid packets received on this Rx SA."
    ::= { vtssMacsecStatisticsSecyEntry 387 }

vtssMacsecStatisticsSecyRxSc4Sa1InPacketsNotValid OBJECT-TYPE
    SYNTAX      VTSSUnsigned64
    MAX-ACCESS  read-only
    STATUS      current
    DESCRIPTION
        "Number of not valid packets received on this Rx SA."
    ::= { vtssMacsecStatisticsSecyEntry 388 }

vtssMacsecStatisticsSecyRxSc4Sa1InPacketsNotUsingSa OBJECT-TYPE
    SYNTAX      VTSSUnsigned64
    MAX-ACCESS  read-only
    STATUS      current
    DESCRIPTION
        "Number of packets not using SA received on this Rx SA."
    ::= { vtssMacsecStatisticsSecyEntry 389 }

vtssMacsecStatisticsSecyRxSc4Sa1InPacketsUnusedSa OBJECT-TYPE
    SYNTAX      VTSSUnsigned64
    MAX-ACCESS  read-only
    STATUS      current
    DESCRIPTION
        "Number of packets with unused SA received on this Rx SA."
    ::= { vtssMacsecStatisticsSecyEntry 390 }

vtssMacsecStatisticsSecyRxSc4Sa1InPacketsUnchecked OBJECT-TYPE
    SYNTAX      VTSSUnsigned64
    MAX-ACCESS  read-only
    STATUS      current
    DESCRIPTION
        "Number of unchecked packets received on this Rx SA."
    ::= { vtssMacsecStatisticsSecyEntry 391 }

vtssMacsecStatisticsSecyRxSc4Sa1InPacketsDelayed OBJECT-TYPE
    SYNTAX      VTSSUnsigned64
    MAX-ACCESS  read-only
    STATUS      current
    DESCRIPTION
        "Number of delayed packets received on this Rx SA."
    ::= { vtssMacsecStatisticsSecyEntry 392 }

vtssMacsecStatisticsSecyRxSc4Sa1InPacketsLate OBJECT-TYPE
    SYNTAX      VTSSUnsigned64
    MAX-ACCESS  read-only
    STATUS      current
    DESCRIPTION
        "Number of late packets received on this Rx SA."
    ::= { vtssMacsecStatisticsSecyEntry 393 }

vtssMacsecStatisticsSecyRxSc4Sa2InPacketsOk OBJECT-TYPE
    SYNTAX      VTSSUnsigned64
    MAX-ACCESS  read-only
    STATUS      current
    DESCRIPTION
        "Number of OK packets received on this Rx SA."
    ::= { vtssMacsecStatisticsSecyEntry 404 }

vtssMacsecStatisticsSecyRxSc4Sa2InPacketsInvalid OBJECT-TYPE
    SYNTAX      VTSSUnsigned64
    MAX-ACCESS  read-only
    STATUS      current
    DESCRIPTION
        "Number of invalid packets received on this Rx SA."
    ::= { vtssMacsecStatisticsSecyEntry 405 }

vtssMacsecStatisticsSecyRxSc4Sa2InPacketsNotValid OBJECT-TYPE
    SYNTAX      VTSSUnsigned64
    MAX-ACCESS  read-only
    STATUS      current
    DESCRIPTION
        "Number of not valid packets received on this Rx SA."
    ::= { vtssMacsecStatisticsSecyEntry 406 }

vtssMacsecStatisticsSecyRxSc4Sa2InPacketsNotUsingSa OBJECT-TYPE
    SYNTAX      VTSSUnsigned64
    MAX-ACCESS  read-only
    STATUS      current
    DESCRIPTION
        "Number of packets not using SA received on this Rx SA."
    ::= { vtssMacsecStatisticsSecyEntry 407 }

vtssMacsecStatisticsSecyRxSc4Sa2InPacketsUnusedSa OBJECT-TYPE
    SYNTAX      VTSSUnsigned64
    MAX-ACCESS  read-only
    STATUS      current
    DESCRIPTION
        "Number of packets with unused SA received on this Rx SA."
    ::= { vtssMacsecStatisticsSecyEntry 408 }

vtssMacsecStatisticsSecyRxSc4Sa2InPacketsUnchecked OBJECT-TYPE
    SYNTAX      VTSSUnsigned64
    MAX-ACCESS  read-only
    STATUS      current
    DESCRIPTION
        "Number of unchecked packets received on this Rx SA."
    ::= { vtssMacsecStatisticsSecyEntry 409 }

vtssMacsecStatisticsSecyRxSc4Sa2InPacketsDelayed OBJECT-TYPE
    SYNTAX      VTSSUnsigned64
    MAX-ACCESS  read-only
    STATUS      current
    DESCRIPTION
        "Number of delayed packets received on this Rx SA."
    ::= { vtssMacsecStatisticsSecyEntry 410 }

vtssMacsecStatisticsSecyRxSc4Sa2InPacketsLate OBJECT-TYPE
    SYNTAX      VTSSUnsigned64
    MAX-ACCESS  read-only
    STATUS      current
    DESCRIPTION
        "Number of late packets received on this Rx SA."
    ::= { vtssMacsecStatisticsSecyEntry 411 }

vtssMacsecStatisticsSecyRxSc4Sa3InPacketsOk OBJECT-TYPE
    SYNTAX      VTSSUnsigned64
    MAX-ACCESS  read-only
    STATUS      current
    DESCRIPTION
        "Number of OK packets received on this Rx SA."
    ::= { vtssMacsecStatisticsSecyEntry 422 }

vtssMacsecStatisticsSecyRxSc4Sa3InPacketsInvalid OBJECT-TYPE
    SYNTAX      VTSSUnsigned64
    MAX-ACCESS  read-only
    STATUS      current
    DESCRIPTION
        "Number of invalid packets received on this Rx SA."
    ::= { vtssMacsecStatisticsSecyEntry 423 }

vtssMacsecStatisticsSecyRxSc4Sa3InPacketsNotValid OBJECT-TYPE
    SYNTAX      VTSSUnsigned64
    MAX-ACCESS  read-only
    STATUS      current
    DESCRIPTION
        "Number of not valid packets received on this Rx SA."
    ::= { vtssMacsecStatisticsSecyEntry 424 }

vtssMacsecStatisticsSecyRxSc4Sa3InPacketsNotUsingSa OBJECT-TYPE
    SYNTAX      VTSSUnsigned64
    MAX-ACCESS  read-only
    STATUS      current
    DESCRIPTION
        "Number of packets not using SA received on this Rx SA."
    ::= { vtssMacsecStatisticsSecyEntry 425 }

vtssMacsecStatisticsSecyRxSc4Sa3InPacketsUnusedSa OBJECT-TYPE
    SYNTAX      VTSSUnsigned64
    MAX-ACCESS  read-only
    STATUS      current
    DESCRIPTION
        "Number of packets with unused SA received on this Rx SA."
    ::= { vtssMacsecStatisticsSecyEntry 426 }

vtssMacsecStatisticsSecyRxSc4Sa3InPacketsUnchecked OBJECT-TYPE
    SYNTAX      VTSSUnsigned64
    MAX-ACCESS  read-only
    STATUS      current
    DESCRIPTION
        "Number of unchecked packets received on this Rx SA."
    ::= { vtssMacsecStatisticsSecyEntry 427 }

vtssMacsecStatisticsSecyRxSc4Sa3InPacketsDelayed OBJECT-TYPE
    SYNTAX      VTSSUnsigned64
    MAX-ACCESS  read-only
    STATUS      current
    DESCRIPTION
        "Number of delayed packets received on this Rx SA."
    ::= { vtssMacsecStatisticsSecyEntry 428 }

vtssMacsecStatisticsSecyRxSc4Sa3InPacketsLate OBJECT-TYPE
    SYNTAX      VTSSUnsigned64
    MAX-ACCESS  read-only
    STATUS      current
    DESCRIPTION
        "Number of late packets received on this Rx SA."
    ::= { vtssMacsecStatisticsSecyEntry 429 }

vtssMacsecStatisticsSecyRxSc4Sa4InPacketsOk OBJECT-TYPE
    SYNTAX      VTSSUnsigned64
    MAX-ACCESS  read-only
    STATUS      current
    DESCRIPTION
        "Number of OK packets received on this Rx SA."
    ::= { vtssMacsecStatisticsSecyEntry 440 }

vtssMacsecStatisticsSecyRxSc4Sa4InPacketsInvalid OBJECT-TYPE
    SYNTAX      VTSSUnsigned64
    MAX-ACCESS  read-only
    STATUS      current
    DESCRIPTION
        "Number of invalid packets received on this Rx SA."
    ::= { vtssMacsecStatisticsSecyEntry 441 }

vtssMacsecStatisticsSecyRxSc4Sa4InPacketsNotValid OBJECT-TYPE
    SYNTAX      VTSSUnsigned64
    MAX-ACCESS  read-only
    STATUS      current
    DESCRIPTION
        "Number of not valid packets received on this Rx SA."
    ::= { vtssMacsecStatisticsSecyEntry 442 }

vtssMacsecStatisticsSecyRxSc4Sa4InPacketsNotUsingSa OBJECT-TYPE
    SYNTAX      VTSSUnsigned64
    MAX-ACCESS  read-only
    STATUS      current
    DESCRIPTION
        "Number of packets not using SA received on this Rx SA."
    ::= { vtssMacsecStatisticsSecyEntry 443 }

vtssMacsecStatisticsSecyRxSc4Sa4InPacketsUnusedSa OBJECT-TYPE
    SYNTAX      VTSSUnsigned64
    MAX-ACCESS  read-only
    STATUS      current
    DESCRIPTION
        "Number of packets with unused SA received on this Rx SA."
    ::= { vtssMacsecStatisticsSecyEntry 444 }

vtssMacsecStatisticsSecyRxSc4Sa4InPacketsUnchecked OBJECT-TYPE
    SYNTAX      VTSSUnsigned64
    MAX-ACCESS  read-only
    STATUS      current
    DESCRIPTION
        "Number of unchecked packets received on this Rx SA."
    ::= { vtssMacsecStatisticsSecyEntry 445 }

vtssMacsecStatisticsSecyRxSc4Sa4InPacketsDelayed OBJECT-TYPE
    SYNTAX      VTSSUnsigned64
    MAX-ACCESS  read-only
    STATUS      current
    DESCRIPTION
        "Number of delayed packets received on this Rx SA."
    ::= { vtssMacsecStatisticsSecyEntry 446 }

vtssMacsecStatisticsSecyRxSc4Sa4InPacketsLate OBJECT-TYPE
    SYNTAX      VTSSUnsigned64
    MAX-ACCESS  read-only
    STATUS      current
    DESCRIPTION
        "Number of late packets received on this Rx SA."
    ::= { vtssMacsecStatisticsSecyEntry 447 }

vtssMacsecStatisticsSecyRxSc5InPacketsUnchecked OBJECT-TYPE
    SYNTAX      VTSSUnsigned64
    MAX-ACCESS  read-only
    STATUS      current
    DESCRIPTION
        "Number of unchecked packets received on this Rx SC."
    ::= { vtssMacsecStatisticsSecyEntry 458 }

vtssMacsecStatisticsSecyRxSc5InPacketsDelayed OBJECT-TYPE
    SYNTAX      VTSSUnsigned64
    MAX-ACCESS  read-only
    STATUS      current
    DESCRIPTION
        "Number of delayed packets received on this Rx SC."
    ::= { vtssMacsecStatisticsSecyEntry 459 }

vtssMacsecStatisticsSecyRxSc5InPacketsLate OBJECT-TYPE
    SYNTAX      VTSSUnsigned64
    MAX-ACCESS  read-only
    STATUS      current
    DESCRIPTION
        "Number of late packets received on this Rx SC."
    ::= { vtssMacsecStatisticsSecyEntry 460 }

vtssMacsecStatisticsSecyRxSc5InPacketsOk OBJECT-TYPE
    SYNTAX      VTSSUnsigned64
    MAX-ACCESS  read-only
    STATUS      current
    DESCRIPTION
        "Number of OK packets received on this Rx SC."
    ::= { vtssMacsecStatisticsSecyEntry 461 }

vtssMacsecStatisticsSecyRxSc5InPacketsInvalid OBJECT-TYPE
    SYNTAX      VTSSUnsigned64
    MAX-ACCESS  read-only
    STATUS      current
    DESCRIPTION
        "Number of invalid packets received on this Rx SC."
    ::= { vtssMacsecStatisticsSecyEntry 462 }

vtssMacsecStatisticsSecyRxSc5InPacketsNotValid OBJECT-TYPE
    SYNTAX      VTSSUnsigned64
    MAX-ACCESS  read-only
    STATUS      current
    DESCRIPTION
        "Number of not valid packets received on this Rx SC."
    ::= { vtssMacsecStatisticsSecyEntry 463 }

vtssMacsecStatisticsSecyRxSc5InPacketsNotUsingSa OBJECT-TYPE
    SYNTAX      VTSSUnsigned64
    MAX-ACCESS  read-only
    STATUS      current
    DESCRIPTION
        "Number of packets not using SA received on this Rx SC."
    ::= { vtssMacsecStatisticsSecyEntry 464 }

vtssMacsecStatisticsSecyRxSc5InPacketsUnusedSa OBJECT-TYPE
    SYNTAX      VTSSUnsigned64
    MAX-ACCESS  read-only
    STATUS      current
    DESCRIPTION
        "Number of packets with unused SA received on this Rx SC."
    ::= { vtssMacsecStatisticsSecyEntry 465 }

vtssMacsecStatisticsSecyRxSc5InOctetsValidated OBJECT-TYPE
    SYNTAX      VTSSUnsigned64
    MAX-ACCESS  read-only
    STATUS      current
    DESCRIPTION
        "Number of validated octets received on this Rx SC."
    ::= { vtssMacsecStatisticsSecyEntry 466 }

vtssMacsecStatisticsSecyRxSc5InOctetsDecrypted OBJECT-TYPE
    SYNTAX      VTSSUnsigned64
    MAX-ACCESS  read-only
    STATUS      current
    DESCRIPTION
        "Number of decrypted octets received on this Rx SC."
    ::= { vtssMacsecStatisticsSecyEntry 467 }

vtssMacsecStatisticsSecyRxSc5Sa1InPacketsOk OBJECT-TYPE
    SYNTAX      VTSSUnsigned64
    MAX-ACCESS  read-only
    STATUS      current
    DESCRIPTION
        "Number of OK packets received on this Rx SA."
    ::= { vtssMacsecStatisticsSecyEntry 478 }

vtssMacsecStatisticsSecyRxSc5Sa1InPacketsInvalid OBJECT-TYPE
    SYNTAX      VTSSUnsigned64
    MAX-ACCESS  read-only
    STATUS      current
    DESCRIPTION
        "Number of invalid packets received on this Rx SA."
    ::= { vtssMacsecStatisticsSecyEntry 479 }

vtssMacsecStatisticsSecyRxSc5Sa1InPacketsNotValid OBJECT-TYPE
    SYNTAX      VTSSUnsigned64
    MAX-ACCESS  read-only
    STATUS      current
    DESCRIPTION
        "Number of not valid packets received on this Rx SA."
    ::= { vtssMacsecStatisticsSecyEntry 480 }

vtssMacsecStatisticsSecyRxSc5Sa1InPacketsNotUsingSa OBJECT-TYPE
    SYNTAX      VTSSUnsigned64
    MAX-ACCESS  read-only
    STATUS      current
    DESCRIPTION
        "Number of packets not using SA received on this Rx SA."
    ::= { vtssMacsecStatisticsSecyEntry 481 }

vtssMacsecStatisticsSecyRxSc5Sa1InPacketsUnusedSa OBJECT-TYPE
    SYNTAX      VTSSUnsigned64
    MAX-ACCESS  read-only
    STATUS      current
    DESCRIPTION
        "Number of packets with unused SA received on this Rx SA."
    ::= { vtssMacsecStatisticsSecyEntry 482 }

vtssMacsecStatisticsSecyRxSc5Sa1InPacketsUnchecked OBJECT-TYPE
    SYNTAX      VTSSUnsigned64
    MAX-ACCESS  read-only
    STATUS      current
    DESCRIPTION
        "Number of unchecked packets received on this Rx SA."
    ::= { vtssMacsecStatisticsSecyEntry 483 }

vtssMacsecStatisticsSecyRxSc5Sa1InPacketsDelayed OBJECT-TYPE
    SYNTAX      VTSSUnsigned64
    MAX-ACCESS  read-only
    STATUS      current
    DESCRIPTION
        "Number of delayed packets received on this Rx SA."
    ::= { vtssMacsecStatisticsSecyEntry 484 }

vtssMacsecStatisticsSecyRxSc5Sa1InPacketsLate OBJECT-TYPE
    SYNTAX      VTSSUnsigned64
    MAX-ACCESS  read-only
    STATUS      current
    DESCRIPTION
        "Number of late packets received on this Rx SA."
    ::= { vtssMacsecStatisticsSecyEntry 485 }

vtssMacsecStatisticsSecyRxSc5Sa2InPacketsOk OBJECT-TYPE
    SYNTAX      VTSSUnsigned64
    MAX-ACCESS  read-only
    STATUS      current
    DESCRIPTION
        "Number of OK packets received on this Rx SA."
    ::= { vtssMacsecStatisticsSecyEntry 496 }

vtssMacsecStatisticsSecyRxSc5Sa2InPacketsInvalid OBJECT-TYPE
    SYNTAX      VTSSUnsigned64
    MAX-ACCESS  read-only
    STATUS      current
    DESCRIPTION
        "Number of invalid packets received on this Rx SA."
    ::= { vtssMacsecStatisticsSecyEntry 497 }

vtssMacsecStatisticsSecyRxSc5Sa2InPacketsNotValid OBJECT-TYPE
    SYNTAX      VTSSUnsigned64
    MAX-ACCESS  read-only
    STATUS      current
    DESCRIPTION
        "Number of not valid packets received on this Rx SA."
    ::= { vtssMacsecStatisticsSecyEntry 498 }

vtssMacsecStatisticsSecyRxSc5Sa2InPacketsNotUsingSa OBJECT-TYPE
    SYNTAX      VTSSUnsigned64
    MAX-ACCESS  read-only
    STATUS      current
    DESCRIPTION
        "Number of packets not using SA received on this Rx SA."
    ::= { vtssMacsecStatisticsSecyEntry 499 }

vtssMacsecStatisticsSecyRxSc5Sa2InPacketsUnusedSa OBJECT-TYPE
    SYNTAX      VTSSUnsigned64
    MAX-ACCESS  read-only
    STATUS      current
    DESCRIPTION
        "Number of packets with unused SA received on this Rx SA."
    ::= { vtssMacsecStatisticsSecyEntry 500 }

vtssMacsecStatisticsSecyRxSc5Sa2InPacketsUnchecked OBJECT-TYPE
    SYNTAX      VTSSUnsigned64
    MAX-ACCESS  read-only
    STATUS      current
    DESCRIPTION
        "Number of unchecked packets received on this Rx SA."
    ::= { vtssMacsecStatisticsSecyEntry 501 }

vtssMacsecStatisticsSecyRxSc5Sa2InPacketsDelayed OBJECT-TYPE
    SYNTAX      VTSSUnsigned64
    MAX-ACCESS  read-only
    STATUS      current
    DESCRIPTION
        "Number of delayed packets received on this Rx SA."
    ::= { vtssMacsecStatisticsSecyEntry 502 }

vtssMacsecStatisticsSecyRxSc5Sa2InPacketsLate OBJECT-TYPE
    SYNTAX      VTSSUnsigned64
    MAX-ACCESS  read-only
    STATUS      current
    DESCRIPTION
        "Number of late packets received on this Rx SA."
    ::= { vtssMacsecStatisticsSecyEntry 503 }

vtssMacsecStatisticsSecyRxSc5Sa3InPacketsOk OBJECT-TYPE
    SYNTAX      VTSSUnsigned64
    MAX-ACCESS  read-only
    STATUS      current
    DESCRIPTION
        "Number of OK packets received on this Rx SA."
    ::= { vtssMacsecStatisticsSecyEntry 514 }

vtssMacsecStatisticsSecyRxSc5Sa3InPacketsInvalid OBJECT-TYPE
    SYNTAX      VTSSUnsigned64
    MAX-ACCESS  read-only
    STATUS      current
    DESCRIPTION
        "Number of invalid packets received on this Rx SA."
    ::= { vtssMacsecStatisticsSecyEntry 515 }

vtssMacsecStatisticsSecyRxSc5Sa3InPacketsNotValid OBJECT-TYPE
    SYNTAX      VTSSUnsigned64
    MAX-ACCESS  read-only
    STATUS      current
    DESCRIPTION
        "Number of not valid packets received on this Rx SA."
    ::= { vtssMacsecStatisticsSecyEntry 516 }

vtssMacsecStatisticsSecyRxSc5Sa3InPacketsNotUsingSa OBJECT-TYPE
    SYNTAX      VTSSUnsigned64
    MAX-ACCESS  read-only
    STATUS      current
    DESCRIPTION
        "Number of packets not using SA received on this Rx SA."
    ::= { vtssMacsecStatisticsSecyEntry 517 }

vtssMacsecStatisticsSecyRxSc5Sa3InPacketsUnusedSa OBJECT-TYPE
    SYNTAX      VTSSUnsigned64
    MAX-ACCESS  read-only
    STATUS      current
    DESCRIPTION
        "Number of packets with unused SA received on this Rx SA."
    ::= { vtssMacsecStatisticsSecyEntry 518 }

vtssMacsecStatisticsSecyRxSc5Sa3InPacketsUnchecked OBJECT-TYPE
    SYNTAX      VTSSUnsigned64
    MAX-ACCESS  read-only
    STATUS      current
    DESCRIPTION
        "Number of unchecked packets received on this Rx SA."
    ::= { vtssMacsecStatisticsSecyEntry 519 }

vtssMacsecStatisticsSecyRxSc5Sa3InPacketsDelayed OBJECT-TYPE
    SYNTAX      VTSSUnsigned64
    MAX-ACCESS  read-only
    STATUS      current
    DESCRIPTION
        "Number of delayed packets received on this Rx SA."
    ::= { vtssMacsecStatisticsSecyEntry 520 }

vtssMacsecStatisticsSecyRxSc5Sa3InPacketsLate OBJECT-TYPE
    SYNTAX      VTSSUnsigned64
    MAX-ACCESS  read-only
    STATUS      current
    DESCRIPTION
        "Number of late packets received on this Rx SA."
    ::= { vtssMacsecStatisticsSecyEntry 521 }

vtssMacsecStatisticsSecyRxSc5Sa4InPacketsOk OBJECT-TYPE
    SYNTAX      VTSSUnsigned64
    MAX-ACCESS  read-only
    STATUS      current
    DESCRIPTION
        "Number of OK packets received on this Rx SA."
    ::= { vtssMacsecStatisticsSecyEntry 532 }

vtssMacsecStatisticsSecyRxSc5Sa4InPacketsInvalid OBJECT-TYPE
    SYNTAX      VTSSUnsigned64
    MAX-ACCESS  read-only
    STATUS      current
    DESCRIPTION
        "Number of invalid packets received on this Rx SA."
    ::= { vtssMacsecStatisticsSecyEntry 533 }

vtssMacsecStatisticsSecyRxSc5Sa4InPacketsNotValid OBJECT-TYPE
    SYNTAX      VTSSUnsigned64
    MAX-ACCESS  read-only
    STATUS      current
    DESCRIPTION
        "Number of not valid packets received on this Rx SA."
    ::= { vtssMacsecStatisticsSecyEntry 534 }

vtssMacsecStatisticsSecyRxSc5Sa4InPacketsNotUsingSa OBJECT-TYPE
    SYNTAX      VTSSUnsigned64
    MAX-ACCESS  read-only
    STATUS      current
    DESCRIPTION
        "Number of packets not using SA received on this Rx SA."
    ::= { vtssMacsecStatisticsSecyEntry 535 }

vtssMacsecStatisticsSecyRxSc5Sa4InPacketsUnusedSa OBJECT-TYPE
    SYNTAX      VTSSUnsigned64
    MAX-ACCESS  read-only
    STATUS      current
    DESCRIPTION
        "Number of packets with unused SA received on this Rx SA."
    ::= { vtssMacsecStatisticsSecyEntry 536 }

vtssMacsecStatisticsSecyRxSc5Sa4InPacketsUnchecked OBJECT-TYPE
    SYNTAX      VTSSUnsigned64
    MAX-ACCESS  read-only
    STATUS      current
    DESCRIPTION
        "Number of unchecked packets received on this Rx SA."
    ::= { vtssMacsecStatisticsSecyEntry 537 }

vtssMacsecStatisticsSecyRxSc5Sa4InPacketsDelayed OBJECT-TYPE
    SYNTAX      VTSSUnsigned64
    MAX-ACCESS  read-only
    STATUS      current
    DESCRIPTION
        "Number of delayed packets received on this Rx SA."
    ::= { vtssMacsecStatisticsSecyEntry 538 }

vtssMacsecStatisticsSecyRxSc5Sa4InPacketsLate OBJECT-TYPE
    SYNTAX      VTSSUnsigned64
    MAX-ACCESS  read-only
    STATUS      current
    DESCRIPTION
        "Number of late packets received on this Rx SA."
    ::= { vtssMacsecStatisticsSecyEntry 539 }

vtssMacsecStatisticsSecyRxSc6InPacketsUnchecked OBJECT-TYPE
    SYNTAX      VTSSUnsigned64
    MAX-ACCESS  read-only
    STATUS      current
    DESCRIPTION
        "Number of unchecked packets received on this Rx SC."
    ::= { vtssMacsecStatisticsSecyEntry 550 }

vtssMacsecStatisticsSecyRxSc6InPacketsDelayed OBJECT-TYPE
    SYNTAX      VTSSUnsigned64
    MAX-ACCESS  read-only
    STATUS      current
    DESCRIPTION
        "Number of delayed packets received on this Rx SC."
    ::= { vtssMacsecStatisticsSecyEntry 551 }

vtssMacsecStatisticsSecyRxSc6InPacketsLate OBJECT-TYPE
    SYNTAX      VTSSUnsigned64
    MAX-ACCESS  read-only
    STATUS      current
    DESCRIPTION
        "Number of late packets received on this Rx SC."
    ::= { vtssMacsecStatisticsSecyEntry 552 }

vtssMacsecStatisticsSecyRxSc6InPacketsOk OBJECT-TYPE
    SYNTAX      VTSSUnsigned64
    MAX-ACCESS  read-only
    STATUS      current
    DESCRIPTION
        "Number of OK packets received on this Rx SC."
    ::= { vtssMacsecStatisticsSecyEntry 553 }

vtssMacsecStatisticsSecyRxSc6InPacketsInvalid OBJECT-TYPE
    SYNTAX      VTSSUnsigned64
    MAX-ACCESS  read-only
    STATUS      current
    DESCRIPTION
        "Number of invalid packets received on this Rx SC."
    ::= { vtssMacsecStatisticsSecyEntry 554 }

vtssMacsecStatisticsSecyRxSc6InPacketsNotValid OBJECT-TYPE
    SYNTAX      VTSSUnsigned64
    MAX-ACCESS  read-only
    STATUS      current
    DESCRIPTION
        "Number of not valid packets received on this Rx SC."
    ::= { vtssMacsecStatisticsSecyEntry 555 }

vtssMacsecStatisticsSecyRxSc6InPacketsNotUsingSa OBJECT-TYPE
    SYNTAX      VTSSUnsigned64
    MAX-ACCESS  read-only
    STATUS      current
    DESCRIPTION
        "Number of packets not using SA received on this Rx SC."
    ::= { vtssMacsecStatisticsSecyEntry 556 }

vtssMacsecStatisticsSecyRxSc6InPacketsUnusedSa OBJECT-TYPE
    SYNTAX      VTSSUnsigned64
    MAX-ACCESS  read-only
    STATUS      current
    DESCRIPTION
        "Number of packets with unused SA received on this Rx SC."
    ::= { vtssMacsecStatisticsSecyEntry 557 }

vtssMacsecStatisticsSecyRxSc6InOctetsValidated OBJECT-TYPE
    SYNTAX      VTSSUnsigned64
    MAX-ACCESS  read-only
    STATUS      current
    DESCRIPTION
        "Number of validated octets received on this Rx SC."
    ::= { vtssMacsecStatisticsSecyEntry 558 }

vtssMacsecStatisticsSecyRxSc6InOctetsDecrypted OBJECT-TYPE
    SYNTAX      VTSSUnsigned64
    MAX-ACCESS  read-only
    STATUS      current
    DESCRIPTION
        "Number of decrypted octets received on this Rx SC."
    ::= { vtssMacsecStatisticsSecyEntry 559 }

vtssMacsecStatisticsSecyRxSc6Sa1InPacketsOk OBJECT-TYPE
    SYNTAX      VTSSUnsigned64
    MAX-ACCESS  read-only
    STATUS      current
    DESCRIPTION
        "Number of OK packets received on this Rx SA."
    ::= { vtssMacsecStatisticsSecyEntry 570 }

vtssMacsecStatisticsSecyRxSc6Sa1InPacketsInvalid OBJECT-TYPE
    SYNTAX      VTSSUnsigned64
    MAX-ACCESS  read-only
    STATUS      current
    DESCRIPTION
        "Number of invalid packets received on this Rx SA."
    ::= { vtssMacsecStatisticsSecyEntry 571 }

vtssMacsecStatisticsSecyRxSc6Sa1InPacketsNotValid OBJECT-TYPE
    SYNTAX      VTSSUnsigned64
    MAX-ACCESS  read-only
    STATUS      current
    DESCRIPTION
        "Number of not valid packets received on this Rx SA."
    ::= { vtssMacsecStatisticsSecyEntry 572 }

vtssMacsecStatisticsSecyRxSc6Sa1InPacketsNotUsingSa OBJECT-TYPE
    SYNTAX      VTSSUnsigned64
    MAX-ACCESS  read-only
    STATUS      current
    DESCRIPTION
        "Number of packets not using SA received on this Rx SA."
    ::= { vtssMacsecStatisticsSecyEntry 573 }

vtssMacsecStatisticsSecyRxSc6Sa1InPacketsUnusedSa OBJECT-TYPE
    SYNTAX      VTSSUnsigned64
    MAX-ACCESS  read-only
    STATUS      current
    DESCRIPTION
        "Number of packets with unused SA received on this Rx SA."
    ::= { vtssMacsecStatisticsSecyEntry 574 }

vtssMacsecStatisticsSecyRxSc6Sa1InPacketsUnchecked OBJECT-TYPE
    SYNTAX      VTSSUnsigned64
    MAX-ACCESS  read-only
    STATUS      current
    DESCRIPTION
        "Number of unchecked packets received on this Rx SA."
    ::= { vtssMacsecStatisticsSecyEntry 575 }

vtssMacsecStatisticsSecyRxSc6Sa1InPacketsDelayed OBJECT-TYPE
    SYNTAX      VTSSUnsigned64
    MAX-ACCESS  read-only
    STATUS      current
    DESCRIPTION
        "Number of delayed packets received on this Rx SA."
    ::= { vtssMacsecStatisticsSecyEntry 576 }

vtssMacsecStatisticsSecyRxSc6Sa1InPacketsLate OBJECT-TYPE
    SYNTAX      VTSSUnsigned64
    MAX-ACCESS  read-only
    STATUS      current
    DESCRIPTION
        "Number of late packets received on this Rx SA."
    ::= { vtssMacsecStatisticsSecyEntry 577 }

vtssMacsecStatisticsSecyRxSc6Sa2InPacketsOk OBJECT-TYPE
    SYNTAX      VTSSUnsigned64
    MAX-ACCESS  read-only
    STATUS      current
    DESCRIPTION
        "Number of OK packets received on this Rx SA."
    ::= { vtssMacsecStatisticsSecyEntry 588 }

vtssMacsecStatisticsSecyRxSc6Sa2InPacketsInvalid OBJECT-TYPE
    SYNTAX      VTSSUnsigned64
    MAX-ACCESS  read-only
    STATUS      current
    DESCRIPTION
        "Number of invalid packets received on this Rx SA."
    ::= { vtssMacsecStatisticsSecyEntry 589 }

vtssMacsecStatisticsSecyRxSc6Sa2InPacketsNotValid OBJECT-TYPE
    SYNTAX      VTSSUnsigned64
    MAX-ACCESS  read-only
    STATUS      current
    DESCRIPTION
        "Number of not valid packets received on this Rx SA."
    ::= { vtssMacsecStatisticsSecyEntry 590 }

vtssMacsecStatisticsSecyRxSc6Sa2InPacketsNotUsingSa OBJECT-TYPE
    SYNTAX      VTSSUnsigned64
    MAX-ACCESS  read-only
    STATUS      current
    DESCRIPTION
        "Number of packets not using SA received on this Rx SA."
    ::= { vtssMacsecStatisticsSecyEntry 591 }

vtssMacsecStatisticsSecyRxSc6Sa2InPacketsUnusedSa OBJECT-TYPE
    SYNTAX      VTSSUnsigned64
    MAX-ACCESS  read-only
    STATUS      current
    DESCRIPTION
        "Number of packets with unused SA received on this Rx SA."
    ::= { vtssMacsecStatisticsSecyEntry 592 }

vtssMacsecStatisticsSecyRxSc6Sa2InPacketsUnchecked OBJECT-TYPE
    SYNTAX      VTSSUnsigned64
    MAX-ACCESS  read-only
    STATUS      current
    DESCRIPTION
        "Number of unchecked packets received on this Rx SA."
    ::= { vtssMacsecStatisticsSecyEntry 593 }

vtssMacsecStatisticsSecyRxSc6Sa2InPacketsDelayed OBJECT-TYPE
    SYNTAX      VTSSUnsigned64
    MAX-ACCESS  read-only
    STATUS      current
    DESCRIPTION
        "Number of delayed packets received on this Rx SA."
    ::= { vtssMacsecStatisticsSecyEntry 594 }

vtssMacsecStatisticsSecyRxSc6Sa2InPacketsLate OBJECT-TYPE
    SYNTAX      VTSSUnsigned64
    MAX-ACCESS  read-only
    STATUS      current
    DESCRIPTION
        "Number of late packets received on this Rx SA."
    ::= { vtssMacsecStatisticsSecyEntry 595 }

vtssMacsecStatisticsSecyRxSc6Sa3InPacketsOk OBJECT-TYPE
    SYNTAX      VTSSUnsigned64
    MAX-ACCESS  read-only
    STATUS      current
    DESCRIPTION
        "Number of OK packets received on this Rx SA."
    ::= { vtssMacsecStatisticsSecyEntry 606 }

vtssMacsecStatisticsSecyRxSc6Sa3InPacketsInvalid OBJECT-TYPE
    SYNTAX      VTSSUnsigned64
    MAX-ACCESS  read-only
    STATUS      current
    DESCRIPTION
        "Number of invalid packets received on this Rx SA."
    ::= { vtssMacsecStatisticsSecyEntry 607 }

vtssMacsecStatisticsSecyRxSc6Sa3InPacketsNotValid OBJECT-TYPE
    SYNTAX      VTSSUnsigned64
    MAX-ACCESS  read-only
    STATUS      current
    DESCRIPTION
        "Number of not valid packets received on this Rx SA."
    ::= { vtssMacsecStatisticsSecyEntry 608 }

vtssMacsecStatisticsSecyRxSc6Sa3InPacketsNotUsingSa OBJECT-TYPE
    SYNTAX      VTSSUnsigned64
    MAX-ACCESS  read-only
    STATUS      current
    DESCRIPTION
        "Number of packets not using SA received on this Rx SA."
    ::= { vtssMacsecStatisticsSecyEntry 609 }

vtssMacsecStatisticsSecyRxSc6Sa3InPacketsUnusedSa OBJECT-TYPE
    SYNTAX      VTSSUnsigned64
    MAX-ACCESS  read-only
    STATUS      current
    DESCRIPTION
        "Number of packets with unused SA received on this Rx SA."
    ::= { vtssMacsecStatisticsSecyEntry 610 }

vtssMacsecStatisticsSecyRxSc6Sa3InPacketsUnchecked OBJECT-TYPE
    SYNTAX      VTSSUnsigned64
    MAX-ACCESS  read-only
    STATUS      current
    DESCRIPTION
        "Number of unchecked packets received on this Rx SA."
    ::= { vtssMacsecStatisticsSecyEntry 611 }

vtssMacsecStatisticsSecyRxSc6Sa3InPacketsDelayed OBJECT-TYPE
    SYNTAX      VTSSUnsigned64
    MAX-ACCESS  read-only
    STATUS      current
    DESCRIPTION
        "Number of delayed packets received on this Rx SA."
    ::= { vtssMacsecStatisticsSecyEntry 612 }

vtssMacsecStatisticsSecyRxSc6Sa3InPacketsLate OBJECT-TYPE
    SYNTAX      VTSSUnsigned64
    MAX-ACCESS  read-only
    STATUS      current
    DESCRIPTION
        "Number of late packets received on this Rx SA."
    ::= { vtssMacsecStatisticsSecyEntry 613 }

vtssMacsecStatisticsSecyRxSc6Sa4InPacketsOk OBJECT-TYPE
    SYNTAX      VTSSUnsigned64
    MAX-ACCESS  read-only
    STATUS      current
    DESCRIPTION
        "Number of OK packets received on this Rx SA."
    ::= { vtssMacsecStatisticsSecyEntry 624 }

vtssMacsecStatisticsSecyRxSc6Sa4InPacketsInvalid OBJECT-TYPE
    SYNTAX      VTSSUnsigned64
    MAX-ACCESS  read-only
    STATUS      current
    DESCRIPTION
        "Number of invalid packets received on this Rx SA."
    ::= { vtssMacsecStatisticsSecyEntry 625 }

vtssMacsecStatisticsSecyRxSc6Sa4InPacketsNotValid OBJECT-TYPE
    SYNTAX      VTSSUnsigned64
    MAX-ACCESS  read-only
    STATUS      current
    DESCRIPTION
        "Number of not valid packets received on this Rx SA."
    ::= { vtssMacsecStatisticsSecyEntry 626 }

vtssMacsecStatisticsSecyRxSc6Sa4InPacketsNotUsingSa OBJECT-TYPE
    SYNTAX      VTSSUnsigned64
    MAX-ACCESS  read-only
    STATUS      current
    DESCRIPTION
        "Number of packets not using SA received on this Rx SA."
    ::= { vtssMacsecStatisticsSecyEntry 627 }

vtssMacsecStatisticsSecyRxSc6Sa4InPacketsUnusedSa OBJECT-TYPE
    SYNTAX      VTSSUnsigned64
    MAX-ACCESS  read-only
    STATUS      current
    DESCRIPTION
        "Number of packets with unused SA received on this Rx SA."
    ::= { vtssMacsecStatisticsSecyEntry 628 }

vtssMacsecStatisticsSecyRxSc6Sa4InPacketsUnchecked OBJECT-TYPE
    SYNTAX      VTSSUnsigned64
    MAX-ACCESS  read-only
    STATUS      current
    DESCRIPTION
        "Number of unchecked packets received on this Rx SA."
    ::= { vtssMacsecStatisticsSecyEntry 629 }

vtssMacsecStatisticsSecyRxSc6Sa4InPacketsDelayed OBJECT-TYPE
    SYNTAX      VTSSUnsigned64
    MAX-ACCESS  read-only
    STATUS      current
    DESCRIPTION
        "Number of delayed packets received on this Rx SA."
    ::= { vtssMacsecStatisticsSecyEntry 630 }

vtssMacsecStatisticsSecyRxSc6Sa4InPacketsLate OBJECT-TYPE
    SYNTAX      VTSSUnsigned64
    MAX-ACCESS  read-only
    STATUS      current
    DESCRIPTION
        "Number of late packets received on this Rx SA."
    ::= { vtssMacsecStatisticsSecyEntry 631 }

vtssMacsecStatisticsSecyRxSc7InPacketsUnchecked OBJECT-TYPE
    SYNTAX      VTSSUnsigned64
    MAX-ACCESS  read-only
    STATUS      current
    DESCRIPTION
        "Number of unchecked packets received on this Rx SC."
    ::= { vtssMacsecStatisticsSecyEntry 642 }

vtssMacsecStatisticsSecyRxSc7InPacketsDelayed OBJECT-TYPE
    SYNTAX      VTSSUnsigned64
    MAX-ACCESS  read-only
    STATUS      current
    DESCRIPTION
        "Number of delayed packets received on this Rx SC."
    ::= { vtssMacsecStatisticsSecyEntry 643 }

vtssMacsecStatisticsSecyRxSc7InPacketsLate OBJECT-TYPE
    SYNTAX      VTSSUnsigned64
    MAX-ACCESS  read-only
    STATUS      current
    DESCRIPTION
        "Number of late packets received on this Rx SC."
    ::= { vtssMacsecStatisticsSecyEntry 644 }

vtssMacsecStatisticsSecyRxSc7InPacketsOk OBJECT-TYPE
    SYNTAX      VTSSUnsigned64
    MAX-ACCESS  read-only
    STATUS      current
    DESCRIPTION
        "Number of OK packets received on this Rx SC."
    ::= { vtssMacsecStatisticsSecyEntry 645 }

vtssMacsecStatisticsSecyRxSc7InPacketsInvalid OBJECT-TYPE
    SYNTAX      VTSSUnsigned64
    MAX-ACCESS  read-only
    STATUS      current
    DESCRIPTION
        "Number of invalid packets received on this Rx SC."
    ::= { vtssMacsecStatisticsSecyEntry 646 }

vtssMacsecStatisticsSecyRxSc7InPacketsNotValid OBJECT-TYPE
    SYNTAX      VTSSUnsigned64
    MAX-ACCESS  read-only
    STATUS      current
    DESCRIPTION
        "Number of not valid packets received on this Rx SC."
    ::= { vtssMacsecStatisticsSecyEntry 647 }

vtssMacsecStatisticsSecyRxSc7InPacketsNotUsingSa OBJECT-TYPE
    SYNTAX      VTSSUnsigned64
    MAX-ACCESS  read-only
    STATUS      current
    DESCRIPTION
        "Number of packets not using SA received on this Rx SC."
    ::= { vtssMacsecStatisticsSecyEntry 648 }

vtssMacsecStatisticsSecyRxSc7InPacketsUnusedSa OBJECT-TYPE
    SYNTAX      VTSSUnsigned64
    MAX-ACCESS  read-only
    STATUS      current
    DESCRIPTION
        "Number of packets with unused SA received on this Rx SC."
    ::= { vtssMacsecStatisticsSecyEntry 649 }

vtssMacsecStatisticsSecyRxSc7InOctetsValidated OBJECT-TYPE
    SYNTAX      VTSSUnsigned64
    MAX-ACCESS  read-only
    STATUS      current
    DESCRIPTION
        "Number of validated octets received on this Rx SC."
    ::= { vtssMacsecStatisticsSecyEntry 650 }

vtssMacsecStatisticsSecyRxSc7InOctetsDecrypted OBJECT-TYPE
    SYNTAX      VTSSUnsigned64
    MAX-ACCESS  read-only
    STATUS      current
    DESCRIPTION
        "Number of decrypted octets received on this Rx SC."
    ::= { vtssMacsecStatisticsSecyEntry 651 }

vtssMacsecStatisticsSecyRxSc7Sa1InPacketsOk OBJECT-TYPE
    SYNTAX      VTSSUnsigned64
    MAX-ACCESS  read-only
    STATUS      current
    DESCRIPTION
        "Number of OK packets received on this Rx SA."
    ::= { vtssMacsecStatisticsSecyEntry 662 }

vtssMacsecStatisticsSecyRxSc7Sa1InPacketsInvalid OBJECT-TYPE
    SYNTAX      VTSSUnsigned64
    MAX-ACCESS  read-only
    STATUS      current
    DESCRIPTION
        "Number of invalid packets received on this Rx SA."
    ::= { vtssMacsecStatisticsSecyEntry 663 }

vtssMacsecStatisticsSecyRxSc7Sa1InPacketsNotValid OBJECT-TYPE
    SYNTAX      VTSSUnsigned64
    MAX-ACCESS  read-only
    STATUS      current
    DESCRIPTION
        "Number of not valid packets received on this Rx SA."
    ::= { vtssMacsecStatisticsSecyEntry 664 }

vtssMacsecStatisticsSecyRxSc7Sa1InPacketsNotUsingSa OBJECT-TYPE
    SYNTAX      VTSSUnsigned64
    MAX-ACCESS  read-only
    STATUS      current
    DESCRIPTION
        "Number of packets not using SA received on this Rx SA."
    ::= { vtssMacsecStatisticsSecyEntry 665 }

vtssMacsecStatisticsSecyRxSc7Sa1InPacketsUnusedSa OBJECT-TYPE
    SYNTAX      VTSSUnsigned64
    MAX-ACCESS  read-only
    STATUS      current
    DESCRIPTION
        "Number of packets with unused SA received on this Rx SA."
    ::= { vtssMacsecStatisticsSecyEntry 666 }

vtssMacsecStatisticsSecyRxSc7Sa1InPacketsUnchecked OBJECT-TYPE
    SYNTAX      VTSSUnsigned64
    MAX-ACCESS  read-only
    STATUS      current
    DESCRIPTION
        "Number of unchecked packets received on this Rx SA."
    ::= { vtssMacsecStatisticsSecyEntry 667 }

vtssMacsecStatisticsSecyRxSc7Sa1InPacketsDelayed OBJECT-TYPE
    SYNTAX      VTSSUnsigned64
    MAX-ACCESS  read-only
    STATUS      current
    DESCRIPTION
        "Number of delayed packets received on this Rx SA."
    ::= { vtssMacsecStatisticsSecyEntry 668 }

vtssMacsecStatisticsSecyRxSc7Sa1InPacketsLate OBJECT-TYPE
    SYNTAX      VTSSUnsigned64
    MAX-ACCESS  read-only
    STATUS      current
    DESCRIPTION
        "Number of late packets received on this Rx SA."
    ::= { vtssMacsecStatisticsSecyEntry 669 }

vtssMacsecStatisticsSecyRxSc7Sa2InPacketsOk OBJECT-TYPE
    SYNTAX      VTSSUnsigned64
    MAX-ACCESS  read-only
    STATUS      current
    DESCRIPTION
        "Number of OK packets received on this Rx SA."
    ::= { vtssMacsecStatisticsSecyEntry 680 }

vtssMacsecStatisticsSecyRxSc7Sa2InPacketsInvalid OBJECT-TYPE
    SYNTAX      VTSSUnsigned64
    MAX-ACCESS  read-only
    STATUS      current
    DESCRIPTION
        "Number of invalid packets received on this Rx SA."
    ::= { vtssMacsecStatisticsSecyEntry 681 }

vtssMacsecStatisticsSecyRxSc7Sa2InPacketsNotValid OBJECT-TYPE
    SYNTAX      VTSSUnsigned64
    MAX-ACCESS  read-only
    STATUS      current
    DESCRIPTION
        "Number of not valid packets received on this Rx SA."
    ::= { vtssMacsecStatisticsSecyEntry 682 }

vtssMacsecStatisticsSecyRxSc7Sa2InPacketsNotUsingSa OBJECT-TYPE
    SYNTAX      VTSSUnsigned64
    MAX-ACCESS  read-only
    STATUS      current
    DESCRIPTION
        "Number of packets not using SA received on this Rx SA."
    ::= { vtssMacsecStatisticsSecyEntry 683 }

vtssMacsecStatisticsSecyRxSc7Sa2InPacketsUnusedSa OBJECT-TYPE
    SYNTAX      VTSSUnsigned64
    MAX-ACCESS  read-only
    STATUS      current
    DESCRIPTION
        "Number of packets with unused SA received on this Rx SA."
    ::= { vtssMacsecStatisticsSecyEntry 684 }

vtssMacsecStatisticsSecyRxSc7Sa2InPacketsUnchecked OBJECT-TYPE
    SYNTAX      VTSSUnsigned64
    MAX-ACCESS  read-only
    STATUS      current
    DESCRIPTION
        "Number of unchecked packets received on this Rx SA."
    ::= { vtssMacsecStatisticsSecyEntry 685 }

vtssMacsecStatisticsSecyRxSc7Sa2InPacketsDelayed OBJECT-TYPE
    SYNTAX      VTSSUnsigned64
    MAX-ACCESS  read-only
    STATUS      current
    DESCRIPTION
        "Number of delayed packets received on this Rx SA."
    ::= { vtssMacsecStatisticsSecyEntry 686 }

vtssMacsecStatisticsSecyRxSc7Sa2InPacketsLate OBJECT-TYPE
    SYNTAX      VTSSUnsigned64
    MAX-ACCESS  read-only
    STATUS      current
    DESCRIPTION
        "Number of late packets received on this Rx SA."
    ::= { vtssMacsecStatisticsSecyEntry 687 }

vtssMacsecStatisticsSecyRxSc7Sa3InPacketsOk OBJECT-TYPE
    SYNTAX      VTSSUnsigned64
    MAX-ACCESS  read-only
    STATUS      current
    DESCRIPTION
        "Number of OK packets received on this Rx SA."
    ::= { vtssMacsecStatisticsSecyEntry 698 }

vtssMacsecStatisticsSecyRxSc7Sa3InPacketsInvalid OBJECT-TYPE
    SYNTAX      VTSSUnsigned64
    MAX-ACCESS  read-only
    STATUS      current
    DESCRIPTION
        "Number of invalid packets received on this Rx SA."
    ::= { vtssMacsecStatisticsSecyEntry 699 }

vtssMacsecStatisticsSecyRxSc7Sa3InPacketsNotValid OBJECT-TYPE
    SYNTAX      VTSSUnsigned64
    MAX-ACCESS  read-only
    STATUS      current
    DESCRIPTION
        "Number of not valid packets received on this Rx SA."
    ::= { vtssMacsecStatisticsSecyEntry 700 }

vtssMacsecStatisticsSecyRxSc7Sa3InPacketsNotUsingSa OBJECT-TYPE
    SYNTAX      VTSSUnsigned64
    MAX-ACCESS  read-only
    STATUS      current
    DESCRIPTION
        "Number of packets not using SA received on this Rx SA."
    ::= { vtssMacsecStatisticsSecyEntry 701 }

vtssMacsecStatisticsSecyRxSc7Sa3InPacketsUnusedSa OBJECT-TYPE
    SYNTAX      VTSSUnsigned64
    MAX-ACCESS  read-only
    STATUS      current
    DESCRIPTION
        "Number of packets with unused SA received on this Rx SA."
    ::= { vtssMacsecStatisticsSecyEntry 702 }

vtssMacsecStatisticsSecyRxSc7Sa3InPacketsUnchecked OBJECT-TYPE
    SYNTAX      VTSSUnsigned64
    MAX-ACCESS  read-only
    STATUS      current
    DESCRIPTION
        "Number of unchecked packets received on this Rx SA."
    ::= { vtssMacsecStatisticsSecyEntry 703 }

vtssMacsecStatisticsSecyRxSc7Sa3InPacketsDelayed OBJECT-TYPE
    SYNTAX      VTSSUnsigned64
    MAX-ACCESS  read-only
    STATUS      current
    DESCRIPTION
        "Number of delayed packets received on this Rx SA."
    ::= { vtssMacsecStatisticsSecyEntry 704 }

vtssMacsecStatisticsSecyRxSc7Sa3InPacketsLate OBJECT-TYPE
    SYNTAX      VTSSUnsigned64
    MAX-ACCESS  read-only
    STATUS      current
    DESCRIPTION
        "Number of late packets received on this Rx SA."
    ::= { vtssMacsecStatisticsSecyEntry 705 }

vtssMacsecStatisticsSecyRxSc7Sa4InPacketsOk OBJECT-TYPE
    SYNTAX      VTSSUnsigned64
    MAX-ACCESS  read-only
    STATUS      current
    DESCRIPTION
        "Number of OK packets received on this Rx SA."
    ::= { vtssMacsecStatisticsSecyEntry 716 }

vtssMacsecStatisticsSecyRxSc7Sa4InPacketsInvalid OBJECT-TYPE
    SYNTAX      VTSSUnsigned64
    MAX-ACCESS  read-only
    STATUS      current
    DESCRIPTION
        "Number of invalid packets received on this Rx SA."
    ::= { vtssMacsecStatisticsSecyEntry 717 }

vtssMacsecStatisticsSecyRxSc7Sa4InPacketsNotValid OBJECT-TYPE
    SYNTAX      VTSSUnsigned64
    MAX-ACCESS  read-only
    STATUS      current
    DESCRIPTION
        "Number of not valid packets received on this Rx SA."
    ::= { vtssMacsecStatisticsSecyEntry 718 }

vtssMacsecStatisticsSecyRxSc7Sa4InPacketsNotUsingSa OBJECT-TYPE
    SYNTAX      VTSSUnsigned64
    MAX-ACCESS  read-only
    STATUS      current
    DESCRIPTION
        "Number of packets not using SA received on this Rx SA."
    ::= { vtssMacsecStatisticsSecyEntry 719 }

vtssMacsecStatisticsSecyRxSc7Sa4InPacketsUnusedSa OBJECT-TYPE
    SYNTAX      VTSSUnsigned64
    MAX-ACCESS  read-only
    STATUS      current
    DESCRIPTION
        "Number of packets with unused SA received on this Rx SA."
    ::= { vtssMacsecStatisticsSecyEntry 720 }

vtssMacsecStatisticsSecyRxSc7Sa4InPacketsUnchecked OBJECT-TYPE
    SYNTAX      VTSSUnsigned64
    MAX-ACCESS  read-only
    STATUS      current
    DESCRIPTION
        "Number of unchecked packets received on this Rx SA."
    ::= { vtssMacsecStatisticsSecyEntry 721 }

vtssMacsecStatisticsSecyRxSc7Sa4InPacketsDelayed OBJECT-TYPE
    SYNTAX      VTSSUnsigned64
    MAX-ACCESS  read-only
    STATUS      current
    DESCRIPTION
        "Number of delayed packets received on this Rx SA."
    ::= { vtssMacsecStatisticsSecyEntry 722 }

vtssMacsecStatisticsSecyRxSc7Sa4InPacketsLate OBJECT-TYPE
    SYNTAX      VTSSUnsigned64
    MAX-ACCESS  read-only
    STATUS      current
    DESCRIPTION
        "Number of late packets received on this Rx SA."
    ::= { vtssMacsecStatisticsSecyEntry 723 }

vtssMacsecStatisticsSecyRxSc8InPacketsUnchecked OBJECT-TYPE
    SYNTAX      VTSSUnsigned64
    MAX-ACCESS  read-only
    STATUS      current
    DESCRIPTION
        "Number of unchecked packets received on this Rx SC."
    ::= { vtssMacsecStatisticsSecyEntry 734 }

vtssMacsecStatisticsSecyRxSc8InPacketsDelayed OBJECT-TYPE
    SYNTAX      VTSSUnsigned64
    MAX-ACCESS  read-only
    STATUS      current
    DESCRIPTION
        "Number of delayed packets received on this Rx SC."
    ::= { vtssMacsecStatisticsSecyEntry 735 }

vtssMacsecStatisticsSecyRxSc8InPacketsLate OBJECT-TYPE
    SYNTAX      VTSSUnsigned64
    MAX-ACCESS  read-only
    STATUS      current
    DESCRIPTION
        "Number of late packets received on this Rx SC."
    ::= { vtssMacsecStatisticsSecyEntry 736 }

vtssMacsecStatisticsSecyRxSc8InPacketsOk OBJECT-TYPE
    SYNTAX      VTSSUnsigned64
    MAX-ACCESS  read-only
    STATUS      current
    DESCRIPTION
        "Number of OK packets received on this Rx SC."
    ::= { vtssMacsecStatisticsSecyEntry 737 }

vtssMacsecStatisticsSecyRxSc8InPacketsInvalid OBJECT-TYPE
    SYNTAX      VTSSUnsigned64
    MAX-ACCESS  read-only
    STATUS      current
    DESCRIPTION
        "Number of invalid packets received on this Rx SC."
    ::= { vtssMacsecStatisticsSecyEntry 738 }

vtssMacsecStatisticsSecyRxSc8InPacketsNotValid OBJECT-TYPE
    SYNTAX      VTSSUnsigned64
    MAX-ACCESS  read-only
    STATUS      current
    DESCRIPTION
        "Number of not valid packets received on this Rx SC."
    ::= { vtssMacsecStatisticsSecyEntry 739 }

vtssMacsecStatisticsSecyRxSc8InPacketsNotUsingSa OBJECT-TYPE
    SYNTAX      VTSSUnsigned64
    MAX-ACCESS  read-only
    STATUS      current
    DESCRIPTION
        "Number of packets not using SA received on this Rx SC."
    ::= { vtssMacsecStatisticsSecyEntry 740 }

vtssMacsecStatisticsSecyRxSc8InPacketsUnusedSa OBJECT-TYPE
    SYNTAX      VTSSUnsigned64
    MAX-ACCESS  read-only
    STATUS      current
    DESCRIPTION
        "Number of packets with unused SA received on this Rx SC."
    ::= { vtssMacsecStatisticsSecyEntry 741 }

vtssMacsecStatisticsSecyRxSc8InOctetsValidated OBJECT-TYPE
    SYNTAX      VTSSUnsigned64
    MAX-ACCESS  read-only
    STATUS      current
    DESCRIPTION
        "Number of validated octets received on this Rx SC."
    ::= { vtssMacsecStatisticsSecyEntry 742 }

vtssMacsecStatisticsSecyRxSc8InOctetsDecrypted OBJECT-TYPE
    SYNTAX      VTSSUnsigned64
    MAX-ACCESS  read-only
    STATUS      current
    DESCRIPTION
        "Number of decrypted octets received on this Rx SC."
    ::= { vtssMacsecStatisticsSecyEntry 743 }

vtssMacsecStatisticsSecyRxSc8Sa1InPacketsOk OBJECT-TYPE
    SYNTAX      VTSSUnsigned64
    MAX-ACCESS  read-only
    STATUS      current
    DESCRIPTION
        "Number of OK packets received on this Rx SA."
    ::= { vtssMacsecStatisticsSecyEntry 754 }

vtssMacsecStatisticsSecyRxSc8Sa1InPacketsInvalid OBJECT-TYPE
    SYNTAX      VTSSUnsigned64
    MAX-ACCESS  read-only
    STATUS      current
    DESCRIPTION
        "Number of invalid packets received on this Rx SA."
    ::= { vtssMacsecStatisticsSecyEntry 755 }

vtssMacsecStatisticsSecyRxSc8Sa1InPacketsNotValid OBJECT-TYPE
    SYNTAX      VTSSUnsigned64
    MAX-ACCESS  read-only
    STATUS      current
    DESCRIPTION
        "Number of not valid packets received on this Rx SA."
    ::= { vtssMacsecStatisticsSecyEntry 756 }

vtssMacsecStatisticsSecyRxSc8Sa1InPacketsNotUsingSa OBJECT-TYPE
    SYNTAX      VTSSUnsigned64
    MAX-ACCESS  read-only
    STATUS      current
    DESCRIPTION
        "Number of packets not using SA received on this Rx SA."
    ::= { vtssMacsecStatisticsSecyEntry 757 }

vtssMacsecStatisticsSecyRxSc8Sa1InPacketsUnusedSa OBJECT-TYPE
    SYNTAX      VTSSUnsigned64
    MAX-ACCESS  read-only
    STATUS      current
    DESCRIPTION
        "Number of packets with unused SA received on this Rx SA."
    ::= { vtssMacsecStatisticsSecyEntry 758 }

vtssMacsecStatisticsSecyRxSc8Sa1InPacketsUnchecked OBJECT-TYPE
    SYNTAX      VTSSUnsigned64
    MAX-ACCESS  read-only
    STATUS      current
    DESCRIPTION
        "Number of unchecked packets received on this Rx SA."
    ::= { vtssMacsecStatisticsSecyEntry 759 }

vtssMacsecStatisticsSecyRxSc8Sa1InPacketsDelayed OBJECT-TYPE
    SYNTAX      VTSSUnsigned64
    MAX-ACCESS  read-only
    STATUS      current
    DESCRIPTION
        "Number of delayed packets received on this Rx SA."
    ::= { vtssMacsecStatisticsSecyEntry 760 }

vtssMacsecStatisticsSecyRxSc8Sa1InPacketsLate OBJECT-TYPE
    SYNTAX      VTSSUnsigned64
    MAX-ACCESS  read-only
    STATUS      current
    DESCRIPTION
        "Number of late packets received on this Rx SA."
    ::= { vtssMacsecStatisticsSecyEntry 761 }

vtssMacsecStatisticsSecyRxSc8Sa2InPacketsOk OBJECT-TYPE
    SYNTAX      VTSSUnsigned64
    MAX-ACCESS  read-only
    STATUS      current
    DESCRIPTION
        "Number of OK packets received on this Rx SA."
    ::= { vtssMacsecStatisticsSecyEntry 772 }

vtssMacsecStatisticsSecyRxSc8Sa2InPacketsInvalid OBJECT-TYPE
    SYNTAX      VTSSUnsigned64
    MAX-ACCESS  read-only
    STATUS      current
    DESCRIPTION
        "Number of invalid packets received on this Rx SA."
    ::= { vtssMacsecStatisticsSecyEntry 773 }

vtssMacsecStatisticsSecyRxSc8Sa2InPacketsNotValid OBJECT-TYPE
    SYNTAX      VTSSUnsigned64
    MAX-ACCESS  read-only
    STATUS      current
    DESCRIPTION
        "Number of not valid packets received on this Rx SA."
    ::= { vtssMacsecStatisticsSecyEntry 774 }

vtssMacsecStatisticsSecyRxSc8Sa2InPacketsNotUsingSa OBJECT-TYPE
    SYNTAX      VTSSUnsigned64
    MAX-ACCESS  read-only
    STATUS      current
    DESCRIPTION
        "Number of packets not using SA received on this Rx SA."
    ::= { vtssMacsecStatisticsSecyEntry 775 }

vtssMacsecStatisticsSecyRxSc8Sa2InPacketsUnusedSa OBJECT-TYPE
    SYNTAX      VTSSUnsigned64
    MAX-ACCESS  read-only
    STATUS      current
    DESCRIPTION
        "Number of packets with unused SA received on this Rx SA."
    ::= { vtssMacsecStatisticsSecyEntry 776 }

vtssMacsecStatisticsSecyRxSc8Sa2InPacketsUnchecked OBJECT-TYPE
    SYNTAX      VTSSUnsigned64
    MAX-ACCESS  read-only
    STATUS      current
    DESCRIPTION
        "Number of unchecked packets received on this Rx SA."
    ::= { vtssMacsecStatisticsSecyEntry 777 }

vtssMacsecStatisticsSecyRxSc8Sa2InPacketsDelayed OBJECT-TYPE
    SYNTAX      VTSSUnsigned64
    MAX-ACCESS  read-only
    STATUS      current
    DESCRIPTION
        "Number of delayed packets received on this Rx SA."
    ::= { vtssMacsecStatisticsSecyEntry 778 }

vtssMacsecStatisticsSecyRxSc8Sa2InPacketsLate OBJECT-TYPE
    SYNTAX      VTSSUnsigned64
    MAX-ACCESS  read-only
    STATUS      current
    DESCRIPTION
        "Number of late packets received on this Rx SA."
    ::= { vtssMacsecStatisticsSecyEntry 779 }

vtssMacsecStatisticsSecyRxSc8Sa3InPacketsOk OBJECT-TYPE
    SYNTAX      VTSSUnsigned64
    MAX-ACCESS  read-only
    STATUS      current
    DESCRIPTION
        "Number of OK packets received on this Rx SA."
    ::= { vtssMacsecStatisticsSecyEntry 790 }

vtssMacsecStatisticsSecyRxSc8Sa3InPacketsInvalid OBJECT-TYPE
    SYNTAX      VTSSUnsigned64
    MAX-ACCESS  read-only
    STATUS      current
    DESCRIPTION
        "Number of invalid packets received on this Rx SA."
    ::= { vtssMacsecStatisticsSecyEntry 791 }

vtssMacsecStatisticsSecyRxSc8Sa3InPacketsNotValid OBJECT-TYPE
    SYNTAX      VTSSUnsigned64
    MAX-ACCESS  read-only
    STATUS      current
    DESCRIPTION
        "Number of not valid packets received on this Rx SA."
    ::= { vtssMacsecStatisticsSecyEntry 792 }

vtssMacsecStatisticsSecyRxSc8Sa3InPacketsNotUsingSa OBJECT-TYPE
    SYNTAX      VTSSUnsigned64
    MAX-ACCESS  read-only
    STATUS      current
    DESCRIPTION
        "Number of packets not using SA received on this Rx SA."
    ::= { vtssMacsecStatisticsSecyEntry 793 }

vtssMacsecStatisticsSecyRxSc8Sa3InPacketsUnusedSa OBJECT-TYPE
    SYNTAX      VTSSUnsigned64
    MAX-ACCESS  read-only
    STATUS      current
    DESCRIPTION
        "Number of packets with unused SA received on this Rx SA."
    ::= { vtssMacsecStatisticsSecyEntry 794 }

vtssMacsecStatisticsSecyRxSc8Sa3InPacketsUnchecked OBJECT-TYPE
    SYNTAX      VTSSUnsigned64
    MAX-ACCESS  read-only
    STATUS      current
    DESCRIPTION
        "Number of unchecked packets received on this Rx SA."
    ::= { vtssMacsecStatisticsSecyEntry 795 }

vtssMacsecStatisticsSecyRxSc8Sa3InPacketsDelayed OBJECT-TYPE
    SYNTAX      VTSSUnsigned64
    MAX-ACCESS  read-only
    STATUS      current
    DESCRIPTION
        "Number of delayed packets received on this Rx SA."
    ::= { vtssMacsecStatisticsSecyEntry 796 }

vtssMacsecStatisticsSecyRxSc8Sa3InPacketsLate OBJECT-TYPE
    SYNTAX      VTSSUnsigned64
    MAX-ACCESS  read-only
    STATUS      current
    DESCRIPTION
        "Number of late packets received on this Rx SA."
    ::= { vtssMacsecStatisticsSecyEntry 797 }

vtssMacsecStatisticsSecyRxSc8Sa4InPacketsOk OBJECT-TYPE
    SYNTAX      VTSSUnsigned64
    MAX-ACCESS  read-only
    STATUS      current
    DESCRIPTION
        "Number of OK packets received on this Rx SA."
    ::= { vtssMacsecStatisticsSecyEntry 808 }

vtssMacsecStatisticsSecyRxSc8Sa4InPacketsInvalid OBJECT-TYPE
    SYNTAX      VTSSUnsigned64
    MAX-ACCESS  read-only
    STATUS      current
    DESCRIPTION
        "Number of invalid packets received on this Rx SA."
    ::= { vtssMacsecStatisticsSecyEntry 809 }

vtssMacsecStatisticsSecyRxSc8Sa4InPacketsNotValid OBJECT-TYPE
    SYNTAX      VTSSUnsigned64
    MAX-ACCESS  read-only
    STATUS      current
    DESCRIPTION
        "Number of not valid packets received on this Rx SA."
    ::= { vtssMacsecStatisticsSecyEntry 810 }

vtssMacsecStatisticsSecyRxSc8Sa4InPacketsNotUsingSa OBJECT-TYPE
    SYNTAX      VTSSUnsigned64
    MAX-ACCESS  read-only
    STATUS      current
    DESCRIPTION
        "Number of packets not using SA received on this Rx SA."
    ::= { vtssMacsecStatisticsSecyEntry 811 }

vtssMacsecStatisticsSecyRxSc8Sa4InPacketsUnusedSa OBJECT-TYPE
    SYNTAX      VTSSUnsigned64
    MAX-ACCESS  read-only
    STATUS      current
    DESCRIPTION
        "Number of packets with unused SA received on this Rx SA."
    ::= { vtssMacsecStatisticsSecyEntry 812 }

vtssMacsecStatisticsSecyRxSc8Sa4InPacketsUnchecked OBJECT-TYPE
    SYNTAX      VTSSUnsigned64
    MAX-ACCESS  read-only
    STATUS      current
    DESCRIPTION
        "Number of unchecked packets received on this Rx SA."
    ::= { vtssMacsecStatisticsSecyEntry 813 }

vtssMacsecStatisticsSecyRxSc8Sa4InPacketsDelayed OBJECT-TYPE
    SYNTAX      VTSSUnsigned64
    MAX-ACCESS  read-only
    STATUS      current
    DESCRIPTION
        "Number of delayed packets received on this Rx SA."
    ::= { vtssMacsecStatisticsSecyEntry 814 }

vtssMacsecStatisticsSecyRxSc8Sa4InPacketsLate OBJECT-TYPE
    SYNTAX      VTSSUnsigned64
    MAX-ACCESS  read-only
    STATUS      current
    DESCRIPTION
        "Number of late packets received on this Rx SA."
    ::= { vtssMacsecStatisticsSecyEntry 815 }

vtssMacsecTrap OBJECT IDENTIFIER
    ::= { vtssMacsecMibObjects 6 }

vtssMacsecMibConformance OBJECT IDENTIFIER
    ::= { vtssMacsecMib 2 }

vtssMacsecMibCompliances OBJECT IDENTIFIER
    ::= { vtssMacsecMibConformance 1 }

vtssMacsecMibGroups OBJECT IDENTIFIER
    ::= { vtssMacsecMibConformance 2 }

vtssMacsecCapabilitiesListInfoGroup OBJECT-GROUP
    OBJECTS     { vtssMacsecCapabilitiesListMacsecSupported }
    STATUS      current
    DESCRIPTION
        "A collection of objects."
    ::= { vtssMacsecMibGroups 1 }

vtssMacsecCapabilitiesInterfacesInfoGroup OBJECT-GROUP
    OBJECTS     { vtssMacsecCapabilitiesInterfacesIfIndex,
                  vtssMacsecCapabilitiesInterfacesMacsecCapable,
                  vtssMacsecCapabilitiesInterfacesGcmAes128,
                  vtssMacsecCapabilitiesInterfacesGcmAes256,
                  vtssMacsecCapabilitiesInterfacesGcmAesXpn128,
                  vtssMacsecCapabilitiesInterfacesGcmAesXpn256,
                  vtssMacsecCapabilitiesInterfacesTotalRxSaCnt,
                  vtssMacsecCapabilitiesInterfacesTotalTxSaCnt,
                  vtssMacsecCapabilitiesInterfacesSecyCntMax,
                  vtssMacsecCapabilitiesInterfacesTxScCntPerSecyMax,
                  vtssMacsecCapabilitiesInterfacesRxScCntPerSecyMax,
                  vtssMacsecCapabilitiesInterfacesTxSaCntPerScMax,
                  vtssMacsecCapabilitiesInterfacesRxSaCntPerScMax }
    STATUS      current
    DESCRIPTION
        "A collection of objects."
    ::= { vtssMacsecMibGroups 2 }

vtssMacsecConfigPortTableInfoGroup OBJECT-GROUP
    OBJECTS     { vtssMacsecConfigPortIfIndex,
                  vtssMacsecConfigPortEnable }
    STATUS      current
    DESCRIPTION
        "A collection of objects."
    ::= { vtssMacsecMibGroups 3 }

vtssMacsecConfigSecyTableInfoGroup OBJECT-GROUP
    OBJECTS     { vtssMacsecConfigSecyIfIndex,
                  vtssMacsecConfigSecySecyId,
                  vtssMacsecConfigSecyAdminActive,
                  vtssMacsecConfigSecyVirtualPortId,
                  vtssMacsecConfigSecyCipherSuite,
                  vtssMacsecConfigSecyConfidentialityOffset,
                  vtssMacsecConfigSecyTxProtectFrames,
                  vtssMacsecConfigSecyTxAlwaysIncludeSci,
                  vtssMacsecConfigSecyTxUseES,
                  vtssMacsecConfigSecyTxUseSCB,
                  vtssMacsecConfigSecyRxFrameValidation,
                  vtssMacsecConfigSecyRxReplayProtect,
                  vtssMacsecConfigSecyRxReplayWindow,
                  vtssMacsecConfigSecyTxScConfigured,
                  vtssMacsecConfigSecyTxScMacType,
                  vtssMacsecConfigSecyTxScCustomMac,
                  vtssMacsecConfigSecyTxSa1Configured,
                  vtssMacsecConfigSecyTxSa1Active,
                  vtssMacsecConfigSecyTxSa1NextPN,
                  vtssMacsecConfigSecyTxSa1Encrypt,
                  vtssMacsecConfigSecyTxSa1Key,
                  vtssMacsecConfigSecyTxSa1Salt,
                  vtssMacsecConfigSecyTxSa2Configured,
                  vtssMacsecConfigSecyTxSa2Active,
                  vtssMacsecConfigSecyTxSa2NextPN,
                  vtssMacsecConfigSecyTxSa2Encrypt,
                  vtssMacsecConfigSecyTxSa2Key,
                  vtssMacsecConfigSecyTxSa2Salt,
                  vtssMacsecConfigSecyTxSa3Configured,
                  vtssMacsecConfigSecyTxSa3Active,
                  vtssMacsecConfigSecyTxSa3NextPN,
                  vtssMacsecConfigSecyTxSa3Encrypt,
                  vtssMacsecConfigSecyTxSa3Key,
                  vtssMacsecConfigSecyTxSa3Salt,
                  vtssMacsecConfigSecyTxSa4Configured,
                  vtssMacsecConfigSecyTxSa4Active,
                  vtssMacsecConfigSecyTxSa4NextPN,
                  vtssMacsecConfigSecyTxSa4Encrypt,
                  vtssMacsecConfigSecyTxSa4Key,
                  vtssMacsecConfigSecyTxSa4Salt,
                  vtssMacsecConfigSecyRxSc1Configured,
                  vtssMacsecConfigSecyRxSc1PeerMac,
                  vtssMacsecConfigSecyRxSc1Sa1Configured,
                  vtssMacsecConfigSecyRxSc1Sa1Active,
                  vtssMacsecConfigSecyRxSc1Sa1LowestPN,
                  vtssMacsecConfigSecyRxSc1Sa1Key,
                  vtssMacsecConfigSecyRxSc1Sa1Salt,
                  vtssMacsecConfigSecyRxSc1Sa2Configured,
                  vtssMacsecConfigSecyRxSc1Sa2Active,
                  vtssMacsecConfigSecyRxSc1Sa2LowestPN,
                  vtssMacsecConfigSecyRxSc1Sa2Key,
                  vtssMacsecConfigSecyRxSc1Sa2Salt,
                  vtssMacsecConfigSecyRxSc1Sa3Configured,
                  vtssMacsecConfigSecyRxSc1Sa3Active,
                  vtssMacsecConfigSecyRxSc1Sa3LowestPN,
                  vtssMacsecConfigSecyRxSc1Sa3Key,
                  vtssMacsecConfigSecyRxSc1Sa3Salt,
                  vtssMacsecConfigSecyRxSc1Sa4Configured,
                  vtssMacsecConfigSecyRxSc1Sa4Active,
                  vtssMacsecConfigSecyRxSc1Sa4LowestPN,
                  vtssMacsecConfigSecyRxSc1Sa4Key,
                  vtssMacsecConfigSecyRxSc1Sa4Salt,
                  vtssMacsecConfigSecyRxSc2Configured,
                  vtssMacsecConfigSecyRxSc2PeerMac,
                  vtssMacsecConfigSecyRxSc2Sa1Configured,
                  vtssMacsecConfigSecyRxSc2Sa1Active,
                  vtssMacsecConfigSecyRxSc2Sa1LowestPN,
                  vtssMacsecConfigSecyRxSc2Sa1Key,
                  vtssMacsecConfigSecyRxSc2Sa1Salt,
                  vtssMacsecConfigSecyRxSc2Sa2Configured,
                  vtssMacsecConfigSecyRxSc2Sa2Active,
                  vtssMacsecConfigSecyRxSc2Sa2LowestPN,
                  vtssMacsecConfigSecyRxSc2Sa2Key,
                  vtssMacsecConfigSecyRxSc2Sa2Salt,
                  vtssMacsecConfigSecyRxSc2Sa3Configured,
                  vtssMacsecConfigSecyRxSc2Sa3Active,
                  vtssMacsecConfigSecyRxSc2Sa3LowestPN,
                  vtssMacsecConfigSecyRxSc2Sa3Key,
                  vtssMacsecConfigSecyRxSc2Sa3Salt,
                  vtssMacsecConfigSecyRxSc2Sa4Configured,
                  vtssMacsecConfigSecyRxSc2Sa4Active,
                  vtssMacsecConfigSecyRxSc2Sa4LowestPN,
                  vtssMacsecConfigSecyRxSc2Sa4Key,
                  vtssMacsecConfigSecyRxSc2Sa4Salt,
                  vtssMacsecConfigSecyRxSc3Configured,
                  vtssMacsecConfigSecyRxSc3PeerMac,
                  vtssMacsecConfigSecyRxSc3Sa1Configured,
                  vtssMacsecConfigSecyRxSc3Sa1Active,
                  vtssMacsecConfigSecyRxSc3Sa1LowestPN,
                  vtssMacsecConfigSecyRxSc3Sa1Key,
                  vtssMacsecConfigSecyRxSc3Sa1Salt,
                  vtssMacsecConfigSecyRxSc3Sa2Configured,
                  vtssMacsecConfigSecyRxSc3Sa2Active,
                  vtssMacsecConfigSecyRxSc3Sa2LowestPN,
                  vtssMacsecConfigSecyRxSc3Sa2Key,
                  vtssMacsecConfigSecyRxSc3Sa2Salt,
                  vtssMacsecConfigSecyRxSc3Sa3Configured,
                  vtssMacsecConfigSecyRxSc3Sa3Active,
                  vtssMacsecConfigSecyRxSc3Sa3LowestPN,
                  vtssMacsecConfigSecyRxSc3Sa3Key,
                  vtssMacsecConfigSecyRxSc3Sa3Salt,
                  vtssMacsecConfigSecyRxSc3Sa4Configured,
                  vtssMacsecConfigSecyRxSc3Sa4Active,
                  vtssMacsecConfigSecyRxSc3Sa4LowestPN,
                  vtssMacsecConfigSecyRxSc3Sa4Key,
                  vtssMacsecConfigSecyRxSc3Sa4Salt,
                  vtssMacsecConfigSecyRxSc4Configured,
                  vtssMacsecConfigSecyRxSc4PeerMac,
                  vtssMacsecConfigSecyRxSc4Sa1Configured,
                  vtssMacsecConfigSecyRxSc4Sa1Active,
                  vtssMacsecConfigSecyRxSc4Sa1LowestPN,
                  vtssMacsecConfigSecyRxSc4Sa1Key,
                  vtssMacsecConfigSecyRxSc4Sa1Salt,
                  vtssMacsecConfigSecyRxSc4Sa2Configured,
                  vtssMacsecConfigSecyRxSc4Sa2Active,
                  vtssMacsecConfigSecyRxSc4Sa2LowestPN,
                  vtssMacsecConfigSecyRxSc4Sa2Key,
                  vtssMacsecConfigSecyRxSc4Sa2Salt,
                  vtssMacsecConfigSecyRxSc4Sa3Configured,
                  vtssMacsecConfigSecyRxSc4Sa3Active,
                  vtssMacsecConfigSecyRxSc4Sa3LowestPN,
                  vtssMacsecConfigSecyRxSc4Sa3Key,
                  vtssMacsecConfigSecyRxSc4Sa3Salt,
                  vtssMacsecConfigSecyRxSc4Sa4Configured,
                  vtssMacsecConfigSecyRxSc4Sa4Active,
                  vtssMacsecConfigSecyRxSc4Sa4LowestPN,
                  vtssMacsecConfigSecyRxSc4Sa4Key,
                  vtssMacsecConfigSecyRxSc4Sa4Salt,
                  vtssMacsecConfigSecyRxSc5Configured,
                  vtssMacsecConfigSecyRxSc5PeerMac,
                  vtssMacsecConfigSecyRxSc5Sa1Configured,
                  vtssMacsecConfigSecyRxSc5Sa1Active,
                  vtssMacsecConfigSecyRxSc5Sa1LowestPN,
                  vtssMacsecConfigSecyRxSc5Sa1Key,
                  vtssMacsecConfigSecyRxSc5Sa1Salt,
                  vtssMacsecConfigSecyRxSc5Sa2Configured,
                  vtssMacsecConfigSecyRxSc5Sa2Active,
                  vtssMacsecConfigSecyRxSc5Sa2LowestPN,
                  vtssMacsecConfigSecyRxSc5Sa2Key,
                  vtssMacsecConfigSecyRxSc5Sa2Salt,
                  vtssMacsecConfigSecyRxSc5Sa3Configured,
                  vtssMacsecConfigSecyRxSc5Sa3Active,
                  vtssMacsecConfigSecyRxSc5Sa3LowestPN,
                  vtssMacsecConfigSecyRxSc5Sa3Key,
                  vtssMacsecConfigSecyRxSc5Sa3Salt,
                  vtssMacsecConfigSecyRxSc5Sa4Configured,
                  vtssMacsecConfigSecyRxSc5Sa4Active,
                  vtssMacsecConfigSecyRxSc5Sa4LowestPN,
                  vtssMacsecConfigSecyRxSc5Sa4Key,
                  vtssMacsecConfigSecyRxSc5Sa4Salt,
                  vtssMacsecConfigSecyRxSc6Configured,
                  vtssMacsecConfigSecyRxSc6PeerMac,
                  vtssMacsecConfigSecyRxSc6Sa1Configured,
                  vtssMacsecConfigSecyRxSc6Sa1Active,
                  vtssMacsecConfigSecyRxSc6Sa1LowestPN,
                  vtssMacsecConfigSecyRxSc6Sa1Key,
                  vtssMacsecConfigSecyRxSc6Sa1Salt,
                  vtssMacsecConfigSecyRxSc6Sa2Configured,
                  vtssMacsecConfigSecyRxSc6Sa2Active,
                  vtssMacsecConfigSecyRxSc6Sa2LowestPN,
                  vtssMacsecConfigSecyRxSc6Sa2Key,
                  vtssMacsecConfigSecyRxSc6Sa2Salt,
                  vtssMacsecConfigSecyRxSc6Sa3Configured,
                  vtssMacsecConfigSecyRxSc6Sa3Active,
                  vtssMacsecConfigSecyRxSc6Sa3LowestPN,
                  vtssMacsecConfigSecyRxSc6Sa3Key,
                  vtssMacsecConfigSecyRxSc6Sa3Salt,
                  vtssMacsecConfigSecyRxSc6Sa4Configured,
                  vtssMacsecConfigSecyRxSc6Sa4Active,
                  vtssMacsecConfigSecyRxSc6Sa4LowestPN,
                  vtssMacsecConfigSecyRxSc6Sa4Key,
                  vtssMacsecConfigSecyRxSc6Sa4Salt,
                  vtssMacsecConfigSecyRxSc7Configured,
                  vtssMacsecConfigSecyRxSc7PeerMac,
                  vtssMacsecConfigSecyRxSc7Sa1Configured,
                  vtssMacsecConfigSecyRxSc7Sa1Active,
                  vtssMacsecConfigSecyRxSc7Sa1LowestPN,
                  vtssMacsecConfigSecyRxSc7Sa1Key,
                  vtssMacsecConfigSecyRxSc7Sa1Salt,
                  vtssMacsecConfigSecyRxSc7Sa2Configured,
                  vtssMacsecConfigSecyRxSc7Sa2Active,
                  vtssMacsecConfigSecyRxSc7Sa2LowestPN,
                  vtssMacsecConfigSecyRxSc7Sa2Key,
                  vtssMacsecConfigSecyRxSc7Sa2Salt,
                  vtssMacsecConfigSecyRxSc7Sa3Configured,
                  vtssMacsecConfigSecyRxSc7Sa3Active,
                  vtssMacsecConfigSecyRxSc7Sa3LowestPN,
                  vtssMacsecConfigSecyRxSc7Sa3Key,
                  vtssMacsecConfigSecyRxSc7Sa3Salt,
                  vtssMacsecConfigSecyRxSc7Sa4Configured,
                  vtssMacsecConfigSecyRxSc7Sa4Active,
                  vtssMacsecConfigSecyRxSc7Sa4LowestPN,
                  vtssMacsecConfigSecyRxSc7Sa4Key,
                  vtssMacsecConfigSecyRxSc7Sa4Salt,
                  vtssMacsecConfigSecyRxSc8Configured,
                  vtssMacsecConfigSecyRxSc8PeerMac,
                  vtssMacsecConfigSecyRxSc8Sa1Configured,
                  vtssMacsecConfigSecyRxSc8Sa1Active,
                  vtssMacsecConfigSecyRxSc8Sa1LowestPN,
                  vtssMacsecConfigSecyRxSc8Sa1Key,
                  vtssMacsecConfigSecyRxSc8Sa1Salt,
                  vtssMacsecConfigSecyRxSc8Sa2Configured,
                  vtssMacsecConfigSecyRxSc8Sa2Active,
                  vtssMacsecConfigSecyRxSc8Sa2LowestPN,
                  vtssMacsecConfigSecyRxSc8Sa2Key,
                  vtssMacsecConfigSecyRxSc8Sa2Salt,
                  vtssMacsecConfigSecyRxSc8Sa3Configured,
                  vtssMacsecConfigSecyRxSc8Sa3Active,
                  vtssMacsecConfigSecyRxSc8Sa3LowestPN,
                  vtssMacsecConfigSecyRxSc8Sa3Key,
                  vtssMacsecConfigSecyRxSc8Sa3Salt,
                  vtssMacsecConfigSecyRxSc8Sa4Configured,
                  vtssMacsecConfigSecyRxSc8Sa4Active,
                  vtssMacsecConfigSecyRxSc8Sa4LowestPN,
                  vtssMacsecConfigSecyRxSc8Sa4Key,
                  vtssMacsecConfigSecyRxSc8Sa4Salt,
                  vtssMacsecConfigSecyAction }
    STATUS      current
    DESCRIPTION
        "A collection of objects."
    ::= { vtssMacsecMibGroups 4 }

vtssMacsecConfigSecyRowEditorInfoGroup OBJECT-GROUP
    OBJECTS     { vtssMacsecConfigSecyRowEditorIfIndex,
                  vtssMacsecConfigSecyRowEditorSecyId,
                  vtssMacsecConfigSecyRowEditorAdminActive,
                  vtssMacsecConfigSecyRowEditorVirtualPortId,
                  vtssMacsecConfigSecyRowEditorCipherSuite,
                  vtssMacsecConfigSecyRowEditorConfidentialityOffset,
                  vtssMacsecConfigSecyRowEditorTxProtectFrames,
                  vtssMacsecConfigSecyRowEditorTxAlwaysIncludeSci,
                  vtssMacsecConfigSecyRowEditorTxUseES,
                  vtssMacsecConfigSecyRowEditorTxUseSCB,
                  vtssMacsecConfigSecyRowEditorRxFrameValidation,
                  vtssMacsecConfigSecyRowEditorRxReplayProtect,
                  vtssMacsecConfigSecyRowEditorRxReplayWindow,
                  vtssMacsecConfigSecyRowEditorTxScConfigured,
                  vtssMacsecConfigSecyRowEditorTxScMacType,
                  vtssMacsecConfigSecyRowEditorTxScCustomMac,
                  vtssMacsecConfigSecyRowEditorTxSa1Configured,
                  vtssMacsecConfigSecyRowEditorTxSa1Active,
                  vtssMacsecConfigSecyRowEditorTxSa1NextPN,
                  vtssMacsecConfigSecyRowEditorTxSa1Encrypt,
                  vtssMacsecConfigSecyRowEditorTxSa1Key,
                  vtssMacsecConfigSecyRowEditorTxSa1Salt,
                  vtssMacsecConfigSecyRowEditorTxSa2Configured,
                  vtssMacsecConfigSecyRowEditorTxSa2Active,
                  vtssMacsecConfigSecyRowEditorTxSa2NextPN,
                  vtssMacsecConfigSecyRowEditorTxSa2Encrypt,
                  vtssMacsecConfigSecyRowEditorTxSa2Key,
                  vtssMacsecConfigSecyRowEditorTxSa2Salt,
                  vtssMacsecConfigSecyRowEditorTxSa3Configured,
                  vtssMacsecConfigSecyRowEditorTxSa3Active,
                  vtssMacsecConfigSecyRowEditorTxSa3NextPN,
                  vtssMacsecConfigSecyRowEditorTxSa3Encrypt,
                  vtssMacsecConfigSecyRowEditorTxSa3Key,
                  vtssMacsecConfigSecyRowEditorTxSa3Salt,
                  vtssMacsecConfigSecyRowEditorTxSa4Configured,
                  vtssMacsecConfigSecyRowEditorTxSa4Active,
                  vtssMacsecConfigSecyRowEditorTxSa4NextPN,
                  vtssMacsecConfigSecyRowEditorTxSa4Encrypt,
                  vtssMacsecConfigSecyRowEditorTxSa4Key,
                  vtssMacsecConfigSecyRowEditorTxSa4Salt,
                  vtssMacsecConfigSecyRowEditorRxSc1Configured,
                  vtssMacsecConfigSecyRowEditorRxSc1PeerMac,
                  vtssMacsecConfigSecyRowEditorRxSc1Sa1Configured,
                  vtssMacsecConfigSecyRowEditorRxSc1Sa1Active,
                  vtssMacsecConfigSecyRowEditorRxSc1Sa1LowestPN,
                  vtssMacsecConfigSecyRowEditorRxSc1Sa1Key,
                  vtssMacsecConfigSecyRowEditorRxSc1Sa1Salt,
                  vtssMacsecConfigSecyRowEditorRxSc1Sa2Configured,
                  vtssMacsecConfigSecyRowEditorRxSc1Sa2Active,
                  vtssMacsecConfigSecyRowEditorRxSc1Sa2LowestPN,
                  vtssMacsecConfigSecyRowEditorRxSc1Sa2Key,
                  vtssMacsecConfigSecyRowEditorRxSc1Sa2Salt,
                  vtssMacsecConfigSecyRowEditorRxSc1Sa3Configured,
                  vtssMacsecConfigSecyRowEditorRxSc1Sa3Active,
                  vtssMacsecConfigSecyRowEditorRxSc1Sa3LowestPN,
                  vtssMacsecConfigSecyRowEditorRxSc1Sa3Key,
                  vtssMacsecConfigSecyRowEditorRxSc1Sa3Salt,
                  vtssMacsecConfigSecyRowEditorRxSc1Sa4Configured,
                  vtssMacsecConfigSecyRowEditorRxSc1Sa4Active,
                  vtssMacsecConfigSecyRowEditorRxSc1Sa4LowestPN,
                  vtssMacsecConfigSecyRowEditorRxSc1Sa4Key,
                  vtssMacsecConfigSecyRowEditorRxSc1Sa4Salt,
                  vtssMacsecConfigSecyRowEditorRxSc2Configured,
                  vtssMacsecConfigSecyRowEditorRxSc2PeerMac,
                  vtssMacsecConfigSecyRowEditorRxSc2Sa1Configured,
                  vtssMacsecConfigSecyRowEditorRxSc2Sa1Active,
                  vtssMacsecConfigSecyRowEditorRxSc2Sa1LowestPN,
                  vtssMacsecConfigSecyRowEditorRxSc2Sa1Key,
                  vtssMacsecConfigSecyRowEditorRxSc2Sa1Salt,
                  vtssMacsecConfigSecyRowEditorRxSc2Sa2Configured,
                  vtssMacsecConfigSecyRowEditorRxSc2Sa2Active,
                  vtssMacsecConfigSecyRowEditorRxSc2Sa2LowestPN,
                  vtssMacsecConfigSecyRowEditorRxSc2Sa2Key,
                  vtssMacsecConfigSecyRowEditorRxSc2Sa2Salt,
                  vtssMacsecConfigSecyRowEditorRxSc2Sa3Configured,
                  vtssMacsecConfigSecyRowEditorRxSc2Sa3Active,
                  vtssMacsecConfigSecyRowEditorRxSc2Sa3LowestPN,
                  vtssMacsecConfigSecyRowEditorRxSc2Sa3Key,
                  vtssMacsecConfigSecyRowEditorRxSc2Sa3Salt,
                  vtssMacsecConfigSecyRowEditorRxSc2Sa4Configured,
                  vtssMacsecConfigSecyRowEditorRxSc2Sa4Active,
                  vtssMacsecConfigSecyRowEditorRxSc2Sa4LowestPN,
                  vtssMacsecConfigSecyRowEditorRxSc2Sa4Key,
                  vtssMacsecConfigSecyRowEditorRxSc2Sa4Salt,
                  vtssMacsecConfigSecyRowEditorRxSc3Configured,
                  vtssMacsecConfigSecyRowEditorRxSc3PeerMac,
                  vtssMacsecConfigSecyRowEditorRxSc3Sa1Configured,
                  vtssMacsecConfigSecyRowEditorRxSc3Sa1Active,
                  vtssMacsecConfigSecyRowEditorRxSc3Sa1LowestPN,
                  vtssMacsecConfigSecyRowEditorRxSc3Sa1Key,
                  vtssMacsecConfigSecyRowEditorRxSc3Sa1Salt,
                  vtssMacsecConfigSecyRowEditorRxSc3Sa2Configured,
                  vtssMacsecConfigSecyRowEditorRxSc3Sa2Active,
                  vtssMacsecConfigSecyRowEditorRxSc3Sa2LowestPN,
                  vtssMacsecConfigSecyRowEditorRxSc3Sa2Key,
                  vtssMacsecConfigSecyRowEditorRxSc3Sa2Salt,
                  vtssMacsecConfigSecyRowEditorRxSc3Sa3Configured,
                  vtssMacsecConfigSecyRowEditorRxSc3Sa3Active,
                  vtssMacsecConfigSecyRowEditorRxSc3Sa3LowestPN,
                  vtssMacsecConfigSecyRowEditorRxSc3Sa3Key,
                  vtssMacsecConfigSecyRowEditorRxSc3Sa3Salt,
                  vtssMacsecConfigSecyRowEditorRxSc3Sa4Configured,
                  vtssMacsecConfigSecyRowEditorRxSc3Sa4Active,
                  vtssMacsecConfigSecyRowEditorRxSc3Sa4LowestPN,
                  vtssMacsecConfigSecyRowEditorRxSc3Sa4Key,
                  vtssMacsecConfigSecyRowEditorRxSc3Sa4Salt,
                  vtssMacsecConfigSecyRowEditorRxSc4Configured,
                  vtssMacsecConfigSecyRowEditorRxSc4PeerMac,
                  vtssMacsecConfigSecyRowEditorRxSc4Sa1Configured,
                  vtssMacsecConfigSecyRowEditorRxSc4Sa1Active,
                  vtssMacsecConfigSecyRowEditorRxSc4Sa1LowestPN,
                  vtssMacsecConfigSecyRowEditorRxSc4Sa1Key,
                  vtssMacsecConfigSecyRowEditorRxSc4Sa1Salt,
                  vtssMacsecConfigSecyRowEditorRxSc4Sa2Configured,
                  vtssMacsecConfigSecyRowEditorRxSc4Sa2Active,
                  vtssMacsecConfigSecyRowEditorRxSc4Sa2LowestPN,
                  vtssMacsecConfigSecyRowEditorRxSc4Sa2Key,
                  vtssMacsecConfigSecyRowEditorRxSc4Sa2Salt,
                  vtssMacsecConfigSecyRowEditorRxSc4Sa3Configured,
                  vtssMacsecConfigSecyRowEditorRxSc4Sa3Active,
                  vtssMacsecConfigSecyRowEditorRxSc4Sa3LowestPN,
                  vtssMacsecConfigSecyRowEditorRxSc4Sa3Key,
                  vtssMacsecConfigSecyRowEditorRxSc4Sa3Salt,
                  vtssMacsecConfigSecyRowEditorRxSc4Sa4Configured,
                  vtssMacsecConfigSecyRowEditorRxSc4Sa4Active,
                  vtssMacsecConfigSecyRowEditorRxSc4Sa4LowestPN,
                  vtssMacsecConfigSecyRowEditorRxSc4Sa4Key,
                  vtssMacsecConfigSecyRowEditorRxSc4Sa4Salt,
                  vtssMacsecConfigSecyRowEditorRxSc5Configured,
                  vtssMacsecConfigSecyRowEditorRxSc5PeerMac,
                  vtssMacsecConfigSecyRowEditorRxSc5Sa1Configured,
                  vtssMacsecConfigSecyRowEditorRxSc5Sa1Active,
                  vtssMacsecConfigSecyRowEditorRxSc5Sa1LowestPN,
                  vtssMacsecConfigSecyRowEditorRxSc5Sa1Key,
                  vtssMacsecConfigSecyRowEditorRxSc5Sa1Salt,
                  vtssMacsecConfigSecyRowEditorRxSc5Sa2Configured,
                  vtssMacsecConfigSecyRowEditorRxSc5Sa2Active,
                  vtssMacsecConfigSecyRowEditorRxSc5Sa2LowestPN,
                  vtssMacsecConfigSecyRowEditorRxSc5Sa2Key,
                  vtssMacsecConfigSecyRowEditorRxSc5Sa2Salt,
                  vtssMacsecConfigSecyRowEditorRxSc5Sa3Configured,
                  vtssMacsecConfigSecyRowEditorRxSc5Sa3Active,
                  vtssMacsecConfigSecyRowEditorRxSc5Sa3LowestPN,
                  vtssMacsecConfigSecyRowEditorRxSc5Sa3Key,
                  vtssMacsecConfigSecyRowEditorRxSc5Sa3Salt,
                  vtssMacsecConfigSecyRowEditorRxSc5Sa4Configured,
                  vtssMacsecConfigSecyRowEditorRxSc5Sa4Active,
                  vtssMacsecConfigSecyRowEditorRxSc5Sa4LowestPN,
                  vtssMacsecConfigSecyRowEditorRxSc5Sa4Key,
                  vtssMacsecConfigSecyRowEditorRxSc5Sa4Salt,
                  vtssMacsecConfigSecyRowEditorRxSc6Configured,
                  vtssMacsecConfigSecyRowEditorRxSc6PeerMac,
                  vtssMacsecConfigSecyRowEditorRxSc6Sa1Configured,
                  vtssMacsecConfigSecyRowEditorRxSc6Sa1Active,
                  vtssMacsecConfigSecyRowEditorRxSc6Sa1LowestPN,
                  vtssMacsecConfigSecyRowEditorRxSc6Sa1Key,
                  vtssMacsecConfigSecyRowEditorRxSc6Sa1Salt,
                  vtssMacsecConfigSecyRowEditorRxSc6Sa2Configured,
                  vtssMacsecConfigSecyRowEditorRxSc6Sa2Active,
                  vtssMacsecConfigSecyRowEditorRxSc6Sa2LowestPN,
                  vtssMacsecConfigSecyRowEditorRxSc6Sa2Key,
                  vtssMacsecConfigSecyRowEditorRxSc6Sa2Salt,
                  vtssMacsecConfigSecyRowEditorRxSc6Sa3Configured,
                  vtssMacsecConfigSecyRowEditorRxSc6Sa3Active,
                  vtssMacsecConfigSecyRowEditorRxSc6Sa3LowestPN,
                  vtssMacsecConfigSecyRowEditorRxSc6Sa3Key,
                  vtssMacsecConfigSecyRowEditorRxSc6Sa3Salt,
                  vtssMacsecConfigSecyRowEditorRxSc6Sa4Configured,
                  vtssMacsecConfigSecyRowEditorRxSc6Sa4Active,
                  vtssMacsecConfigSecyRowEditorRxSc6Sa4LowestPN,
                  vtssMacsecConfigSecyRowEditorRxSc6Sa4Key,
                  vtssMacsecConfigSecyRowEditorRxSc6Sa4Salt,
                  vtssMacsecConfigSecyRowEditorRxSc7Configured,
                  vtssMacsecConfigSecyRowEditorRxSc7PeerMac,
                  vtssMacsecConfigSecyRowEditorRxSc7Sa1Configured,
                  vtssMacsecConfigSecyRowEditorRxSc7Sa1Active,
                  vtssMacsecConfigSecyRowEditorRxSc7Sa1LowestPN,
                  vtssMacsecConfigSecyRowEditorRxSc7Sa1Key,
                  vtssMacsecConfigSecyRowEditorRxSc7Sa1Salt,
                  vtssMacsecConfigSecyRowEditorRxSc7Sa2Configured,
                  vtssMacsecConfigSecyRowEditorRxSc7Sa2Active,
                  vtssMacsecConfigSecyRowEditorRxSc7Sa2LowestPN,
                  vtssMacsecConfigSecyRowEditorRxSc7Sa2Key,
                  vtssMacsecConfigSecyRowEditorRxSc7Sa2Salt,
                  vtssMacsecConfigSecyRowEditorRxSc7Sa3Configured,
                  vtssMacsecConfigSecyRowEditorRxSc7Sa3Active,
                  vtssMacsecConfigSecyRowEditorRxSc7Sa3LowestPN,
                  vtssMacsecConfigSecyRowEditorRxSc7Sa3Key,
                  vtssMacsecConfigSecyRowEditorRxSc7Sa3Salt,
                  vtssMacsecConfigSecyRowEditorRxSc7Sa4Configured,
                  vtssMacsecConfigSecyRowEditorRxSc7Sa4Active,
                  vtssMacsecConfigSecyRowEditorRxSc7Sa4LowestPN,
                  vtssMacsecConfigSecyRowEditorRxSc7Sa4Key,
                  vtssMacsecConfigSecyRowEditorRxSc7Sa4Salt,
                  vtssMacsecConfigSecyRowEditorRxSc8Configured,
                  vtssMacsecConfigSecyRowEditorRxSc8PeerMac,
                  vtssMacsecConfigSecyRowEditorRxSc8Sa1Configured,
                  vtssMacsecConfigSecyRowEditorRxSc8Sa1Active,
                  vtssMacsecConfigSecyRowEditorRxSc8Sa1LowestPN,
                  vtssMacsecConfigSecyRowEditorRxSc8Sa1Key,
                  vtssMacsecConfigSecyRowEditorRxSc8Sa1Salt,
                  vtssMacsecConfigSecyRowEditorRxSc8Sa2Configured,
                  vtssMacsecConfigSecyRowEditorRxSc8Sa2Active,
                  vtssMacsecConfigSecyRowEditorRxSc8Sa2LowestPN,
                  vtssMacsecConfigSecyRowEditorRxSc8Sa2Key,
                  vtssMacsecConfigSecyRowEditorRxSc8Sa2Salt,
                  vtssMacsecConfigSecyRowEditorRxSc8Sa3Configured,
                  vtssMacsecConfigSecyRowEditorRxSc8Sa3Active,
                  vtssMacsecConfigSecyRowEditorRxSc8Sa3LowestPN,
                  vtssMacsecConfigSecyRowEditorRxSc8Sa3Key,
                  vtssMacsecConfigSecyRowEditorRxSc8Sa3Salt,
                  vtssMacsecConfigSecyRowEditorRxSc8Sa4Configured,
                  vtssMacsecConfigSecyRowEditorRxSc8Sa4Active,
                  vtssMacsecConfigSecyRowEditorRxSc8Sa4LowestPN,
                  vtssMacsecConfigSecyRowEditorRxSc8Sa4Key,
                  vtssMacsecConfigSecyRowEditorRxSc8Sa4Salt,
                  vtssMacsecConfigSecyRowEditorAction }
    STATUS      current
    DESCRIPTION
        "A collection of objects."
    ::= { vtssMacsecMibGroups 5 }

vtssMacsecStatusSecyTableInfoGroup OBJECT-GROUP
    OBJECTS     { vtssMacsecStatusSecyIfIndex,
                  vtssMacsecStatusSecySecyId,
                  vtssMacsecStatusSecyUptimeSeconds,
                  vtssMacsecStatusSecyInstalled,
                  vtssMacsecStatusSecyMacEnabled,
                  vtssMacsecStatusSecyMacOperational,
                  vtssMacsecStatusSecyOperPointToPointMac,
                  vtssMacsecStatusSecyTxScInstalled,
                  vtssMacsecStatusSecyTxScTransmitting,
                  vtssMacsecStatusSecyTxScEncodingSaIdx,
                  vtssMacsecStatusSecyTxScEncipheringSaIdx,
                  vtssMacsecStatusSecyTxScActiveSaIdx,
                  vtssMacsecStatusSecyTxScCreatedTime,
                  vtssMacsecStatusSecyTxScStartedTime,
                  vtssMacsecStatusSecyTxScStoppedTime,
                  vtssMacsecStatusSecyTxSa1Installed,
                  vtssMacsecStatusSecyTxSa1InUse,
                  vtssMacsecStatusSecyTxSa1NextPN,
                  vtssMacsecStatusSecyTxSa1CreatedTime,
                  vtssMacsecStatusSecyTxSa1StartedTime,
                  vtssMacsecStatusSecyTxSa1StoppedTime,
                  vtssMacsecStatusSecyTxSa2Installed,
                  vtssMacsecStatusSecyTxSa2InUse,
                  vtssMacsecStatusSecyTxSa2NextPN,
                  vtssMacsecStatusSecyTxSa2CreatedTime,
                  vtssMacsecStatusSecyTxSa2StartedTime,
                  vtssMacsecStatusSecyTxSa2StoppedTime,
                  vtssMacsecStatusSecyTxSa3Installed,
                  vtssMacsecStatusSecyTxSa3InUse,
                  vtssMacsecStatusSecyTxSa3NextPN,
                  vtssMacsecStatusSecyTxSa3CreatedTime,
                  vtssMacsecStatusSecyTxSa3StartedTime,
                  vtssMacsecStatusSecyTxSa3StoppedTime,
                  vtssMacsecStatusSecyTxSa4Installed,
                  vtssMacsecStatusSecyTxSa4InUse,
                  vtssMacsecStatusSecyTxSa4NextPN,
                  vtssMacsecStatusSecyTxSa4CreatedTime,
                  vtssMacsecStatusSecyTxSa4StartedTime,
                  vtssMacsecStatusSecyTxSa4StoppedTime,
                  vtssMacsecStatusSecyRxSc1Installed,
                  vtssMacsecStatusSecyRxSc1Receiving,
                  vtssMacsecStatusSecyRxSc1ActiveSaIdx,
                  vtssMacsecStatusSecyRxSc1CreatedTime,
                  vtssMacsecStatusSecyRxSc1StartedTime,
                  vtssMacsecStatusSecyRxSc1StoppedTime,
                  vtssMacsecStatusSecyRxSc1Sa1Installed,
                  vtssMacsecStatusSecyRxSc1Sa1InUse,
                  vtssMacsecStatusSecyRxSc1Sa1NextPN,
                  vtssMacsecStatusSecyRxSc1Sa1LowestPN,
                  vtssMacsecStatusSecyRxSc1Sa1CreatedTime,
                  vtssMacsecStatusSecyRxSc1Sa1StartedTime,
                  vtssMacsecStatusSecyRxSc1Sa1StoppedTime,
                  vtssMacsecStatusSecyRxSc1Sa2Installed,
                  vtssMacsecStatusSecyRxSc1Sa2InUse,
                  vtssMacsecStatusSecyRxSc1Sa2NextPN,
                  vtssMacsecStatusSecyRxSc1Sa2LowestPN,
                  vtssMacsecStatusSecyRxSc1Sa2CreatedTime,
                  vtssMacsecStatusSecyRxSc1Sa2StartedTime,
                  vtssMacsecStatusSecyRxSc1Sa2StoppedTime,
                  vtssMacsecStatusSecyRxSc1Sa3Installed,
                  vtssMacsecStatusSecyRxSc1Sa3InUse,
                  vtssMacsecStatusSecyRxSc1Sa3NextPN,
                  vtssMacsecStatusSecyRxSc1Sa3LowestPN,
                  vtssMacsecStatusSecyRxSc1Sa3CreatedTime,
                  vtssMacsecStatusSecyRxSc1Sa3StartedTime,
                  vtssMacsecStatusSecyRxSc1Sa3StoppedTime,
                  vtssMacsecStatusSecyRxSc1Sa4Installed,
                  vtssMacsecStatusSecyRxSc1Sa4InUse,
                  vtssMacsecStatusSecyRxSc1Sa4NextPN,
                  vtssMacsecStatusSecyRxSc1Sa4LowestPN,
                  vtssMacsecStatusSecyRxSc1Sa4CreatedTime,
                  vtssMacsecStatusSecyRxSc1Sa4StartedTime,
                  vtssMacsecStatusSecyRxSc1Sa4StoppedTime,
                  vtssMacsecStatusSecyRxSc2Installed,
                  vtssMacsecStatusSecyRxSc2Receiving,
                  vtssMacsecStatusSecyRxSc2ActiveSaIdx,
                  vtssMacsecStatusSecyRxSc2CreatedTime,
                  vtssMacsecStatusSecyRxSc2StartedTime,
                  vtssMacsecStatusSecyRxSc2StoppedTime,
                  vtssMacsecStatusSecyRxSc2Sa1Installed,
                  vtssMacsecStatusSecyRxSc2Sa1InUse,
                  vtssMacsecStatusSecyRxSc2Sa1NextPN,
                  vtssMacsecStatusSecyRxSc2Sa1LowestPN,
                  vtssMacsecStatusSecyRxSc2Sa1CreatedTime,
                  vtssMacsecStatusSecyRxSc2Sa1StartedTime,
                  vtssMacsecStatusSecyRxSc2Sa1StoppedTime,
                  vtssMacsecStatusSecyRxSc2Sa2Installed,
                  vtssMacsecStatusSecyRxSc2Sa2InUse,
                  vtssMacsecStatusSecyRxSc2Sa2NextPN,
                  vtssMacsecStatusSecyRxSc2Sa2LowestPN,
                  vtssMacsecStatusSecyRxSc2Sa2CreatedTime,
                  vtssMacsecStatusSecyRxSc2Sa2StartedTime,
                  vtssMacsecStatusSecyRxSc2Sa2StoppedTime,
                  vtssMacsecStatusSecyRxSc2Sa3Installed,
                  vtssMacsecStatusSecyRxSc2Sa3InUse,
                  vtssMacsecStatusSecyRxSc2Sa3NextPN,
                  vtssMacsecStatusSecyRxSc2Sa3LowestPN,
                  vtssMacsecStatusSecyRxSc2Sa3CreatedTime,
                  vtssMacsecStatusSecyRxSc2Sa3StartedTime,
                  vtssMacsecStatusSecyRxSc2Sa3StoppedTime,
                  vtssMacsecStatusSecyRxSc2Sa4Installed,
                  vtssMacsecStatusSecyRxSc2Sa4InUse,
                  vtssMacsecStatusSecyRxSc2Sa4NextPN,
                  vtssMacsecStatusSecyRxSc2Sa4LowestPN,
                  vtssMacsecStatusSecyRxSc2Sa4CreatedTime,
                  vtssMacsecStatusSecyRxSc2Sa4StartedTime,
                  vtssMacsecStatusSecyRxSc2Sa4StoppedTime,
                  vtssMacsecStatusSecyRxSc3Installed,
                  vtssMacsecStatusSecyRxSc3Receiving,
                  vtssMacsecStatusSecyRxSc3ActiveSaIdx,
                  vtssMacsecStatusSecyRxSc3CreatedTime,
                  vtssMacsecStatusSecyRxSc3StartedTime,
                  vtssMacsecStatusSecyRxSc3StoppedTime,
                  vtssMacsecStatusSecyRxSc3Sa1Installed,
                  vtssMacsecStatusSecyRxSc3Sa1InUse,
                  vtssMacsecStatusSecyRxSc3Sa1NextPN,
                  vtssMacsecStatusSecyRxSc3Sa1LowestPN,
                  vtssMacsecStatusSecyRxSc3Sa1CreatedTime,
                  vtssMacsecStatusSecyRxSc3Sa1StartedTime,
                  vtssMacsecStatusSecyRxSc3Sa1StoppedTime,
                  vtssMacsecStatusSecyRxSc3Sa2Installed,
                  vtssMacsecStatusSecyRxSc3Sa2InUse,
                  vtssMacsecStatusSecyRxSc3Sa2NextPN,
                  vtssMacsecStatusSecyRxSc3Sa2LowestPN,
                  vtssMacsecStatusSecyRxSc3Sa2CreatedTime,
                  vtssMacsecStatusSecyRxSc3Sa2StartedTime,
                  vtssMacsecStatusSecyRxSc3Sa2StoppedTime,
                  vtssMacsecStatusSecyRxSc3Sa3Installed,
                  vtssMacsecStatusSecyRxSc3Sa3InUse,
                  vtssMacsecStatusSecyRxSc3Sa3NextPN,
                  vtssMacsecStatusSecyRxSc3Sa3LowestPN,
                  vtssMacsecStatusSecyRxSc3Sa3CreatedTime,
                  vtssMacsecStatusSecyRxSc3Sa3StartedTime,
                  vtssMacsecStatusSecyRxSc3Sa3StoppedTime,
                  vtssMacsecStatusSecyRxSc3Sa4Installed,
                  vtssMacsecStatusSecyRxSc3Sa4InUse,
                  vtssMacsecStatusSecyRxSc3Sa4NextPN,
                  vtssMacsecStatusSecyRxSc3Sa4LowestPN,
                  vtssMacsecStatusSecyRxSc3Sa4CreatedTime,
                  vtssMacsecStatusSecyRxSc3Sa4StartedTime,
                  vtssMacsecStatusSecyRxSc3Sa4StoppedTime,
                  vtssMacsecStatusSecyRxSc4Installed,
                  vtssMacsecStatusSecyRxSc4Receiving,
                  vtssMacsecStatusSecyRxSc4ActiveSaIdx,
                  vtssMacsecStatusSecyRxSc4CreatedTime,
                  vtssMacsecStatusSecyRxSc4StartedTime,
                  vtssMacsecStatusSecyRxSc4StoppedTime,
                  vtssMacsecStatusSecyRxSc4Sa1Installed,
                  vtssMacsecStatusSecyRxSc4Sa1InUse,
                  vtssMacsecStatusSecyRxSc4Sa1NextPN,
                  vtssMacsecStatusSecyRxSc4Sa1LowestPN,
                  vtssMacsecStatusSecyRxSc4Sa1CreatedTime,
                  vtssMacsecStatusSecyRxSc4Sa1StartedTime,
                  vtssMacsecStatusSecyRxSc4Sa1StoppedTime,
                  vtssMacsecStatusSecyRxSc4Sa2Installed,
                  vtssMacsecStatusSecyRxSc4Sa2InUse,
                  vtssMacsecStatusSecyRxSc4Sa2NextPN,
                  vtssMacsecStatusSecyRxSc4Sa2LowestPN,
                  vtssMacsecStatusSecyRxSc4Sa2CreatedTime,
                  vtssMacsecStatusSecyRxSc4Sa2StartedTime,
                  vtssMacsecStatusSecyRxSc4Sa2StoppedTime,
                  vtssMacsecStatusSecyRxSc4Sa3Installed,
                  vtssMacsecStatusSecyRxSc4Sa3InUse,
                  vtssMacsecStatusSecyRxSc4Sa3NextPN,
                  vtssMacsecStatusSecyRxSc4Sa3LowestPN,
                  vtssMacsecStatusSecyRxSc4Sa3CreatedTime,
                  vtssMacsecStatusSecyRxSc4Sa3StartedTime,
                  vtssMacsecStatusSecyRxSc4Sa3StoppedTime,
                  vtssMacsecStatusSecyRxSc4Sa4Installed,
                  vtssMacsecStatusSecyRxSc4Sa4InUse,
                  vtssMacsecStatusSecyRxSc4Sa4NextPN,
                  vtssMacsecStatusSecyRxSc4Sa4LowestPN,
                  vtssMacsecStatusSecyRxSc4Sa4CreatedTime,
                  vtssMacsecStatusSecyRxSc4Sa4StartedTime,
                  vtssMacsecStatusSecyRxSc4Sa4StoppedTime,
                  vtssMacsecStatusSecyRxSc5Installed,
                  vtssMacsecStatusSecyRxSc5Receiving,
                  vtssMacsecStatusSecyRxSc5ActiveSaIdx,
                  vtssMacsecStatusSecyRxSc5CreatedTime,
                  vtssMacsecStatusSecyRxSc5StartedTime,
                  vtssMacsecStatusSecyRxSc5StoppedTime,
                  vtssMacsecStatusSecyRxSc5Sa1Installed,
                  vtssMacsecStatusSecyRxSc5Sa1InUse,
                  vtssMacsecStatusSecyRxSc5Sa1NextPN,
                  vtssMacsecStatusSecyRxSc5Sa1LowestPN,
                  vtssMacsecStatusSecyRxSc5Sa1CreatedTime,
                  vtssMacsecStatusSecyRxSc5Sa1StartedTime,
                  vtssMacsecStatusSecyRxSc5Sa1StoppedTime,
                  vtssMacsecStatusSecyRxSc5Sa2Installed,
                  vtssMacsecStatusSecyRxSc5Sa2InUse,
                  vtssMacsecStatusSecyRxSc5Sa2NextPN,
                  vtssMacsecStatusSecyRxSc5Sa2LowestPN,
                  vtssMacsecStatusSecyRxSc5Sa2CreatedTime,
                  vtssMacsecStatusSecyRxSc5Sa2StartedTime,
                  vtssMacsecStatusSecyRxSc5Sa2StoppedTime,
                  vtssMacsecStatusSecyRxSc5Sa3Installed,
                  vtssMacsecStatusSecyRxSc5Sa3InUse,
                  vtssMacsecStatusSecyRxSc5Sa3NextPN,
                  vtssMacsecStatusSecyRxSc5Sa3LowestPN,
                  vtssMacsecStatusSecyRxSc5Sa3CreatedTime,
                  vtssMacsecStatusSecyRxSc5Sa3StartedTime,
                  vtssMacsecStatusSecyRxSc5Sa3StoppedTime,
                  vtssMacsecStatusSecyRxSc5Sa4Installed,
                  vtssMacsecStatusSecyRxSc5Sa4InUse,
                  vtssMacsecStatusSecyRxSc5Sa4NextPN,
                  vtssMacsecStatusSecyRxSc5Sa4LowestPN,
                  vtssMacsecStatusSecyRxSc5Sa4CreatedTime,
                  vtssMacsecStatusSecyRxSc5Sa4StartedTime,
                  vtssMacsecStatusSecyRxSc5Sa4StoppedTime,
                  vtssMacsecStatusSecyRxSc6Installed,
                  vtssMacsecStatusSecyRxSc6Receiving,
                  vtssMacsecStatusSecyRxSc6ActiveSaIdx,
                  vtssMacsecStatusSecyRxSc6CreatedTime,
                  vtssMacsecStatusSecyRxSc6StartedTime,
                  vtssMacsecStatusSecyRxSc6StoppedTime,
                  vtssMacsecStatusSecyRxSc6Sa1Installed,
                  vtssMacsecStatusSecyRxSc6Sa1InUse,
                  vtssMacsecStatusSecyRxSc6Sa1NextPN,
                  vtssMacsecStatusSecyRxSc6Sa1LowestPN,
                  vtssMacsecStatusSecyRxSc6Sa1CreatedTime,
                  vtssMacsecStatusSecyRxSc6Sa1StartedTime,
                  vtssMacsecStatusSecyRxSc6Sa1StoppedTime,
                  vtssMacsecStatusSecyRxSc6Sa2Installed,
                  vtssMacsecStatusSecyRxSc6Sa2InUse,
                  vtssMacsecStatusSecyRxSc6Sa2NextPN,
                  vtssMacsecStatusSecyRxSc6Sa2LowestPN,
                  vtssMacsecStatusSecyRxSc6Sa2CreatedTime,
                  vtssMacsecStatusSecyRxSc6Sa2StartedTime,
                  vtssMacsecStatusSecyRxSc6Sa2StoppedTime,
                  vtssMacsecStatusSecyRxSc6Sa3Installed,
                  vtssMacsecStatusSecyRxSc6Sa3InUse,
                  vtssMacsecStatusSecyRxSc6Sa3NextPN,
                  vtssMacsecStatusSecyRxSc6Sa3LowestPN,
                  vtssMacsecStatusSecyRxSc6Sa3CreatedTime,
                  vtssMacsecStatusSecyRxSc6Sa3StartedTime,
                  vtssMacsecStatusSecyRxSc6Sa3StoppedTime,
                  vtssMacsecStatusSecyRxSc6Sa4Installed,
                  vtssMacsecStatusSecyRxSc6Sa4InUse,
                  vtssMacsecStatusSecyRxSc6Sa4NextPN,
                  vtssMacsecStatusSecyRxSc6Sa4LowestPN,
                  vtssMacsecStatusSecyRxSc6Sa4CreatedTime,
                  vtssMacsecStatusSecyRxSc6Sa4StartedTime,
                  vtssMacsecStatusSecyRxSc6Sa4StoppedTime,
                  vtssMacsecStatusSecyRxSc7Installed,
                  vtssMacsecStatusSecyRxSc7Receiving,
                  vtssMacsecStatusSecyRxSc7ActiveSaIdx,
                  vtssMacsecStatusSecyRxSc7CreatedTime,
                  vtssMacsecStatusSecyRxSc7StartedTime,
                  vtssMacsecStatusSecyRxSc7StoppedTime,
                  vtssMacsecStatusSecyRxSc7Sa1Installed,
                  vtssMacsecStatusSecyRxSc7Sa1InUse,
                  vtssMacsecStatusSecyRxSc7Sa1NextPN,
                  vtssMacsecStatusSecyRxSc7Sa1LowestPN,
                  vtssMacsecStatusSecyRxSc7Sa1CreatedTime,
                  vtssMacsecStatusSecyRxSc7Sa1StartedTime,
                  vtssMacsecStatusSecyRxSc7Sa1StoppedTime,
                  vtssMacsecStatusSecyRxSc7Sa2Installed,
                  vtssMacsecStatusSecyRxSc7Sa2InUse,
                  vtssMacsecStatusSecyRxSc7Sa2NextPN,
                  vtssMacsecStatusSecyRxSc7Sa2LowestPN,
                  vtssMacsecStatusSecyRxSc7Sa2CreatedTime,
                  vtssMacsecStatusSecyRxSc7Sa2StartedTime,
                  vtssMacsecStatusSecyRxSc7Sa2StoppedTime,
                  vtssMacsecStatusSecyRxSc7Sa3Installed,
                  vtssMacsecStatusSecyRxSc7Sa3InUse,
                  vtssMacsecStatusSecyRxSc7Sa3NextPN,
                  vtssMacsecStatusSecyRxSc7Sa3LowestPN,
                  vtssMacsecStatusSecyRxSc7Sa3CreatedTime,
                  vtssMacsecStatusSecyRxSc7Sa3StartedTime,
                  vtssMacsecStatusSecyRxSc7Sa3StoppedTime,
                  vtssMacsecStatusSecyRxSc7Sa4Installed,
                  vtssMacsecStatusSecyRxSc7Sa4InUse,
                  vtssMacsecStatusSecyRxSc7Sa4NextPN,
                  vtssMacsecStatusSecyRxSc7Sa4LowestPN,
                  vtssMacsecStatusSecyRxSc7Sa4CreatedTime,
                  vtssMacsecStatusSecyRxSc7Sa4StartedTime,
                  vtssMacsecStatusSecyRxSc7Sa4StoppedTime,
                  vtssMacsecStatusSecyRxSc8Installed,
                  vtssMacsecStatusSecyRxSc8Receiving,
                  vtssMacsecStatusSecyRxSc8ActiveSaIdx,
                  vtssMacsecStatusSecyRxSc8CreatedTime,
                  vtssMacsecStatusSecyRxSc8StartedTime,
                  vtssMacsecStatusSecyRxSc8StoppedTime,
                  vtssMacsecStatusSecyRxSc8Sa1Installed,
                  vtssMacsecStatusSecyRxSc8Sa1InUse,
                  vtssMacsecStatusSecyRxSc8Sa1NextPN,
                  vtssMacsecStatusSecyRxSc8Sa1LowestPN,
                  vtssMacsecStatusSecyRxSc8Sa1CreatedTime,
                  vtssMacsecStatusSecyRxSc8Sa1StartedTime,
                  vtssMacsecStatusSecyRxSc8Sa1StoppedTime,
                  vtssMacsecStatusSecyRxSc8Sa2Installed,
                  vtssMacsecStatusSecyRxSc8Sa2InUse,
                  vtssMacsecStatusSecyRxSc8Sa2NextPN,
                  vtssMacsecStatusSecyRxSc8Sa2LowestPN,
                  vtssMacsecStatusSecyRxSc8Sa2CreatedTime,
                  vtssMacsecStatusSecyRxSc8Sa2StartedTime,
                  vtssMacsecStatusSecyRxSc8Sa2StoppedTime,
                  vtssMacsecStatusSecyRxSc8Sa3Installed,
                  vtssMacsecStatusSecyRxSc8Sa3InUse,
                  vtssMacsecStatusSecyRxSc8Sa3NextPN,
                  vtssMacsecStatusSecyRxSc8Sa3LowestPN,
                  vtssMacsecStatusSecyRxSc8Sa3CreatedTime,
                  vtssMacsecStatusSecyRxSc8Sa3StartedTime,
                  vtssMacsecStatusSecyRxSc8Sa3StoppedTime,
                  vtssMacsecStatusSecyRxSc8Sa4Installed,
                  vtssMacsecStatusSecyRxSc8Sa4InUse,
                  vtssMacsecStatusSecyRxSc8Sa4NextPN,
                  vtssMacsecStatusSecyRxSc8Sa4LowestPN,
                  vtssMacsecStatusSecyRxSc8Sa4CreatedTime,
                  vtssMacsecStatusSecyRxSc8Sa4StartedTime,
                  vtssMacsecStatusSecyRxSc8Sa4StoppedTime }
    STATUS      current
    DESCRIPTION
        "A collection of objects."
    ::= { vtssMacsecMibGroups 6 }

vtssMacsecControlStatisticsClearInfoGroup OBJECT-GROUP
    OBJECTS     { vtssMacsecControlStatisticsClearIfIndex,
                  vtssMacsecControlStatisticsClearWhat,
                  vtssMacsecControlStatisticsClearSecyId,
                  vtssMacsecControlStatisticsClearRxScIdx,
                  vtssMacsecControlStatisticsClearSaIdx }
    STATUS      current
    DESCRIPTION
        "A collection of objects."
    ::= { vtssMacsecMibGroups 7 }

vtssMacsecStatisticsPortTableInfoGroup OBJECT-GROUP
    OBJECTS     { vtssMacsecStatisticsPortIfIndex,
                  vtssMacsecStatisticsPortUncontrolledInPackets,
                  vtssMacsecStatisticsPortUncontrolledInOctets,
                  vtssMacsecStatisticsPortUncontrolledInUnicastPackets,
                  vtssMacsecStatisticsPortUncontrolledInMulticastPackets,
                  vtssMacsecStatisticsPortUncontrolledInBroadcastPackets,
                  vtssMacsecStatisticsPortUncontrolledInDiscards,
                  vtssMacsecStatisticsPortUncontrolledInErrors,
                  vtssMacsecStatisticsPortUncontrolledOutPackets,
                  vtssMacsecStatisticsPortUncontrolledOutOctets,
                  vtssMacsecStatisticsPortUncontrolledOutUnicastPackets,
                  vtssMacsecStatisticsPortUncontrolledOutMulticastPackets,
                  vtssMacsecStatisticsPortUncontrolledOutBroadcastPackets,
                  vtssMacsecStatisticsPortUncontrolledOutErrors,
                  vtssMacsecStatisticsPortCommonInPackets,
                  vtssMacsecStatisticsPortCommonInOctets,
                  vtssMacsecStatisticsPortCommonInUnicastPackets,
                  vtssMacsecStatisticsPortCommonInMulticastPackets,
                  vtssMacsecStatisticsPortCommonInBroadcastPackets,
                  vtssMacsecStatisticsPortCommonInDiscards,
                  vtssMacsecStatisticsPortCommonInErrors,
                  vtssMacsecStatisticsPortCommonOutPackets,
                  vtssMacsecStatisticsPortCommonOutOctets,
                  vtssMacsecStatisticsPortCommonOutUnicastPackets,
                  vtssMacsecStatisticsPortCommonOutMulticastPackets,
                  vtssMacsecStatisticsPortCommonOutBroadcastPackets,
                  vtssMacsecStatisticsPortCommonOutErrors }
    STATUS      current
    DESCRIPTION
        "A collection of objects."
    ::= { vtssMacsecMibGroups 8 }

vtssMacsecStatisticsSecyTableInfoGroup OBJECT-GROUP
    OBJECTS     { vtssMacsecStatisticsSecyIfIndex,
                  vtssMacsecStatisticsSecySecyId,
                  vtssMacsecStatisticsSecyControlledInPackets,
                  vtssMacsecStatisticsSecyControlledInOctets,
                  vtssMacsecStatisticsSecyControlledInUnicastPackets,
                  vtssMacsecStatisticsSecyControlledInMulticastPackets,
                  vtssMacsecStatisticsSecyControlledInBroadcastPackets,
                  vtssMacsecStatisticsSecyControlledInDiscards,
                  vtssMacsecStatisticsSecyControlledInErrors,
                  vtssMacsecStatisticsSecyControlledOutPackets,
                  vtssMacsecStatisticsSecyControlledOutOctets,
                  vtssMacsecStatisticsSecyControlledOutUnicastPackets,
                  vtssMacsecStatisticsSecyControlledOutMulticastPackets,
                  vtssMacsecStatisticsSecyControlledOutBroadcastPackets,
                  vtssMacsecStatisticsSecyControlledOutErrors,
                  vtssMacsecStatisticsSecySecyInPacketsUntagged,
                  vtssMacsecStatisticsSecySecyInPacketsNoTag,
                  vtssMacsecStatisticsSecySecyInPacketsBadTag,
                  vtssMacsecStatisticsSecySecyInPacketsUnknownSci,
                  vtssMacsecStatisticsSecySecyInPacketsNoSci,
                  vtssMacsecStatisticsSecySecyInPacketsOverrun,
                  vtssMacsecStatisticsSecySecyInOctetsValidated,
                  vtssMacsecStatisticsSecySecyInOctetsDecrypted,
                  vtssMacsecStatisticsSecySecyOutPacketsUntagged,
                  vtssMacsecStatisticsSecySecyOutPacketsTooLong,
                  vtssMacsecStatisticsSecySecyOutOctetsProtected,
                  vtssMacsecStatisticsSecySecyOutOctetsEncrypted,
                  vtssMacsecStatisticsSecyTxScOutPacketsProtected,
                  vtssMacsecStatisticsSecyTxScOutPacketsEncrypted,
                  vtssMacsecStatisticsSecyTxScOutOctetsProtected,
                  vtssMacsecStatisticsSecyTxScOutOctetsEncrypted,
                  vtssMacsecStatisticsSecyTxSa1OutPacketsProtected,
                  vtssMacsecStatisticsSecyTxSa1OutPacketsEncrypted,
                  vtssMacsecStatisticsSecyTxSa2OutPacketsProtected,
                  vtssMacsecStatisticsSecyTxSa2OutPacketsEncrypted,
                  vtssMacsecStatisticsSecyTxSa3OutPacketsProtected,
                  vtssMacsecStatisticsSecyTxSa3OutPacketsEncrypted,
                  vtssMacsecStatisticsSecyTxSa4OutPacketsProtected,
                  vtssMacsecStatisticsSecyTxSa4OutPacketsEncrypted,
                  vtssMacsecStatisticsSecyRxSc1InPacketsUnchecked,
                  vtssMacsecStatisticsSecyRxSc1InPacketsDelayed,
                  vtssMacsecStatisticsSecyRxSc1InPacketsLate,
                  vtssMacsecStatisticsSecyRxSc1InPacketsOk,
                  vtssMacsecStatisticsSecyRxSc1InPacketsInvalid,
                  vtssMacsecStatisticsSecyRxSc1InPacketsNotValid,
                  vtssMacsecStatisticsSecyRxSc1InPacketsNotUsingSa,
                  vtssMacsecStatisticsSecyRxSc1InPacketsUnusedSa,
                  vtssMacsecStatisticsSecyRxSc1InOctetsValidated,
                  vtssMacsecStatisticsSecyRxSc1InOctetsDecrypted,
                  vtssMacsecStatisticsSecyRxSc1Sa1InPacketsOk,
                  vtssMacsecStatisticsSecyRxSc1Sa1InPacketsInvalid,
                  vtssMacsecStatisticsSecyRxSc1Sa1InPacketsNotValid,
                  vtssMacsecStatisticsSecyRxSc1Sa1InPacketsNotUsingSa,
                  vtssMacsecStatisticsSecyRxSc1Sa1InPacketsUnusedSa,
                  vtssMacsecStatisticsSecyRxSc1Sa1InPacketsUnchecked,
                  vtssMacsecStatisticsSecyRxSc1Sa1InPacketsDelayed,
                  vtssMacsecStatisticsSecyRxSc1Sa1InPacketsLate,
                  vtssMacsecStatisticsSecyRxSc1Sa2InPacketsOk,
                  vtssMacsecStatisticsSecyRxSc1Sa2InPacketsInvalid,
                  vtssMacsecStatisticsSecyRxSc1Sa2InPacketsNotValid,
                  vtssMacsecStatisticsSecyRxSc1Sa2InPacketsNotUsingSa,
                  vtssMacsecStatisticsSecyRxSc1Sa2InPacketsUnusedSa,
                  vtssMacsecStatisticsSecyRxSc1Sa2InPacketsUnchecked,
                  vtssMacsecStatisticsSecyRxSc1Sa2InPacketsDelayed,
                  vtssMacsecStatisticsSecyRxSc1Sa2InPacketsLate,
                  vtssMacsecStatisticsSecyRxSc1Sa3InPacketsOk,
                  vtssMacsecStatisticsSecyRxSc1Sa3InPacketsInvalid,
                  vtssMacsecStatisticsSecyRxSc1Sa3InPacketsNotValid,
                  vtssMacsecStatisticsSecyRxSc1Sa3InPacketsNotUsingSa,
                  vtssMacsecStatisticsSecyRxSc1Sa3InPacketsUnusedSa,
                  vtssMacsecStatisticsSecyRxSc1Sa3InPacketsUnchecked,
                  vtssMacsecStatisticsSecyRxSc1Sa3InPacketsDelayed,
                  vtssMacsecStatisticsSecyRxSc1Sa3InPacketsLate,
                  vtssMacsecStatisticsSecyRxSc1Sa4InPacketsOk,
                  vtssMacsecStatisticsSecyRxSc1Sa4InPacketsInvalid,
                  vtssMacsecStatisticsSecyRxSc1Sa4InPacketsNotValid,
                  vtssMacsecStatisticsSecyRxSc1Sa4InPacketsNotUsingSa,
                  vtssMacsecStatisticsSecyRxSc1Sa4InPacketsUnusedSa,
                  vtssMacsecStatisticsSecyRxSc1Sa4InPacketsUnchecked,
                  vtssMacsecStatisticsSecyRxSc1Sa4InPacketsDelayed,
                  vtssMacsecStatisticsSecyRxSc1Sa4InPacketsLate,
                  vtssMacsecStatisticsSecyRxSc2InPacketsUnchecked,
                  vtssMacsecStatisticsSecyRxSc2InPacketsDelayed,
                  vtssMacsecStatisticsSecyRxSc2InPacketsLate,
                  vtssMacsecStatisticsSecyRxSc2InPacketsOk,
                  vtssMacsecStatisticsSecyRxSc2InPacketsInvalid,
                  vtssMacsecStatisticsSecyRxSc2InPacketsNotValid,
                  vtssMacsecStatisticsSecyRxSc2InPacketsNotUsingSa,
                  vtssMacsecStatisticsSecyRxSc2InPacketsUnusedSa,
                  vtssMacsecStatisticsSecyRxSc2InOctetsValidated,
                  vtssMacsecStatisticsSecyRxSc2InOctetsDecrypted,
                  vtssMacsecStatisticsSecyRxSc2Sa1InPacketsOk,
                  vtssMacsecStatisticsSecyRxSc2Sa1InPacketsInvalid,
                  vtssMacsecStatisticsSecyRxSc2Sa1InPacketsNotValid,
                  vtssMacsecStatisticsSecyRxSc2Sa1InPacketsNotUsingSa,
                  vtssMacsecStatisticsSecyRxSc2Sa1InPacketsUnusedSa,
                  vtssMacsecStatisticsSecyRxSc2Sa1InPacketsUnchecked,
                  vtssMacsecStatisticsSecyRxSc2Sa1InPacketsDelayed,
                  vtssMacsecStatisticsSecyRxSc2Sa1InPacketsLate,
                  vtssMacsecStatisticsSecyRxSc2Sa2InPacketsOk,
                  vtssMacsecStatisticsSecyRxSc2Sa2InPacketsInvalid,
                  vtssMacsecStatisticsSecyRxSc2Sa2InPacketsNotValid,
                  vtssMacsecStatisticsSecyRxSc2Sa2InPacketsNotUsingSa,
                  vtssMacsecStatisticsSecyRxSc2Sa2InPacketsUnusedSa,
                  vtssMacsecStatisticsSecyRxSc2Sa2InPacketsUnchecked,
                  vtssMacsecStatisticsSecyRxSc2Sa2InPacketsDelayed,
                  vtssMacsecStatisticsSecyRxSc2Sa2InPacketsLate,
                  vtssMacsecStatisticsSecyRxSc2Sa3InPacketsOk,
                  vtssMacsecStatisticsSecyRxSc2Sa3InPacketsInvalid,
                  vtssMacsecStatisticsSecyRxSc2Sa3InPacketsNotValid,
                  vtssMacsecStatisticsSecyRxSc2Sa3InPacketsNotUsingSa,
                  vtssMacsecStatisticsSecyRxSc2Sa3InPacketsUnusedSa,
                  vtssMacsecStatisticsSecyRxSc2Sa3InPacketsUnchecked,
                  vtssMacsecStatisticsSecyRxSc2Sa3InPacketsDelayed,
                  vtssMacsecStatisticsSecyRxSc2Sa3InPacketsLate,
                  vtssMacsecStatisticsSecyRxSc2Sa4InPacketsOk,
                  vtssMacsecStatisticsSecyRxSc2Sa4InPacketsInvalid,
                  vtssMacsecStatisticsSecyRxSc2Sa4InPacketsNotValid,
                  vtssMacsecStatisticsSecyRxSc2Sa4InPacketsNotUsingSa,
                  vtssMacsecStatisticsSecyRxSc2Sa4InPacketsUnusedSa,
                  vtssMacsecStatisticsSecyRxSc2Sa4InPacketsUnchecked,
                  vtssMacsecStatisticsSecyRxSc2Sa4InPacketsDelayed,
                  vtssMacsecStatisticsSecyRxSc2Sa4InPacketsLate,
                  vtssMacsecStatisticsSecyRxSc3InPacketsUnchecked,
                  vtssMacsecStatisticsSecyRxSc3InPacketsDelayed,
                  vtssMacsecStatisticsSecyRxSc3InPacketsLate,
                  vtssMacsecStatisticsSecyRxSc3InPacketsOk,
                  vtssMacsecStatisticsSecyRxSc3InPacketsInvalid,
                  vtssMacsecStatisticsSecyRxSc3InPacketsNotValid,
                  vtssMacsecStatisticsSecyRxSc3InPacketsNotUsingSa,
                  vtssMacsecStatisticsSecyRxSc3InPacketsUnusedSa,
                  vtssMacsecStatisticsSecyRxSc3InOctetsValidated,
                  vtssMacsecStatisticsSecyRxSc3InOctetsDecrypted,
                  vtssMacsecStatisticsSecyRxSc3Sa1InPacketsOk,
                  vtssMacsecStatisticsSecyRxSc3Sa1InPacketsInvalid,
                  vtssMacsecStatisticsSecyRxSc3Sa1InPacketsNotValid,
                  vtssMacsecStatisticsSecyRxSc3Sa1InPacketsNotUsingSa,
                  vtssMacsecStatisticsSecyRxSc3Sa1InPacketsUnusedSa,
                  vtssMacsecStatisticsSecyRxSc3Sa1InPacketsUnchecked,
                  vtssMacsecStatisticsSecyRxSc3Sa1InPacketsDelayed,
                  vtssMacsecStatisticsSecyRxSc3Sa1InPacketsLate,
                  vtssMacsecStatisticsSecyRxSc3Sa2InPacketsOk,
                  vtssMacsecStatisticsSecyRxSc3Sa2InPacketsInvalid,
                  vtssMacsecStatisticsSecyRxSc3Sa2InPacketsNotValid,
                  vtssMacsecStatisticsSecyRxSc3Sa2InPacketsNotUsingSa,
                  vtssMacsecStatisticsSecyRxSc3Sa2InPacketsUnusedSa,
                  vtssMacsecStatisticsSecyRxSc3Sa2InPacketsUnchecked,
                  vtssMacsecStatisticsSecyRxSc3Sa2InPacketsDelayed,
                  vtssMacsecStatisticsSecyRxSc3Sa2InPacketsLate,
                  vtssMacsecStatisticsSecyRxSc3Sa3InPacketsOk,
                  vtssMacsecStatisticsSecyRxSc3Sa3InPacketsInvalid,
                  vtssMacsecStatisticsSecyRxSc3Sa3InPacketsNotValid,
                  vtssMacsecStatisticsSecyRxSc3Sa3InPacketsNotUsingSa,
                  vtssMacsecStatisticsSecyRxSc3Sa3InPacketsUnusedSa,
                  vtssMacsecStatisticsSecyRxSc3Sa3InPacketsUnchecked,
                  vtssMacsecStatisticsSecyRxSc3Sa3InPacketsDelayed,
                  vtssMacsecStatisticsSecyRxSc3Sa3InPacketsLate,
                  vtssMacsecStatisticsSecyRxSc3Sa4InPacketsOk,
                  vtssMacsecStatisticsSecyRxSc3Sa4InPacketsInvalid,
                  vtssMacsecStatisticsSecyRxSc3Sa4InPacketsNotValid,
                  vtssMacsecStatisticsSecyRxSc3Sa4InPacketsNotUsingSa,
                  vtssMacsecStatisticsSecyRxSc3Sa4InPacketsUnusedSa,
                  vtssMacsecStatisticsSecyRxSc3Sa4InPacketsUnchecked,
                  vtssMacsecStatisticsSecyRxSc3Sa4InPacketsDelayed,
                  vtssMacsecStatisticsSecyRxSc3Sa4InPacketsLate,
                  vtssMacsecStatisticsSecyRxSc4InPacketsUnchecked,
                  vtssMacsecStatisticsSecyRxSc4InPacketsDelayed,
                  vtssMacsecStatisticsSecyRxSc4InPacketsLate,
                  vtssMacsecStatisticsSecyRxSc4InPacketsOk,
                  vtssMacsecStatisticsSecyRxSc4InPacketsInvalid,
                  vtssMacsecStatisticsSecyRxSc4InPacketsNotValid,
                  vtssMacsecStatisticsSecyRxSc4InPacketsNotUsingSa,
                  vtssMacsecStatisticsSecyRxSc4InPacketsUnusedSa,
                  vtssMacsecStatisticsSecyRxSc4InOctetsValidated,
                  vtssMacsecStatisticsSecyRxSc4InOctetsDecrypted,
                  vtssMacsecStatisticsSecyRxSc4Sa1InPacketsOk,
                  vtssMacsecStatisticsSecyRxSc4Sa1InPacketsInvalid,
                  vtssMacsecStatisticsSecyRxSc4Sa1InPacketsNotValid,
                  vtssMacsecStatisticsSecyRxSc4Sa1InPacketsNotUsingSa,
                  vtssMacsecStatisticsSecyRxSc4Sa1InPacketsUnusedSa,
                  vtssMacsecStatisticsSecyRxSc4Sa1InPacketsUnchecked,
                  vtssMacsecStatisticsSecyRxSc4Sa1InPacketsDelayed,
                  vtssMacsecStatisticsSecyRxSc4Sa1InPacketsLate,
                  vtssMacsecStatisticsSecyRxSc4Sa2InPacketsOk,
                  vtssMacsecStatisticsSecyRxSc4Sa2InPacketsInvalid,
                  vtssMacsecStatisticsSecyRxSc4Sa2InPacketsNotValid,
                  vtssMacsecStatisticsSecyRxSc4Sa2InPacketsNotUsingSa,
                  vtssMacsecStatisticsSecyRxSc4Sa2InPacketsUnusedSa,
                  vtssMacsecStatisticsSecyRxSc4Sa2InPacketsUnchecked,
                  vtssMacsecStatisticsSecyRxSc4Sa2InPacketsDelayed,
                  vtssMacsecStatisticsSecyRxSc4Sa2InPacketsLate,
                  vtssMacsecStatisticsSecyRxSc4Sa3InPacketsOk,
                  vtssMacsecStatisticsSecyRxSc4Sa3InPacketsInvalid,
                  vtssMacsecStatisticsSecyRxSc4Sa3InPacketsNotValid,
                  vtssMacsecStatisticsSecyRxSc4Sa3InPacketsNotUsingSa,
                  vtssMacsecStatisticsSecyRxSc4Sa3InPacketsUnusedSa,
                  vtssMacsecStatisticsSecyRxSc4Sa3InPacketsUnchecked,
                  vtssMacsecStatisticsSecyRxSc4Sa3InPacketsDelayed,
                  vtssMacsecStatisticsSecyRxSc4Sa3InPacketsLate,
                  vtssMacsecStatisticsSecyRxSc4Sa4InPacketsOk,
                  vtssMacsecStatisticsSecyRxSc4Sa4InPacketsInvalid,
                  vtssMacsecStatisticsSecyRxSc4Sa4InPacketsNotValid,
                  vtssMacsecStatisticsSecyRxSc4Sa4InPacketsNotUsingSa,
                  vtssMacsecStatisticsSecyRxSc4Sa4InPacketsUnusedSa,
                  vtssMacsecStatisticsSecyRxSc4Sa4InPacketsUnchecked,
                  vtssMacsecStatisticsSecyRxSc4Sa4InPacketsDelayed,
                  vtssMacsecStatisticsSecyRxSc4Sa4InPacketsLate,
                  vtssMacsecStatisticsSecyRxSc5InPacketsUnchecked,
                  vtssMacsecStatisticsSecyRxSc5InPacketsDelayed,
                  vtssMacsecStatisticsSecyRxSc5InPacketsLate,
                  vtssMacsecStatisticsSecyRxSc5InPacketsOk,
                  vtssMacsecStatisticsSecyRxSc5InPacketsInvalid,
                  vtssMacsecStatisticsSecyRxSc5InPacketsNotValid,
                  vtssMacsecStatisticsSecyRxSc5InPacketsNotUsingSa,
                  vtssMacsecStatisticsSecyRxSc5InPacketsUnusedSa,
                  vtssMacsecStatisticsSecyRxSc5InOctetsValidated,
                  vtssMacsecStatisticsSecyRxSc5InOctetsDecrypted,
                  vtssMacsecStatisticsSecyRxSc5Sa1InPacketsOk,
                  vtssMacsecStatisticsSecyRxSc5Sa1InPacketsInvalid,
                  vtssMacsecStatisticsSecyRxSc5Sa1InPacketsNotValid,
                  vtssMacsecStatisticsSecyRxSc5Sa1InPacketsNotUsingSa,
                  vtssMacsecStatisticsSecyRxSc5Sa1InPacketsUnusedSa,
                  vtssMacsecStatisticsSecyRxSc5Sa1InPacketsUnchecked,
                  vtssMacsecStatisticsSecyRxSc5Sa1InPacketsDelayed,
                  vtssMacsecStatisticsSecyRxSc5Sa1InPacketsLate,
                  vtssMacsecStatisticsSecyRxSc5Sa2InPacketsOk,
                  vtssMacsecStatisticsSecyRxSc5Sa2InPacketsInvalid,
                  vtssMacsecStatisticsSecyRxSc5Sa2InPacketsNotValid,
                  vtssMacsecStatisticsSecyRxSc5Sa2InPacketsNotUsingSa,
                  vtssMacsecStatisticsSecyRxSc5Sa2InPacketsUnusedSa,
                  vtssMacsecStatisticsSecyRxSc5Sa2InPacketsUnchecked,
                  vtssMacsecStatisticsSecyRxSc5Sa2InPacketsDelayed,
                  vtssMacsecStatisticsSecyRxSc5Sa2InPacketsLate,
                  vtssMacsecStatisticsSecyRxSc5Sa3InPacketsOk,
                  vtssMacsecStatisticsSecyRxSc5Sa3InPacketsInvalid,
                  vtssMacsecStatisticsSecyRxSc5Sa3InPacketsNotValid,
                  vtssMacsecStatisticsSecyRxSc5Sa3InPacketsNotUsingSa,
                  vtssMacsecStatisticsSecyRxSc5Sa3InPacketsUnusedSa,
                  vtssMacsecStatisticsSecyRxSc5Sa3InPacketsUnchecked,
                  vtssMacsecStatisticsSecyRxSc5Sa3InPacketsDelayed,
                  vtssMacsecStatisticsSecyRxSc5Sa3InPacketsLate,
                  vtssMacsecStatisticsSecyRxSc5Sa4InPacketsOk,
                  vtssMacsecStatisticsSecyRxSc5Sa4InPacketsInvalid,
                  vtssMacsecStatisticsSecyRxSc5Sa4InPacketsNotValid,
                  vtssMacsecStatisticsSecyRxSc5Sa4InPacketsNotUsingSa,
                  vtssMacsecStatisticsSecyRxSc5Sa4InPacketsUnusedSa,
                  vtssMacsecStatisticsSecyRxSc5Sa4InPacketsUnchecked,
                  vtssMacsecStatisticsSecyRxSc5Sa4InPacketsDelayed,
                  vtssMacsecStatisticsSecyRxSc5Sa4InPacketsLate,
                  vtssMacsecStatisticsSecyRxSc6InPacketsUnchecked,
                  vtssMacsecStatisticsSecyRxSc6InPacketsDelayed,
                  vtssMacsecStatisticsSecyRxSc6InPacketsLate,
                  vtssMacsecStatisticsSecyRxSc6InPacketsOk,
                  vtssMacsecStatisticsSecyRxSc6InPacketsInvalid,
                  vtssMacsecStatisticsSecyRxSc6InPacketsNotValid,
                  vtssMacsecStatisticsSecyRxSc6InPacketsNotUsingSa,
                  vtssMacsecStatisticsSecyRxSc6InPacketsUnusedSa,
                  vtssMacsecStatisticsSecyRxSc6InOctetsValidated,
                  vtssMacsecStatisticsSecyRxSc6InOctetsDecrypted,
                  vtssMacsecStatisticsSecyRxSc6Sa1InPacketsOk,
                  vtssMacsecStatisticsSecyRxSc6Sa1InPacketsInvalid,
                  vtssMacsecStatisticsSecyRxSc6Sa1InPacketsNotValid,
                  vtssMacsecStatisticsSecyRxSc6Sa1InPacketsNotUsingSa,
                  vtssMacsecStatisticsSecyRxSc6Sa1InPacketsUnusedSa,
                  vtssMacsecStatisticsSecyRxSc6Sa1InPacketsUnchecked,
                  vtssMacsecStatisticsSecyRxSc6Sa1InPacketsDelayed,
                  vtssMacsecStatisticsSecyRxSc6Sa1InPacketsLate,
                  vtssMacsecStatisticsSecyRxSc6Sa2InPacketsOk,
                  vtssMacsecStatisticsSecyRxSc6Sa2InPacketsInvalid,
                  vtssMacsecStatisticsSecyRxSc6Sa2InPacketsNotValid,
                  vtssMacsecStatisticsSecyRxSc6Sa2InPacketsNotUsingSa,
                  vtssMacsecStatisticsSecyRxSc6Sa2InPacketsUnusedSa,
                  vtssMacsecStatisticsSecyRxSc6Sa2InPacketsUnchecked,
                  vtssMacsecStatisticsSecyRxSc6Sa2InPacketsDelayed,
                  vtssMacsecStatisticsSecyRxSc6Sa2InPacketsLate,
                  vtssMacsecStatisticsSecyRxSc6Sa3InPacketsOk,
                  vtssMacsecStatisticsSecyRxSc6Sa3InPacketsInvalid,
                  vtssMacsecStatisticsSecyRxSc6Sa3InPacketsNotValid,
                  vtssMacsecStatisticsSecyRxSc6Sa3InPacketsNotUsingSa,
                  vtssMacsecStatisticsSecyRxSc6Sa3InPacketsUnusedSa,
                  vtssMacsecStatisticsSecyRxSc6Sa3InPacketsUnchecked,
                  vtssMacsecStatisticsSecyRxSc6Sa3InPacketsDelayed,
                  vtssMacsecStatisticsSecyRxSc6Sa3InPacketsLate,
                  vtssMacsecStatisticsSecyRxSc6Sa4InPacketsOk,
                  vtssMacsecStatisticsSecyRxSc6Sa4InPacketsInvalid,
                  vtssMacsecStatisticsSecyRxSc6Sa4InPacketsNotValid,
                  vtssMacsecStatisticsSecyRxSc6Sa4InPacketsNotUsingSa,
                  vtssMacsecStatisticsSecyRxSc6Sa4InPacketsUnusedSa,
                  vtssMacsecStatisticsSecyRxSc6Sa4InPacketsUnchecked,
                  vtssMacsecStatisticsSecyRxSc6Sa4InPacketsDelayed,
                  vtssMacsecStatisticsSecyRxSc6Sa4InPacketsLate,
                  vtssMacsecStatisticsSecyRxSc7InPacketsUnchecked,
                  vtssMacsecStatisticsSecyRxSc7InPacketsDelayed,
                  vtssMacsecStatisticsSecyRxSc7InPacketsLate,
                  vtssMacsecStatisticsSecyRxSc7InPacketsOk,
                  vtssMacsecStatisticsSecyRxSc7InPacketsInvalid,
                  vtssMacsecStatisticsSecyRxSc7InPacketsNotValid,
                  vtssMacsecStatisticsSecyRxSc7InPacketsNotUsingSa,
                  vtssMacsecStatisticsSecyRxSc7InPacketsUnusedSa,
                  vtssMacsecStatisticsSecyRxSc7InOctetsValidated,
                  vtssMacsecStatisticsSecyRxSc7InOctetsDecrypted,
                  vtssMacsecStatisticsSecyRxSc7Sa1InPacketsOk,
                  vtssMacsecStatisticsSecyRxSc7Sa1InPacketsInvalid,
                  vtssMacsecStatisticsSecyRxSc7Sa1InPacketsNotValid,
                  vtssMacsecStatisticsSecyRxSc7Sa1InPacketsNotUsingSa,
                  vtssMacsecStatisticsSecyRxSc7Sa1InPacketsUnusedSa,
                  vtssMacsecStatisticsSecyRxSc7Sa1InPacketsUnchecked,
                  vtssMacsecStatisticsSecyRxSc7Sa1InPacketsDelayed,
                  vtssMacsecStatisticsSecyRxSc7Sa1InPacketsLate,
                  vtssMacsecStatisticsSecyRxSc7Sa2InPacketsOk,
                  vtssMacsecStatisticsSecyRxSc7Sa2InPacketsInvalid,
                  vtssMacsecStatisticsSecyRxSc7Sa2InPacketsNotValid,
                  vtssMacsecStatisticsSecyRxSc7Sa2InPacketsNotUsingSa,
                  vtssMacsecStatisticsSecyRxSc7Sa2InPacketsUnusedSa,
                  vtssMacsecStatisticsSecyRxSc7Sa2InPacketsUnchecked,
                  vtssMacsecStatisticsSecyRxSc7Sa2InPacketsDelayed,
                  vtssMacsecStatisticsSecyRxSc7Sa2InPacketsLate,
                  vtssMacsecStatisticsSecyRxSc7Sa3InPacketsOk,
                  vtssMacsecStatisticsSecyRxSc7Sa3InPacketsInvalid,
                  vtssMacsecStatisticsSecyRxSc7Sa3InPacketsNotValid,
                  vtssMacsecStatisticsSecyRxSc7Sa3InPacketsNotUsingSa,
                  vtssMacsecStatisticsSecyRxSc7Sa3InPacketsUnusedSa,
                  vtssMacsecStatisticsSecyRxSc7Sa3InPacketsUnchecked,
                  vtssMacsecStatisticsSecyRxSc7Sa3InPacketsDelayed,
                  vtssMacsecStatisticsSecyRxSc7Sa3InPacketsLate,
                  vtssMacsecStatisticsSecyRxSc7Sa4InPacketsOk,
                  vtssMacsecStatisticsSecyRxSc7Sa4InPacketsInvalid,
                  vtssMacsecStatisticsSecyRxSc7Sa4InPacketsNotValid,
                  vtssMacsecStatisticsSecyRxSc7Sa4InPacketsNotUsingSa,
                  vtssMacsecStatisticsSecyRxSc7Sa4InPacketsUnusedSa,
                  vtssMacsecStatisticsSecyRxSc7Sa4InPacketsUnchecked,
                  vtssMacsecStatisticsSecyRxSc7Sa4InPacketsDelayed,
                  vtssMacsecStatisticsSecyRxSc7Sa4InPacketsLate,
                  vtssMacsecStatisticsSecyRxSc8InPacketsUnchecked,
                  vtssMacsecStatisticsSecyRxSc8InPacketsDelayed,
                  vtssMacsecStatisticsSecyRxSc8InPacketsLate,
                  vtssMacsecStatisticsSecyRxSc8InPacketsOk,
                  vtssMacsecStatisticsSecyRxSc8InPacketsInvalid,
                  vtssMacsecStatisticsSecyRxSc8InPacketsNotValid,
                  vtssMacsecStatisticsSecyRxSc8InPacketsNotUsingSa,
                  vtssMacsecStatisticsSecyRxSc8InPacketsUnusedSa,
                  vtssMacsecStatisticsSecyRxSc8InOctetsValidated,
                  vtssMacsecStatisticsSecyRxSc8InOctetsDecrypted,
                  vtssMacsecStatisticsSecyRxSc8Sa1InPacketsOk,
                  vtssMacsecStatisticsSecyRxSc8Sa1InPacketsInvalid,
                  vtssMacsecStatisticsSecyRxSc8Sa1InPacketsNotValid,
                  vtssMacsecStatisticsSecyRxSc8Sa1InPacketsNotUsingSa,
                  vtssMacsecStatisticsSecyRxSc8Sa1InPacketsUnusedSa,
                  vtssMacsecStatisticsSecyRxSc8Sa1InPacketsUnchecked,
                  vtssMacsecStatisticsSecyRxSc8Sa1InPacketsDelayed,
                  vtssMacsecStatisticsSecyRxSc8Sa1InPacketsLate,
                  vtssMacsecStatisticsSecyRxSc8Sa2InPacketsOk,
                  vtssMacsecStatisticsSecyRxSc8Sa2InPacketsInvalid,
                  vtssMacsecStatisticsSecyRxSc8Sa2InPacketsNotValid,
                  vtssMacsecStatisticsSecyRxSc8Sa2InPacketsNotUsingSa,
                  vtssMacsecStatisticsSecyRxSc8Sa2InPacketsUnusedSa,
                  vtssMacsecStatisticsSecyRxSc8Sa2InPacketsUnchecked,
                  vtssMacsecStatisticsSecyRxSc8Sa2InPacketsDelayed,
                  vtssMacsecStatisticsSecyRxSc8Sa2InPacketsLate,
                  vtssMacsecStatisticsSecyRxSc8Sa3InPacketsOk,
                  vtssMacsecStatisticsSecyRxSc8Sa3InPacketsInvalid,
                  vtssMacsecStatisticsSecyRxSc8Sa3InPacketsNotValid,
                  vtssMacsecStatisticsSecyRxSc8Sa3InPacketsNotUsingSa,
                  vtssMacsecStatisticsSecyRxSc8Sa3InPacketsUnusedSa,
                  vtssMacsecStatisticsSecyRxSc8Sa3InPacketsUnchecked,
                  vtssMacsecStatisticsSecyRxSc8Sa3InPacketsDelayed,
                  vtssMacsecStatisticsSecyRxSc8Sa3InPacketsLate,
                  vtssMacsecStatisticsSecyRxSc8Sa4InPacketsOk,
                  vtssMacsecStatisticsSecyRxSc8Sa4InPacketsInvalid,
                  vtssMacsecStatisticsSecyRxSc8Sa4InPacketsNotValid,
                  vtssMacsecStatisticsSecyRxSc8Sa4InPacketsNotUsingSa,
                  vtssMacsecStatisticsSecyRxSc8Sa4InPacketsUnusedSa,
                  vtssMacsecStatisticsSecyRxSc8Sa4InPacketsUnchecked,
                  vtssMacsecStatisticsSecyRxSc8Sa4InPacketsDelayed,
                  vtssMacsecStatisticsSecyRxSc8Sa4InPacketsLate }
    STATUS      current
    DESCRIPTION
        "A collection of objects."
    ::= { vtssMacsecMibGroups 9 }

vtssMacsecMibCompliance MODULE-COMPLIANCE
    STATUS      current
    DESCRIPTION
        "The compliance statement for the implementation."

    MODULE      -- this module

    MANDATORY-GROUPS { vtssMacsecCapabilitiesListInfoGroup,
                       vtssMacsecCapabilitiesInterfacesInfoGroup,
                       vtssMacsecConfigPortTableInfoGroup,
                       vtssMacsecConfigSecyTableInfoGroup,
                       vtssMacsecConfigSecyRowEditorInfoGroup,
                       vtssMacsecStatusSecyTableInfoGroup,
                       vtssMacsecControlStatisticsClearInfoGroup,
                       vtssMacsecStatisticsPortTableInfoGroup,
                       vtssMacsecStatisticsSecyTableInfoGroup }

    ::= { vtssMacsecMibCompliances 1 }

END
