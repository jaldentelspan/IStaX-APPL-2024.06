-- *****************************************************************
-- IPMC-MVR-MIB:  Microsemi ENT private MIB
-- ****************************************************************

VTSS-IPMC-MVR-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    IpAddress FROM SNMPv2-SMI
    Unsigned32 FROM SNMPv2-SMI
    TruthValue FROM SNMPv2-TC
    VTSSDisplayString FROM VTSS-TC
    VTSSInterfaceIndex FROM VTSS-TC
    VTSSIpmcFilterMode FROM VTSS-TC
    VTSSIpmcQuerierStatus FROM VTSS-TC
    VTSSPortList FROM VTSS-TC
    VTSSRowEditorState FROM VTSS-TC
    VTSSUnsigned8 FROM VTSS-TC
    ;

vtssIpmcMvrMib MODULE-IDENTITY
    LAST-UPDATED "202210210000Z"
    ORGANIZATION
        "Microsemi Corporation"
    CONTACT-INFO
        "Application support: http://www.microchip.com/support"
    DESCRIPTION
        "This is a private version of the IPMC MVR MIB"
    REVISION    "202210210000Z"
    DESCRIPTION
        "Restructured entire MIB"
    REVISION    "202204190000Z"
    DESCRIPTION
        "Added capability table and updated various text"
    REVISION    "201708240000Z"
    DESCRIPTION
        "Added Querier election cofigured option"
    REVISION    "201407010000Z"
    DESCRIPTION
        "Initial version"
    ::= { vtssSwitchMgmt 68 }


VTSSIpmcMvrVlanInterfacePortRole ::= TEXTUAL-CONVENTION
    STATUS      current
    DESCRIPTION
        "This enumeration indicates the MVR port's operational role."
    SYNTAX      INTEGER { inactive(0), source(1), receiver(2) }

vtssIpmcMvrMibObjects OBJECT IDENTIFIER
    ::= { vtssIpmcMvrMib 1 }

vtssIpmcMvrConfig OBJECT IDENTIFIER
    ::= { vtssIpmcMvrMibObjects 2 }

vtssIpmcMvrConfigGlobals OBJECT IDENTIFIER
    ::= { vtssIpmcMvrConfig 1 }

vtssIpmcMvrConfigGlobalsAdminState OBJECT-TYPE
    SYNTAX      TruthValue
    MAX-ACCESS  read-write
    STATUS      current
    DESCRIPTION
        "Enable or disable MVR globally."
    ::= { vtssIpmcMvrConfigGlobals 1 }

vtssIpmcMvrConfigPortTable OBJECT-TYPE
    SYNTAX      SEQUENCE OF VTSSIpmcMvrConfigPortEntry
    MAX-ACCESS  not-accessible
    STATUS      current
    DESCRIPTION
        "This is a table for managing extra MVR helper features per port basis."
    ::= { vtssIpmcMvrConfig 2 }

vtssIpmcMvrConfigPortEntry OBJECT-TYPE
    SYNTAX      VTSSIpmcMvrConfigPortEntry
    MAX-ACCESS  not-accessible
    STATUS      current
    DESCRIPTION
        "Each port has a set of parameters."
    INDEX       { vtssIpmcMvrConfigPortPortIndex }
    ::= { vtssIpmcMvrConfigPortTable 1 }

VTSSIpmcMvrConfigPortEntry ::= SEQUENCE {
    vtssIpmcMvrConfigPortPortIndex         VTSSInterfaceIndex,
    vtssIpmcMvrConfigPortDoImmediateLeave  TruthValue
}

vtssIpmcMvrConfigPortPortIndex OBJECT-TYPE
    SYNTAX      VTSSInterfaceIndex
    MAX-ACCESS  accessible-for-notify
    STATUS      current
    DESCRIPTION
        "Logical interface number of the physical port."
    ::= { vtssIpmcMvrConfigPortEntry 1 }

vtssIpmcMvrConfigPortDoImmediateLeave OBJECT-TYPE
    SYNTAX      TruthValue
    MAX-ACCESS  read-write
    STATUS      current
    DESCRIPTION
        "Enable/disable the MVR immediate leave functionality."
    ::= { vtssIpmcMvrConfigPortEntry 2 }

vtssIpmcMvrConfigInterfaceTable OBJECT-TYPE
    SYNTAX      SEQUENCE OF VTSSIpmcMvrConfigInterfaceEntry
    MAX-ACCESS  not-accessible
    STATUS      current
    DESCRIPTION
        "This is a table for managing MVR VLAN interface entries."
    ::= { vtssIpmcMvrConfig 3 }

vtssIpmcMvrConfigInterfaceEntry OBJECT-TYPE
    SYNTAX      VTSSIpmcMvrConfigInterfaceEntry
    MAX-ACCESS  not-accessible
    STATUS      current
    DESCRIPTION
        "Each entry has a set of parameters"
    INDEX       { vtssIpmcMvrConfigInterfaceIfIndex }
    ::= { vtssIpmcMvrConfigInterfaceTable 1 }

VTSSIpmcMvrConfigInterfaceEntry ::= SEQUENCE {
    vtssIpmcMvrConfigInterfaceIfIndex               VTSSInterfaceIndex,
    vtssIpmcMvrConfigInterfaceName                  VTSSDisplayString,
    vtssIpmcMvrConfigInterfaceIgmpQuerierAddress    IpAddress,
    vtssIpmcMvrConfigInterfaceMode                  VTSSDisplayString,
    vtssIpmcMvrConfigInterfaceTagging               TruthValue,
    vtssIpmcMvrConfigInterfacePriority              VTSSUnsigned8,
    vtssIpmcMvrConfigInterfaceLastListenerQueryInt  Unsigned32,
    vtssIpmcMvrConfigInterfaceChannelProfile        VTSSDisplayString,
    vtssIpmcMvrConfigInterfaceQuerierElection       TruthValue,
    vtssIpmcMvrConfigInterfaceAction                VTSSRowEditorState
}

vtssIpmcMvrConfigInterfaceIfIndex OBJECT-TYPE
    SYNTAX      VTSSInterfaceIndex
    MAX-ACCESS  accessible-for-notify
    STATUS      current
    DESCRIPTION
        "Logical interface number of the VLAN interface."
    ::= { vtssIpmcMvrConfigInterfaceEntry 1 }

vtssIpmcMvrConfigInterfaceName OBJECT-TYPE
    SYNTAX      VTSSDisplayString (SIZE(0..16))
    MAX-ACCESS  read-write
    STATUS      current
    DESCRIPTION
        "MVR Name is an optional attribute to indicate the name of this MVR VLAN
         allowing the user to easily associate the MVR VLAN purpose with its
         name."
    ::= { vtssIpmcMvrConfigInterfaceEntry 2 }

vtssIpmcMvrConfigInterfaceIgmpQuerierAddress OBJECT-TYPE
    SYNTAX      IpAddress
    MAX-ACCESS  read-write
    STATUS      current
    DESCRIPTION
        "The static IPv4 source address of the specific MVR interface for seding
         IGMP Query message with respect to IGMP Querier election."
    ::= { vtssIpmcMvrConfigInterfaceEntry 3 }

vtssIpmcMvrConfigInterfaceMode OBJECT-TYPE
    SYNTAX      VTSSDisplayString (SIZE(0..10))
    MAX-ACCESS  read-write
    STATUS      current
    DESCRIPTION
        "In Dynamic mode, MVR allows dynamic MVR membership reports on source
         ports. In Compatible mode, MVR membership reports are forbidden on
         source ports."
    ::= { vtssIpmcMvrConfigInterfaceEntry 4 }

vtssIpmcMvrConfigInterfaceTagging OBJECT-TYPE
    SYNTAX      TruthValue
    MAX-ACCESS  read-write
    STATUS      current
    DESCRIPTION
        "Specify whether the IGMP/MLD control frames will be transmitted tagged
         or untagged with MVR VLAN ID."
    ::= { vtssIpmcMvrConfigInterfaceEntry 5 }

vtssIpmcMvrConfigInterfacePriority OBJECT-TYPE
    SYNTAX      VTSSUnsigned8
    MAX-ACCESS  read-write
    STATUS      current
    DESCRIPTION
        "Specify how the traversed IGMP/MLD control frames will be sent in
         prioritized manner in VLAN tag."
    ::= { vtssIpmcMvrConfigInterfaceEntry 6 }

vtssIpmcMvrConfigInterfaceLastListenerQueryInt OBJECT-TYPE
    SYNTAX      Unsigned32
    MAX-ACCESS  read-write
    STATUS      current
    DESCRIPTION
        "This setting Last Listener/Member Query Interval is used to control
         IGMP protocol stack for fast aging mechanism. It defines the maximum
         time to wait for IGMP/MLD report memberships on a port before removing
         the port from multicast group membership. The value is in units of
         tenths of a seconds. The range is from 0 to 31744."
    ::= { vtssIpmcMvrConfigInterfaceEntry 7 }

vtssIpmcMvrConfigInterfaceChannelProfile OBJECT-TYPE
    SYNTAX      VTSSDisplayString (SIZE(0..16))
    MAX-ACCESS  read-write
    STATUS      current
    DESCRIPTION
        "The profile used for the channel filtering condition in the specific
         MVR VLAN. Profile selected for designated interface channel is not
         allowed to have overlapped permit group address by comparing with other
         MVR VLAN interface's channel."
    ::= { vtssIpmcMvrConfigInterfaceEntry 8 }

vtssIpmcMvrConfigInterfaceQuerierElection OBJECT-TYPE
    SYNTAX      TruthValue
    MAX-ACCESS  read-write
    STATUS      current
    DESCRIPTION
        "Enable/Disable the capability to run IGMP/MLD Querier election per-VLAN
         basis."
    ::= { vtssIpmcMvrConfigInterfaceEntry 9 }

vtssIpmcMvrConfigInterfaceAction OBJECT-TYPE
    SYNTAX      VTSSRowEditorState
    MAX-ACCESS  read-write
    STATUS      current
    DESCRIPTION
        "Action"
    ::= { vtssIpmcMvrConfigInterfaceEntry 100 }

vtssIpmcMvrConfigInterfaceTableRowEditor OBJECT IDENTIFIER
    ::= { vtssIpmcMvrConfig 4 }

vtssIpmcMvrConfigInterfaceTableRowEditorIfIndex OBJECT-TYPE
    SYNTAX      VTSSInterfaceIndex
    MAX-ACCESS  read-write
    STATUS      current
    DESCRIPTION
        "Logical interface number of the VLAN interface."
    ::= { vtssIpmcMvrConfigInterfaceTableRowEditor 1 }

vtssIpmcMvrConfigInterfaceTableRowEditorName OBJECT-TYPE
    SYNTAX      VTSSDisplayString (SIZE(0..16))
    MAX-ACCESS  read-write
    STATUS      current
    DESCRIPTION
        "MVR Name is an optional attribute to indicate the name of this MVR VLAN
         allowing the user to easily associate the MVR VLAN purpose with its
         name."
    ::= { vtssIpmcMvrConfigInterfaceTableRowEditor 2 }

vtssIpmcMvrConfigInterfaceTableRowEditorIgmpQuerierAddress OBJECT-TYPE
    SYNTAX      IpAddress
    MAX-ACCESS  read-write
    STATUS      current
    DESCRIPTION
        "The static IPv4 source address of the specific MVR interface for seding
         IGMP Query message with respect to IGMP Querier election."
    ::= { vtssIpmcMvrConfigInterfaceTableRowEditor 3 }

vtssIpmcMvrConfigInterfaceTableRowEditorMode OBJECT-TYPE
    SYNTAX      VTSSDisplayString (SIZE(0..10))
    MAX-ACCESS  read-write
    STATUS      current
    DESCRIPTION
        "In Dynamic mode, MVR allows dynamic MVR membership reports on source
         ports. In Compatible mode, MVR membership reports are forbidden on
         source ports."
    ::= { vtssIpmcMvrConfigInterfaceTableRowEditor 4 }

vtssIpmcMvrConfigInterfaceTableRowEditorTagging OBJECT-TYPE
    SYNTAX      TruthValue
    MAX-ACCESS  read-write
    STATUS      current
    DESCRIPTION
        "Specify whether the IGMP/MLD control frames will be transmitted tagged
         or untagged with MVR VLAN ID."
    ::= { vtssIpmcMvrConfigInterfaceTableRowEditor 5 }

vtssIpmcMvrConfigInterfaceTableRowEditorPriority OBJECT-TYPE
    SYNTAX      VTSSUnsigned8
    MAX-ACCESS  read-write
    STATUS      current
    DESCRIPTION
        "Specify how the traversed IGMP/MLD control frames will be sent in
         prioritized manner in VLAN tag."
    ::= { vtssIpmcMvrConfigInterfaceTableRowEditor 6 }

vtssIpmcMvrConfigInterfaceTableRowEditorLastListenerQueryInt OBJECT-TYPE
    SYNTAX      Unsigned32
    MAX-ACCESS  read-write
    STATUS      current
    DESCRIPTION
        "This setting Last Listener/Member Query Interval is used to control
         IGMP protocol stack for fast aging mechanism. It defines the maximum
         time to wait for IGMP/MLD report memberships on a port before removing
         the port from multicast group membership. The value is in units of
         tenths of a seconds. The range is from 0 to 31744."
    ::= { vtssIpmcMvrConfigInterfaceTableRowEditor 7 }

vtssIpmcMvrConfigInterfaceTableRowEditorChannelProfile OBJECT-TYPE
    SYNTAX      VTSSDisplayString (SIZE(0..16))
    MAX-ACCESS  read-write
    STATUS      current
    DESCRIPTION
        "The profile used for the channel filtering condition in the specific
         MVR VLAN. Profile selected for designated interface channel is not
         allowed to have overlapped permit group address by comparing with other
         MVR VLAN interface's channel."
    ::= { vtssIpmcMvrConfigInterfaceTableRowEditor 8 }

vtssIpmcMvrConfigInterfaceTableRowEditorQuerierElection OBJECT-TYPE
    SYNTAX      TruthValue
    MAX-ACCESS  read-write
    STATUS      current
    DESCRIPTION
        "Enable/Disable the capability to run IGMP/MLD Querier election per-VLAN
         basis."
    ::= { vtssIpmcMvrConfigInterfaceTableRowEditor 9 }

vtssIpmcMvrConfigInterfaceTableRowEditorAction OBJECT-TYPE
    SYNTAX      VTSSRowEditorState
    MAX-ACCESS  read-write
    STATUS      current
    DESCRIPTION
        "Action"
    ::= { vtssIpmcMvrConfigInterfaceTableRowEditor 100 }

vtssIpmcMvrConfigVlanPortTable OBJECT-TYPE
    SYNTAX      SEQUENCE OF VTSSIpmcMvrConfigVlanPortEntry
    MAX-ACCESS  not-accessible
    STATUS      current
    DESCRIPTION
        "This is a table for managing MVR port roles of a specific MVR VLAN
         interface."
    ::= { vtssIpmcMvrConfig 5 }

vtssIpmcMvrConfigVlanPortEntry OBJECT-TYPE
    SYNTAX      VTSSIpmcMvrConfigVlanPortEntry
    MAX-ACCESS  not-accessible
    STATUS      current
    DESCRIPTION
        "Each port has a set of parameters."
    INDEX       { vtssIpmcMvrConfigVlanPortIfIndex,
                  vtssIpmcMvrConfigVlanPortPortIndex }
    ::= { vtssIpmcMvrConfigVlanPortTable 1 }

VTSSIpmcMvrConfigVlanPortEntry ::= SEQUENCE {
    vtssIpmcMvrConfigVlanPortIfIndex    VTSSInterfaceIndex,
    vtssIpmcMvrConfigVlanPortPortIndex  VTSSInterfaceIndex,
    vtssIpmcMvrConfigVlanPortRole       VTSSIpmcMvrVlanInterfacePortRole
}

vtssIpmcMvrConfigVlanPortIfIndex OBJECT-TYPE
    SYNTAX      VTSSInterfaceIndex
    MAX-ACCESS  accessible-for-notify
    STATUS      current
    DESCRIPTION
        "Logical interface number of the VLAN interface."
    ::= { vtssIpmcMvrConfigVlanPortEntry 1 }

vtssIpmcMvrConfigVlanPortPortIndex OBJECT-TYPE
    SYNTAX      VTSSInterfaceIndex
    MAX-ACCESS  accessible-for-notify
    STATUS      current
    DESCRIPTION
        "Logical interface number of the physical port."
    ::= { vtssIpmcMvrConfigVlanPortEntry 2 }

vtssIpmcMvrConfigVlanPortRole OBJECT-TYPE
    SYNTAX      VTSSIpmcMvrVlanInterfacePortRole
    MAX-ACCESS  read-write
    STATUS      current
    DESCRIPTION
        "Configure a MVR port of the designated MVR VLAN as one of the following
         roles: Inactive, Source or Receiver. An inactive port does not
         participate MVR operations. Configure uplink ports that receive and
         send multicast data as a source port, and multicast subscribers cannot
         be directly connected to source ports. Configure a port as a receiver
         port if it is a subscriber port and should only receive multicast data,
         and a receiver port does not receive data unless it becomes a member of
         the multicast group by issuing IGMP/MLD control messages. Be Caution:
         MVR source ports are not recommended to be overlapped with management
         VLAN ports."
    ::= { vtssIpmcMvrConfigVlanPortEntry 3 }

vtssIpmcMvrStatus OBJECT IDENTIFIER
    ::= { vtssIpmcMvrMibObjects 3 }

vtssIpmcMvrStatusIgmpVlanTable OBJECT-TYPE
    SYNTAX      SEQUENCE OF VTSSIpmcMvrStatusIgmpVlanEntry
    MAX-ACCESS  not-accessible
    STATUS      current
    DESCRIPTION
        "This is a table for displaying the per VLAN interface status in MVR
         from IGMP protocol."
    ::= { vtssIpmcMvrStatus 2 }

vtssIpmcMvrStatusIgmpVlanEntry OBJECT-TYPE
    SYNTAX      VTSSIpmcMvrStatusIgmpVlanEntry
    MAX-ACCESS  not-accessible
    STATUS      current
    DESCRIPTION
        "Each entry has a set of parameters."
    INDEX       { vtssIpmcMvrStatusIgmpVlanIfIndex }
    ::= { vtssIpmcMvrStatusIgmpVlanTable 1 }

VTSSIpmcMvrStatusIgmpVlanEntry ::= SEQUENCE {
    vtssIpmcMvrStatusIgmpVlanIfIndex                 VTSSInterfaceIndex,
    vtssIpmcMvrStatusIgmpVlanQuerierStatus           VTSSIpmcQuerierStatus,
    vtssIpmcMvrStatusIgmpVlanActiveQuerierAddress    IpAddress,
    vtssIpmcMvrStatusIgmpVlanQuerierUptime           Unsigned32,
    vtssIpmcMvrStatusIgmpVlanQueryInterval           Unsigned32,
    vtssIpmcMvrStatusIgmpVlanQuerierExpiryTime       Unsigned32,
    vtssIpmcMvrStatusIgmpVlanQuerierVersion          VTSSUnsigned8,
    vtssIpmcMvrStatusIgmpVlanQuerierPresentTimeout   Unsigned32,
    vtssIpmcMvrStatusIgmpVlanHostVersion             VTSSUnsigned8,
    vtssIpmcMvrStatusIgmpVlanHostPresentTimeout      Unsigned32,
    vtssIpmcMvrStatusIgmpVlanCounterTxQuery          Unsigned32,
    vtssIpmcMvrStatusIgmpVlanCounterTxSpecificQuery  Unsigned32,
    vtssIpmcMvrStatusIgmpVlanCounterRxQuery          Unsigned32,
    vtssIpmcMvrStatusIgmpVlanCounterRxV1Join         Unsigned32,
    vtssIpmcMvrStatusIgmpVlanCounterRxV2Join         Unsigned32,
    vtssIpmcMvrStatusIgmpVlanCounterRxV2Leave        Unsigned32,
    vtssIpmcMvrStatusIgmpVlanCounterRxV3Join         Unsigned32,
    vtssIpmcMvrStatusIgmpVlanCounterRxErrors         Unsigned32
}

vtssIpmcMvrStatusIgmpVlanIfIndex OBJECT-TYPE
    SYNTAX      VTSSInterfaceIndex
    MAX-ACCESS  accessible-for-notify
    STATUS      current
    DESCRIPTION
        "Logical interface number of the VLAN interface."
    ::= { vtssIpmcMvrStatusIgmpVlanEntry 1 }

vtssIpmcMvrStatusIgmpVlanQuerierStatus OBJECT-TYPE
    SYNTAX      VTSSIpmcQuerierStatus
    MAX-ACCESS  read-only
    STATUS      current
    DESCRIPTION
        "The IGMP Querier status of this VLAN interface."
    ::= { vtssIpmcMvrStatusIgmpVlanEntry 2 }

vtssIpmcMvrStatusIgmpVlanActiveQuerierAddress OBJECT-TYPE
    SYNTAX      IpAddress
    MAX-ACCESS  read-only
    STATUS      current
    DESCRIPTION
        "The active IGMP Querier address on this VLAN interface."
    ::= { vtssIpmcMvrStatusIgmpVlanEntry 3 }

vtssIpmcMvrStatusIgmpVlanQuerierUptime OBJECT-TYPE
    SYNTAX      Unsigned32
    MAX-ACCESS  read-only
    STATUS      current
    DESCRIPTION
        "Number of seconds this node has acted as IGMP Querier on this VLAN
         interface."
    ::= { vtssIpmcMvrStatusIgmpVlanEntry 4 }

vtssIpmcMvrStatusIgmpVlanQueryInterval OBJECT-TYPE
    SYNTAX      Unsigned32
    MAX-ACCESS  read-only
    STATUS      current
    DESCRIPTION
        "Time left (in seconds) until next query is sent on this VLAN interface
         if we are the active querier."
    ::= { vtssIpmcMvrStatusIgmpVlanEntry 5 }

vtssIpmcMvrStatusIgmpVlanQuerierExpiryTime OBJECT-TYPE
    SYNTAX      Unsigned32
    MAX-ACCESS  read-only
    STATUS      current
    DESCRIPTION
        "Querier Expire Time as stated in RFC3376 section 8.5 on this VLAN
         interface."
    ::= { vtssIpmcMvrStatusIgmpVlanEntry 6 }

vtssIpmcMvrStatusIgmpVlanQuerierVersion OBJECT-TYPE
    SYNTAX      VTSSUnsigned8
    MAX-ACCESS  read-only
    STATUS      current
    DESCRIPTION
        "The current IGMP version that this VLAN interface behaves like when
         running IGMP protocol as a router."
    ::= { vtssIpmcMvrStatusIgmpVlanEntry 7 }

vtssIpmcMvrStatusIgmpVlanQuerierPresentTimeout OBJECT-TYPE
    SYNTAX      Unsigned32
    MAX-ACCESS  read-only
    STATUS      current
    DESCRIPTION
        "Older Version Querier Present Timeout as stated in RFC3376 section 8.12
         on this VLAN interface."
    ::= { vtssIpmcMvrStatusIgmpVlanEntry 8 }

vtssIpmcMvrStatusIgmpVlanHostVersion OBJECT-TYPE
    SYNTAX      VTSSUnsigned8
    MAX-ACCESS  read-only
    STATUS      current
    DESCRIPTION
        "Current IGMP compatibility protocol setting for listener ports in this
         VLAN."
    ::= { vtssIpmcMvrStatusIgmpVlanEntry 9 }

vtssIpmcMvrStatusIgmpVlanHostPresentTimeout OBJECT-TYPE
    SYNTAX      Unsigned32
    MAX-ACCESS  read-only
    STATUS      current
    DESCRIPTION
        "Old Version Host Present Interval as stated in RFC3376 section 8.13 on
         this VLAN interface."
    ::= { vtssIpmcMvrStatusIgmpVlanEntry 10 }

vtssIpmcMvrStatusIgmpVlanCounterTxQuery OBJECT-TYPE
    SYNTAX      Unsigned32
    MAX-ACCESS  read-only
    STATUS      current
    DESCRIPTION
        "Number of IGMP Query control frames transmitted on this VLAN interface."
    ::= { vtssIpmcMvrStatusIgmpVlanEntry 11 }

vtssIpmcMvrStatusIgmpVlanCounterTxSpecificQuery OBJECT-TYPE
    SYNTAX      Unsigned32
    MAX-ACCESS  read-only
    STATUS      current
    DESCRIPTION
        "Number of IGMP Group Query control frames transmitted on this VLAN
         interface."
    ::= { vtssIpmcMvrStatusIgmpVlanEntry 12 }

vtssIpmcMvrStatusIgmpVlanCounterRxQuery OBJECT-TYPE
    SYNTAX      Unsigned32
    MAX-ACCESS  read-only
    STATUS      current
    DESCRIPTION
        "Number of IGMP Query control frames received on this VLAN interface."
    ::= { vtssIpmcMvrStatusIgmpVlanEntry 13 }

vtssIpmcMvrStatusIgmpVlanCounterRxV1Join OBJECT-TYPE
    SYNTAX      Unsigned32
    MAX-ACCESS  read-only
    STATUS      current
    DESCRIPTION
        "Number of IGMPv1 Join frames received and processed on this VLAN
         interface."
    ::= { vtssIpmcMvrStatusIgmpVlanEntry 14 }

vtssIpmcMvrStatusIgmpVlanCounterRxV2Join OBJECT-TYPE
    SYNTAX      Unsigned32
    MAX-ACCESS  read-only
    STATUS      current
    DESCRIPTION
        "Number of IGMPv2 Join frames receives on this VLAN interface."
    ::= { vtssIpmcMvrStatusIgmpVlanEntry 15 }

vtssIpmcMvrStatusIgmpVlanCounterRxV2Leave OBJECT-TYPE
    SYNTAX      Unsigned32
    MAX-ACCESS  read-only
    STATUS      current
    DESCRIPTION
        "Number of IGMPv2 Leave frames received on this VLAN interface."
    ::= { vtssIpmcMvrStatusIgmpVlanEntry 16 }

vtssIpmcMvrStatusIgmpVlanCounterRxV3Join OBJECT-TYPE
    SYNTAX      Unsigned32
    MAX-ACCESS  read-only
    STATUS      current
    DESCRIPTION
        "Number of IGMPv3 Join frames received on this VLAN interface."
    ::= { vtssIpmcMvrStatusIgmpVlanEntry 17 }

vtssIpmcMvrStatusIgmpVlanCounterRxErrors OBJECT-TYPE
    SYNTAX      Unsigned32
    MAX-ACCESS  read-only
    STATUS      current
    DESCRIPTION
        "Number of invalid IGMP control frames received on this VLAN interface."
    ::= { vtssIpmcMvrStatusIgmpVlanEntry 18 }

vtssIpmcMvrStatusIgmpGroupAddressTable OBJECT-TYPE
    SYNTAX      SEQUENCE OF VTSSIpmcMvrStatusIgmpGroupAddressEntry
    MAX-ACCESS  not-accessible
    STATUS      current
    DESCRIPTION
        "This is a table for displaying the registered IPv4 multicast group
         address status in IGMP from MVR."
    ::= { vtssIpmcMvrStatus 3 }

vtssIpmcMvrStatusIgmpGroupAddressEntry OBJECT-TYPE
    SYNTAX      VTSSIpmcMvrStatusIgmpGroupAddressEntry
    MAX-ACCESS  not-accessible
    STATUS      current
    DESCRIPTION
        "Each entry has a set of parameters."
    INDEX       { vtssIpmcMvrStatusIgmpGroupAddressIfIndex,
                  vtssIpmcMvrStatusIgmpGroupAddressGroupAddress }
    ::= { vtssIpmcMvrStatusIgmpGroupAddressTable 1 }

VTSSIpmcMvrStatusIgmpGroupAddressEntry ::= SEQUENCE {
    vtssIpmcMvrStatusIgmpGroupAddressIfIndex         VTSSInterfaceIndex,
    vtssIpmcMvrStatusIgmpGroupAddressGroupAddress    IpAddress,
    vtssIpmcMvrStatusIgmpGroupAddressMemberPorts     VTSSPortList,
    vtssIpmcMvrStatusIgmpGroupAddressHardwareSwitch  TruthValue
}

vtssIpmcMvrStatusIgmpGroupAddressIfIndex OBJECT-TYPE
    SYNTAX      VTSSInterfaceIndex
    MAX-ACCESS  accessible-for-notify
    STATUS      current
    DESCRIPTION
        "Logical interface number of the VLAN interface."
    ::= { vtssIpmcMvrStatusIgmpGroupAddressEntry 1 }

vtssIpmcMvrStatusIgmpGroupAddressGroupAddress OBJECT-TYPE
    SYNTAX      IpAddress
    MAX-ACCESS  accessible-for-notify
    STATUS      current
    DESCRIPTION
        "Assigned IPv4 multicast address."
    ::= { vtssIpmcMvrStatusIgmpGroupAddressEntry 2 }

vtssIpmcMvrStatusIgmpGroupAddressMemberPorts OBJECT-TYPE
    SYNTAX      VTSSPortList
    MAX-ACCESS  read-only
    STATUS      current
    DESCRIPTION
        "Contains the listener ports of this multicast address"
    ::= { vtssIpmcMvrStatusIgmpGroupAddressEntry 3 }

vtssIpmcMvrStatusIgmpGroupAddressHardwareSwitch OBJECT-TYPE
    SYNTAX      TruthValue
    MAX-ACCESS  read-only
    STATUS      current
    DESCRIPTION
        "If true, the chip contains an entry with this group address"
    ::= { vtssIpmcMvrStatusIgmpGroupAddressEntry 4 }

vtssIpmcMvrStatusIgmpGroupSrcListTable OBJECT-TYPE
    SYNTAX      SEQUENCE OF VTSSIpmcMvrStatusIgmpGroupSrcListEntry
    MAX-ACCESS  not-accessible
    STATUS      current
    DESCRIPTION
        "This is a table for displaying the address SFM (a.k.a Source List
         Multicast) status in source list of the registered IPv4 multicast group
         in IGMP from MVR."
    ::= { vtssIpmcMvrStatus 4 }

vtssIpmcMvrStatusIgmpGroupSrcListEntry OBJECT-TYPE
    SYNTAX      VTSSIpmcMvrStatusIgmpGroupSrcListEntry
    MAX-ACCESS  not-accessible
    STATUS      current
    DESCRIPTION
        "Each entry has a set of parameters."
    INDEX       { vtssIpmcMvrStatusIgmpGroupSrcListIfIndex,
                  vtssIpmcMvrStatusIgmpGroupSrcListGroupAddress,
                  vtssIpmcMvrStatusIgmpGroupSrcListPortIndex,
                  vtssIpmcMvrStatusIgmpGroupSrcListHostAddress }
    ::= { vtssIpmcMvrStatusIgmpGroupSrcListTable 1 }

VTSSIpmcMvrStatusIgmpGroupSrcListEntry ::= SEQUENCE {
    vtssIpmcMvrStatusIgmpGroupSrcListIfIndex          VTSSInterfaceIndex,
    vtssIpmcMvrStatusIgmpGroupSrcListGroupAddress     IpAddress,
    vtssIpmcMvrStatusIgmpGroupSrcListPortIndex        VTSSInterfaceIndex,
    vtssIpmcMvrStatusIgmpGroupSrcListHostAddress      IpAddress,
    vtssIpmcMvrStatusIgmpGroupSrcListGroupFilterMode  VTSSIpmcFilterMode,
    vtssIpmcMvrStatusIgmpGroupSrcListFilterTimer      Unsigned32,
    vtssIpmcMvrStatusIgmpGroupSrcListSourceType       TruthValue,
    vtssIpmcMvrStatusIgmpGroupSrcListSourceTimer      Unsigned32,
    vtssIpmcMvrStatusIgmpGroupSrcListHardwareFilter   TruthValue
}

vtssIpmcMvrStatusIgmpGroupSrcListIfIndex OBJECT-TYPE
    SYNTAX      VTSSInterfaceIndex
    MAX-ACCESS  accessible-for-notify
    STATUS      current
    DESCRIPTION
        "Logical interface number of the VLAN interface."
    ::= { vtssIpmcMvrStatusIgmpGroupSrcListEntry 1 }

vtssIpmcMvrStatusIgmpGroupSrcListGroupAddress OBJECT-TYPE
    SYNTAX      IpAddress
    MAX-ACCESS  accessible-for-notify
    STATUS      current
    DESCRIPTION
        "Assigned IPv4 multicast address."
    ::= { vtssIpmcMvrStatusIgmpGroupSrcListEntry 2 }

vtssIpmcMvrStatusIgmpGroupSrcListPortIndex OBJECT-TYPE
    SYNTAX      VTSSInterfaceIndex
    MAX-ACCESS  accessible-for-notify
    STATUS      current
    DESCRIPTION
        "Logical interface number of the physical port."
    ::= { vtssIpmcMvrStatusIgmpGroupSrcListEntry 3 }

vtssIpmcMvrStatusIgmpGroupSrcListHostAddress OBJECT-TYPE
    SYNTAX      IpAddress
    MAX-ACCESS  accessible-for-notify
    STATUS      current
    DESCRIPTION
        "Assigned IPv4 source address."
    ::= { vtssIpmcMvrStatusIgmpGroupSrcListEntry 4 }

vtssIpmcMvrStatusIgmpGroupSrcListGroupFilterMode OBJECT-TYPE
    SYNTAX      VTSSIpmcFilterMode
    MAX-ACCESS  read-only
    STATUS      current
    DESCRIPTION
        "The filter mode of this multicast group on this port."
    ::= { vtssIpmcMvrStatusIgmpGroupSrcListEntry 5 }

vtssIpmcMvrStatusIgmpGroupSrcListFilterTimer OBJECT-TYPE
    SYNTAX      Unsigned32
    MAX-ACCESS  read-only
    STATUS      current
    DESCRIPTION
        "The number of seconds until this group on this port times out (only
         used if filter mode is EXCLUDE)."
    ::= { vtssIpmcMvrStatusIgmpGroupSrcListEntry 6 }

vtssIpmcMvrStatusIgmpGroupSrcListSourceType OBJECT-TYPE
    SYNTAX      TruthValue
    MAX-ACCESS  read-only
    STATUS      current
    DESCRIPTION
        "Indicates whether this source address is forwarding or not."
    ::= { vtssIpmcMvrStatusIgmpGroupSrcListEntry 7 }

vtssIpmcMvrStatusIgmpGroupSrcListSourceTimer OBJECT-TYPE
    SYNTAX      Unsigned32
    MAX-ACCESS  read-only
    STATUS      current
    DESCRIPTION
        "The number of seconds until this source times out."
    ::= { vtssIpmcMvrStatusIgmpGroupSrcListEntry 8 }

vtssIpmcMvrStatusIgmpGroupSrcListHardwareFilter OBJECT-TYPE
    SYNTAX      TruthValue
    MAX-ACCESS  read-only
    STATUS      current
    DESCRIPTION
        "If true, the chip contains an entry with this source address."
    ::= { vtssIpmcMvrStatusIgmpGroupSrcListEntry 9 }

vtssIpmcMvrStatusMldVlanTable OBJECT-TYPE
    SYNTAX      SEQUENCE OF VTSSIpmcMvrStatusMldVlanEntry
    MAX-ACCESS  not-accessible
    STATUS      current
    DESCRIPTION
        "This is a table for displaying the per VLAN interface status in MVR
         from MLD protocol."
    ::= { vtssIpmcMvrStatus 5 }

vtssIpmcMvrStatusMldVlanEntry OBJECT-TYPE
    SYNTAX      VTSSIpmcMvrStatusMldVlanEntry
    MAX-ACCESS  not-accessible
    STATUS      current
    DESCRIPTION
        "Each entry has a set of parameters."
    INDEX       { vtssIpmcMvrStatusMldVlanIfIndex }
    ::= { vtssIpmcMvrStatusMldVlanTable 1 }

VTSSIpmcMvrStatusMldVlanEntry ::= SEQUENCE {
    vtssIpmcMvrStatusMldVlanIfIndex                 VTSSInterfaceIndex,
    vtssIpmcMvrStatusMldVlanQuerierStatus           VTSSIpmcQuerierStatus,
    vtssIpmcMvrStatusMldVlanActiveQuerierAddress    InetAddressIPv6,
    vtssIpmcMvrStatusMldVlanQuerierUptime           Unsigned32,
    vtssIpmcMvrStatusMldVlanQueryInterval           Unsigned32,
    vtssIpmcMvrStatusMldVlanQuerierExpiryTime       Unsigned32,
    vtssIpmcMvrStatusMldVlanQuerierVersion          VTSSUnsigned8,
    vtssIpmcMvrStatusMldVlanQuerierPresentTimeout   Unsigned32,
    vtssIpmcMvrStatusMldVlanHostVersion             VTSSUnsigned8,
    vtssIpmcMvrStatusMldVlanHostPresentTimeout      Unsigned32,
    vtssIpmcMvrStatusMldVlanCounterTxQuery          Unsigned32,
    vtssIpmcMvrStatusMldVlanCounterTxSpecificQuery  Unsigned32,
    vtssIpmcMvrStatusMldVlanCounterRxQuery          Unsigned32,
    vtssIpmcMvrStatusMldVlanCounterRxV1Report       Unsigned32,
    vtssIpmcMvrStatusMldVlanCounterRxV1Done         Unsigned32,
    vtssIpmcMvrStatusMldVlanCounterRxV2Report       Unsigned32,
    vtssIpmcMvrStatusMldVlanCounterRxErrors         Unsigned32
}

vtssIpmcMvrStatusMldVlanIfIndex OBJECT-TYPE
    SYNTAX      VTSSInterfaceIndex
    MAX-ACCESS  accessible-for-notify
    STATUS      current
    DESCRIPTION
        "Logical interface number of the VLAN interface."
    ::= { vtssIpmcMvrStatusMldVlanEntry 1 }

vtssIpmcMvrStatusMldVlanQuerierStatus OBJECT-TYPE
    SYNTAX      VTSSIpmcQuerierStatus
    MAX-ACCESS  read-only
    STATUS      current
    DESCRIPTION
        "The MLD Querier status of this VLAN interface."
    ::= { vtssIpmcMvrStatusMldVlanEntry 2 }

vtssIpmcMvrStatusMldVlanActiveQuerierAddress OBJECT-TYPE
    SYNTAX      InetAddressIPv6
    MAX-ACCESS  read-only
    STATUS      current
    DESCRIPTION
        "The active MLD Querier address on this VLAN interface."
    ::= { vtssIpmcMvrStatusMldVlanEntry 3 }

vtssIpmcMvrStatusMldVlanQuerierUptime OBJECT-TYPE
    SYNTAX      Unsigned32
    MAX-ACCESS  read-only
    STATUS      current
    DESCRIPTION
        "Number of seconds this node has acted as MLD Querier on this VLAN
         interface."
    ::= { vtssIpmcMvrStatusMldVlanEntry 4 }

vtssIpmcMvrStatusMldVlanQueryInterval OBJECT-TYPE
    SYNTAX      Unsigned32
    MAX-ACCESS  read-only
    STATUS      current
    DESCRIPTION
        "Time left (in seconds) until next query is sent on this VLAN interface
         if we are the active querier."
    ::= { vtssIpmcMvrStatusMldVlanEntry 5 }

vtssIpmcMvrStatusMldVlanQuerierExpiryTime OBJECT-TYPE
    SYNTAX      Unsigned32
    MAX-ACCESS  read-only
    STATUS      current
    DESCRIPTION
        "Querier Expire Time as stated in RFC3810 section 9.5 on this VLAN
         interface."
    ::= { vtssIpmcMvrStatusMldVlanEntry 6 }

vtssIpmcMvrStatusMldVlanQuerierVersion OBJECT-TYPE
    SYNTAX      VTSSUnsigned8
    MAX-ACCESS  read-only
    STATUS      current
    DESCRIPTION
        "The current MLD version that this VLAN interface behaves like when
         running MLD protocol as a router."
    ::= { vtssIpmcMvrStatusMldVlanEntry 7 }

vtssIpmcMvrStatusMldVlanQuerierPresentTimeout OBJECT-TYPE
    SYNTAX      Unsigned32
    MAX-ACCESS  read-only
    STATUS      current
    DESCRIPTION
        "Older Version Querier Present Timeout as stated in RFC3810 section 9.12
         on this VLAN interface."
    ::= { vtssIpmcMvrStatusMldVlanEntry 8 }

vtssIpmcMvrStatusMldVlanHostVersion OBJECT-TYPE
    SYNTAX      VTSSUnsigned8
    MAX-ACCESS  read-only
    STATUS      current
    DESCRIPTION
        "Current MLD compatibility protocol setting for listener ports in this
         VLAN."
    ::= { vtssIpmcMvrStatusMldVlanEntry 9 }

vtssIpmcMvrStatusMldVlanHostPresentTimeout OBJECT-TYPE
    SYNTAX      Unsigned32
    MAX-ACCESS  read-only
    STATUS      current
    DESCRIPTION
        "Old Version Host Present Interval as stated in RFC3810 section 9.13 on
         this VLAN interface."
    ::= { vtssIpmcMvrStatusMldVlanEntry 10 }

vtssIpmcMvrStatusMldVlanCounterTxQuery OBJECT-TYPE
    SYNTAX      Unsigned32
    MAX-ACCESS  read-only
    STATUS      current
    DESCRIPTION
        "Number of MLD Query control frames transmitted on this VLAN interface."
    ::= { vtssIpmcMvrStatusMldVlanEntry 11 }

vtssIpmcMvrStatusMldVlanCounterTxSpecificQuery OBJECT-TYPE
    SYNTAX      Unsigned32
    MAX-ACCESS  read-only
    STATUS      current
    DESCRIPTION
        "Number of MLD Group Query control frames transmitted on this VLAN
         interface."
    ::= { vtssIpmcMvrStatusMldVlanEntry 12 }

vtssIpmcMvrStatusMldVlanCounterRxQuery OBJECT-TYPE
    SYNTAX      Unsigned32
    MAX-ACCESS  read-only
    STATUS      current
    DESCRIPTION
        "Number of MLD Query control frames received on this VLAN interface."
    ::= { vtssIpmcMvrStatusMldVlanEntry 13 }

vtssIpmcMvrStatusMldVlanCounterRxV1Report OBJECT-TYPE
    SYNTAX      Unsigned32
    MAX-ACCESS  read-only
    STATUS      current
    DESCRIPTION
        "Number of MLDv1 Report frames received on this VLAN interface."
    ::= { vtssIpmcMvrStatusMldVlanEntry 14 }

vtssIpmcMvrStatusMldVlanCounterRxV1Done OBJECT-TYPE
    SYNTAX      Unsigned32
    MAX-ACCESS  read-only
    STATUS      current
    DESCRIPTION
        "Number of MLDv1 Done frames received on this VLAN interface."
    ::= { vtssIpmcMvrStatusMldVlanEntry 15 }

vtssIpmcMvrStatusMldVlanCounterRxV2Report OBJECT-TYPE
    SYNTAX      Unsigned32
    MAX-ACCESS  read-only
    STATUS      current
    DESCRIPTION
        "Number of MLDv2 Report frames received on this VLAN interface."
    ::= { vtssIpmcMvrStatusMldVlanEntry 16 }

vtssIpmcMvrStatusMldVlanCounterRxErrors OBJECT-TYPE
    SYNTAX      Unsigned32
    MAX-ACCESS  read-only
    STATUS      current
    DESCRIPTION
        "Number of invalid MLD control frames received on this VLAN interface."
    ::= { vtssIpmcMvrStatusMldVlanEntry 17 }

vtssIpmcMvrStatusMldGroupAddressTable OBJECT-TYPE
    SYNTAX      SEQUENCE OF VTSSIpmcMvrStatusMldGroupAddressEntry
    MAX-ACCESS  not-accessible
    STATUS      current
    DESCRIPTION
        "This is a table for displaying the registered IPv6 multicast group
         address status in MLD from MVR."
    ::= { vtssIpmcMvrStatus 6 }

vtssIpmcMvrStatusMldGroupAddressEntry OBJECT-TYPE
    SYNTAX      VTSSIpmcMvrStatusMldGroupAddressEntry
    MAX-ACCESS  not-accessible
    STATUS      current
    DESCRIPTION
        "Each entry has a set of parameters."
    INDEX       { vtssIpmcMvrStatusMldGroupAddressIfIndex,
                  vtssIpmcMvrStatusMldGroupAddressGroupAddress }
    ::= { vtssIpmcMvrStatusMldGroupAddressTable 1 }

VTSSIpmcMvrStatusMldGroupAddressEntry ::= SEQUENCE {
    vtssIpmcMvrStatusMldGroupAddressIfIndex         VTSSInterfaceIndex,
    vtssIpmcMvrStatusMldGroupAddressGroupAddress    InetAddressIPv6,
    vtssIpmcMvrStatusMldGroupAddressMemberPorts     VTSSPortList,
    vtssIpmcMvrStatusMldGroupAddressHardwareSwitch  TruthValue
}

vtssIpmcMvrStatusMldGroupAddressIfIndex OBJECT-TYPE
    SYNTAX      VTSSInterfaceIndex
    MAX-ACCESS  accessible-for-notify
    STATUS      current
    DESCRIPTION
        "Logical interface number of the VLAN interface."
    ::= { vtssIpmcMvrStatusMldGroupAddressEntry 1 }

vtssIpmcMvrStatusMldGroupAddressGroupAddress OBJECT-TYPE
    SYNTAX      InetAddressIPv6
    MAX-ACCESS  accessible-for-notify
    STATUS      current
    DESCRIPTION
        "Assigned IPv6 multicast address."
    ::= { vtssIpmcMvrStatusMldGroupAddressEntry 2 }

vtssIpmcMvrStatusMldGroupAddressMemberPorts OBJECT-TYPE
    SYNTAX      VTSSPortList
    MAX-ACCESS  read-only
    STATUS      current
    DESCRIPTION
        "Contains the listener ports of this multicast address"
    ::= { vtssIpmcMvrStatusMldGroupAddressEntry 3 }

vtssIpmcMvrStatusMldGroupAddressHardwareSwitch OBJECT-TYPE
    SYNTAX      TruthValue
    MAX-ACCESS  read-only
    STATUS      current
    DESCRIPTION
        "If true, the chip contains an entry with this group address"
    ::= { vtssIpmcMvrStatusMldGroupAddressEntry 4 }

vtssIpmcMvrStatusMldGroupSrcListTable OBJECT-TYPE
    SYNTAX      SEQUENCE OF VTSSIpmcMvrStatusMldGroupSrcListEntry
    MAX-ACCESS  not-accessible
    STATUS      current
    DESCRIPTION
        "This is a table for displaying the address SFM (a.k.a Source List
         Multicast) status in source list of the registered IPv6 multicast group
         in MLD from MVR."
    ::= { vtssIpmcMvrStatus 7 }

vtssIpmcMvrStatusMldGroupSrcListEntry OBJECT-TYPE
    SYNTAX      VTSSIpmcMvrStatusMldGroupSrcListEntry
    MAX-ACCESS  not-accessible
    STATUS      current
    DESCRIPTION
        "Each entry has a set of parameters."
    INDEX       { vtssIpmcMvrStatusMldGroupSrcListIfIndex,
                  vtssIpmcMvrStatusMldGroupSrcListGroupAddress,
                  vtssIpmcMvrStatusMldGroupSrcListPortIndex,
                  vtssIpmcMvrStatusMldGroupSrcListHostAddress }
    ::= { vtssIpmcMvrStatusMldGroupSrcListTable 1 }

VTSSIpmcMvrStatusMldGroupSrcListEntry ::= SEQUENCE {
    vtssIpmcMvrStatusMldGroupSrcListIfIndex          VTSSInterfaceIndex,
    vtssIpmcMvrStatusMldGroupSrcListGroupAddress     InetAddressIPv6,
    vtssIpmcMvrStatusMldGroupSrcListPortIndex        VTSSInterfaceIndex,
    vtssIpmcMvrStatusMldGroupSrcListHostAddress      InetAddressIPv6,
    vtssIpmcMvrStatusMldGroupSrcListGroupFilterMode  VTSSIpmcFilterMode,
    vtssIpmcMvrStatusMldGroupSrcListFilterTimer      Unsigned32,
    vtssIpmcMvrStatusMldGroupSrcListSourceType       TruthValue,
    vtssIpmcMvrStatusMldGroupSrcListSourceTimer      Unsigned32,
    vtssIpmcMvrStatusMldGroupSrcListHardwareFilter   TruthValue
}

vtssIpmcMvrStatusMldGroupSrcListIfIndex OBJECT-TYPE
    SYNTAX      VTSSInterfaceIndex
    MAX-ACCESS  accessible-for-notify
    STATUS      current
    DESCRIPTION
        "Logical interface number of the VLAN interface."
    ::= { vtssIpmcMvrStatusMldGroupSrcListEntry 1 }

vtssIpmcMvrStatusMldGroupSrcListGroupAddress OBJECT-TYPE
    SYNTAX      InetAddressIPv6
    MAX-ACCESS  accessible-for-notify
    STATUS      current
    DESCRIPTION
        "Assigned IPv6 multicast address."
    ::= { vtssIpmcMvrStatusMldGroupSrcListEntry 2 }

vtssIpmcMvrStatusMldGroupSrcListPortIndex OBJECT-TYPE
    SYNTAX      VTSSInterfaceIndex
    MAX-ACCESS  accessible-for-notify
    STATUS      current
    DESCRIPTION
        "Logical interface number of the physical port."
    ::= { vtssIpmcMvrStatusMldGroupSrcListEntry 3 }

vtssIpmcMvrStatusMldGroupSrcListHostAddress OBJECT-TYPE
    SYNTAX      InetAddressIPv6
    MAX-ACCESS  accessible-for-notify
    STATUS      current
    DESCRIPTION
        "Assigned IPv6 source address."
    ::= { vtssIpmcMvrStatusMldGroupSrcListEntry 4 }

vtssIpmcMvrStatusMldGroupSrcListGroupFilterMode OBJECT-TYPE
    SYNTAX      VTSSIpmcFilterMode
    MAX-ACCESS  read-only
    STATUS      current
    DESCRIPTION
        "The filter mode of this multicast group on this port."
    ::= { vtssIpmcMvrStatusMldGroupSrcListEntry 5 }

vtssIpmcMvrStatusMldGroupSrcListFilterTimer OBJECT-TYPE
    SYNTAX      Unsigned32
    MAX-ACCESS  read-only
    STATUS      current
    DESCRIPTION
        "The number of seconds until this group on this port times out (only
         used if filter mode is EXCLUDE)."
    ::= { vtssIpmcMvrStatusMldGroupSrcListEntry 6 }

vtssIpmcMvrStatusMldGroupSrcListSourceType OBJECT-TYPE
    SYNTAX      TruthValue
    MAX-ACCESS  read-only
    STATUS      current
    DESCRIPTION
        "Indicates whether this source address is forwarding or not."
    ::= { vtssIpmcMvrStatusMldGroupSrcListEntry 7 }

vtssIpmcMvrStatusMldGroupSrcListSourceTimer OBJECT-TYPE
    SYNTAX      Unsigned32
    MAX-ACCESS  read-only
    STATUS      current
    DESCRIPTION
        "The number of seconds until this source times out."
    ::= { vtssIpmcMvrStatusMldGroupSrcListEntry 8 }

vtssIpmcMvrStatusMldGroupSrcListHardwareFilter OBJECT-TYPE
    SYNTAX      TruthValue
    MAX-ACCESS  read-only
    STATUS      current
    DESCRIPTION
        "If true, the chip contains an entry with this source address."
    ::= { vtssIpmcMvrStatusMldGroupSrcListEntry 9 }

vtssIpmcMvrControl OBJECT IDENTIFIER
    ::= { vtssIpmcMvrMibObjects 4 }

vtssIpmcMvrControlStatisticsClear OBJECT IDENTIFIER
    ::= { vtssIpmcMvrControl 1 }

vtssIpmcMvrControlStatisticsClearIfIndex OBJECT-TYPE
    SYNTAX      VTSSInterfaceIndex
    MAX-ACCESS  read-write
    STATUS      current
    DESCRIPTION
        "Logical interface number of the VLAN interface."
    ::= { vtssIpmcMvrControlStatisticsClear 1 }

vtssIpmcMvrControlStatisticsClearClear OBJECT-TYPE
    SYNTAX      TruthValue
    MAX-ACCESS  read-write
    STATUS      current
    DESCRIPTION
        "Set to TRUE to clear the counters of this VLAN."
    ::= { vtssIpmcMvrControlStatisticsClear 4 }

vtssIpmcMvrMibConformance OBJECT IDENTIFIER
    ::= { vtssIpmcMvrMib 2 }

vtssIpmcMvrMibCompliances OBJECT IDENTIFIER
    ::= { vtssIpmcMvrMibConformance 1 }

vtssIpmcMvrMibGroups OBJECT IDENTIFIER
    ::= { vtssIpmcMvrMibConformance 2 }

vtssIpmcMvrConfigGlobalsInfoGroup OBJECT-GROUP
    OBJECTS     { vtssIpmcMvrConfigGlobalsAdminState }
    STATUS      current
    DESCRIPTION
        "A collection of objects."
    ::= { vtssIpmcMvrMibGroups 1 }

vtssIpmcMvrConfigPortTableInfoGroup OBJECT-GROUP
    OBJECTS     { vtssIpmcMvrConfigPortPortIndex,
                  vtssIpmcMvrConfigPortDoImmediateLeave }
    STATUS      current
    DESCRIPTION
        "A collection of objects."
    ::= { vtssIpmcMvrMibGroups 2 }

vtssIpmcMvrConfigInterfaceTableInfoGroup OBJECT-GROUP
    OBJECTS     { vtssIpmcMvrConfigInterfaceIfIndex,
                  vtssIpmcMvrConfigInterfaceName,
                  vtssIpmcMvrConfigInterfaceIgmpQuerierAddress,
                  vtssIpmcMvrConfigInterfaceMode,
                  vtssIpmcMvrConfigInterfaceTagging,
                  vtssIpmcMvrConfigInterfacePriority,
                  vtssIpmcMvrConfigInterfaceLastListenerQueryInt,
                  vtssIpmcMvrConfigInterfaceChannelProfile,
                  vtssIpmcMvrConfigInterfaceQuerierElection,
                  vtssIpmcMvrConfigInterfaceAction }
    STATUS      current
    DESCRIPTION
        "A collection of objects."
    ::= { vtssIpmcMvrMibGroups 3 }

vtssIpmcMvrConfigInterfaceTableRowEditorInfoGroup OBJECT-GROUP
    OBJECTS     { vtssIpmcMvrConfigInterfaceTableRowEditorIfIndex,
                  vtssIpmcMvrConfigInterfaceTableRowEditorName,
                  vtssIpmcMvrConfigInterfaceTableRowEditorIgmpQuerierAddress,
                  vtssIpmcMvrConfigInterfaceTableRowEditorMode,
                  vtssIpmcMvrConfigInterfaceTableRowEditorTagging,
                  vtssIpmcMvrConfigInterfaceTableRowEditorPriority,
                  vtssIpmcMvrConfigInterfaceTableRowEditorLastListenerQueryInt,
                  vtssIpmcMvrConfigInterfaceTableRowEditorChannelProfile,
                  vtssIpmcMvrConfigInterfaceTableRowEditorQuerierElection,
                  vtssIpmcMvrConfigInterfaceTableRowEditorAction }
    STATUS      current
    DESCRIPTION
        "A collection of objects."
    ::= { vtssIpmcMvrMibGroups 4 }

vtssIpmcMvrConfigVlanPortTableInfoGroup OBJECT-GROUP
    OBJECTS     { vtssIpmcMvrConfigVlanPortIfIndex,
                  vtssIpmcMvrConfigVlanPortPortIndex,
                  vtssIpmcMvrConfigVlanPortRole }
    STATUS      current
    DESCRIPTION
        "A collection of objects."
    ::= { vtssIpmcMvrMibGroups 5 }

vtssIpmcMvrStatusIgmpVlanTableInfoGroup OBJECT-GROUP
    OBJECTS     { vtssIpmcMvrStatusIgmpVlanIfIndex,
                  vtssIpmcMvrStatusIgmpVlanQuerierStatus,
                  vtssIpmcMvrStatusIgmpVlanActiveQuerierAddress,
                  vtssIpmcMvrStatusIgmpVlanQuerierUptime,
                  vtssIpmcMvrStatusIgmpVlanQueryInterval,
                  vtssIpmcMvrStatusIgmpVlanQuerierExpiryTime,
                  vtssIpmcMvrStatusIgmpVlanQuerierVersion,
                  vtssIpmcMvrStatusIgmpVlanQuerierPresentTimeout,
                  vtssIpmcMvrStatusIgmpVlanHostVersion,
                  vtssIpmcMvrStatusIgmpVlanHostPresentTimeout,
                  vtssIpmcMvrStatusIgmpVlanCounterTxQuery,
                  vtssIpmcMvrStatusIgmpVlanCounterTxSpecificQuery,
                  vtssIpmcMvrStatusIgmpVlanCounterRxQuery,
                  vtssIpmcMvrStatusIgmpVlanCounterRxV1Join,
                  vtssIpmcMvrStatusIgmpVlanCounterRxV2Join,
                  vtssIpmcMvrStatusIgmpVlanCounterRxV2Leave,
                  vtssIpmcMvrStatusIgmpVlanCounterRxV3Join,
                  vtssIpmcMvrStatusIgmpVlanCounterRxErrors }
    STATUS      current
    DESCRIPTION
        "A collection of objects."
    ::= { vtssIpmcMvrMibGroups 6 }

vtssIpmcMvrStatusIgmpGroupAddressTableInfoGroup OBJECT-GROUP
    OBJECTS     { vtssIpmcMvrStatusIgmpGroupAddressIfIndex,
                  vtssIpmcMvrStatusIgmpGroupAddressGroupAddress,
                  vtssIpmcMvrStatusIgmpGroupAddressMemberPorts,
                  vtssIpmcMvrStatusIgmpGroupAddressHardwareSwitch }
    STATUS      current
    DESCRIPTION
        "A collection of objects."
    ::= { vtssIpmcMvrMibGroups 7 }

vtssIpmcMvrStatusIgmpGroupSrcListTableInfoGroup OBJECT-GROUP
    OBJECTS     { vtssIpmcMvrStatusIgmpGroupSrcListIfIndex,
                  vtssIpmcMvrStatusIgmpGroupSrcListGroupAddress,
                  vtssIpmcMvrStatusIgmpGroupSrcListPortIndex,
                  vtssIpmcMvrStatusIgmpGroupSrcListHostAddress,
                  vtssIpmcMvrStatusIgmpGroupSrcListGroupFilterMode,
                  vtssIpmcMvrStatusIgmpGroupSrcListFilterTimer,
                  vtssIpmcMvrStatusIgmpGroupSrcListSourceType,
                  vtssIpmcMvrStatusIgmpGroupSrcListSourceTimer,
                  vtssIpmcMvrStatusIgmpGroupSrcListHardwareFilter }
    STATUS      current
    DESCRIPTION
        "A collection of objects."
    ::= { vtssIpmcMvrMibGroups 8 }

vtssIpmcMvrStatusMldVlanTableInfoGroup OBJECT-GROUP
    OBJECTS     { vtssIpmcMvrStatusMldVlanIfIndex,
                  vtssIpmcMvrStatusMldVlanQuerierStatus,
                  vtssIpmcMvrStatusMldVlanActiveQuerierAddress,
                  vtssIpmcMvrStatusMldVlanQuerierUptime,
                  vtssIpmcMvrStatusMldVlanQueryInterval,
                  vtssIpmcMvrStatusMldVlanQuerierExpiryTime,
                  vtssIpmcMvrStatusMldVlanQuerierVersion,
                  vtssIpmcMvrStatusMldVlanQuerierPresentTimeout,
                  vtssIpmcMvrStatusMldVlanHostVersion,
                  vtssIpmcMvrStatusMldVlanHostPresentTimeout,
                  vtssIpmcMvrStatusMldVlanCounterTxQuery,
                  vtssIpmcMvrStatusMldVlanCounterTxSpecificQuery,
                  vtssIpmcMvrStatusMldVlanCounterRxQuery,
                  vtssIpmcMvrStatusMldVlanCounterRxV1Report,
                  vtssIpmcMvrStatusMldVlanCounterRxV1Done,
                  vtssIpmcMvrStatusMldVlanCounterRxV2Report,
                  vtssIpmcMvrStatusMldVlanCounterRxErrors }
    STATUS      current
    DESCRIPTION
        "A collection of objects."
    ::= { vtssIpmcMvrMibGroups 9 }

vtssIpmcMvrStatusMldGroupAddressTableInfoGroup OBJECT-GROUP
    OBJECTS     { vtssIpmcMvrStatusMldGroupAddressIfIndex,
                  vtssIpmcMvrStatusMldGroupAddressGroupAddress,
                  vtssIpmcMvrStatusMldGroupAddressMemberPorts,
                  vtssIpmcMvrStatusMldGroupAddressHardwareSwitch }
    STATUS      current
    DESCRIPTION
        "A collection of objects."
    ::= { vtssIpmcMvrMibGroups 10 }

vtssIpmcMvrStatusMldGroupSrcListTableInfoGroup OBJECT-GROUP
    OBJECTS     { vtssIpmcMvrStatusMldGroupSrcListIfIndex,
                  vtssIpmcMvrStatusMldGroupSrcListGroupAddress,
                  vtssIpmcMvrStatusMldGroupSrcListPortIndex,
                  vtssIpmcMvrStatusMldGroupSrcListHostAddress,
                  vtssIpmcMvrStatusMldGroupSrcListGroupFilterMode,
                  vtssIpmcMvrStatusMldGroupSrcListFilterTimer,
                  vtssIpmcMvrStatusMldGroupSrcListSourceType,
                  vtssIpmcMvrStatusMldGroupSrcListSourceTimer,
                  vtssIpmcMvrStatusMldGroupSrcListHardwareFilter }
    STATUS      current
    DESCRIPTION
        "A collection of objects."
    ::= { vtssIpmcMvrMibGroups 11 }

vtssIpmcMvrControlStatisticsClearInfoGroup OBJECT-GROUP
    OBJECTS     { vtssIpmcMvrControlStatisticsClearIfIndex,
                  vtssIpmcMvrControlStatisticsClearClear }
    STATUS      current
    DESCRIPTION
        "A collection of objects."
    ::= { vtssIpmcMvrMibGroups 12 }

vtssIpmcMvrMibCompliance MODULE-COMPLIANCE
    STATUS      current
    DESCRIPTION
        "The compliance statement for the implementation."

    MODULE      -- this module

    MANDATORY-GROUPS { vtssIpmcMvrConfigGlobalsInfoGroup,
                       vtssIpmcMvrConfigPortTableInfoGroup,
                       vtssIpmcMvrConfigInterfaceTableInfoGroup,
                       vtssIpmcMvrConfigInterfaceTableRowEditorInfoGroup,
                       vtssIpmcMvrConfigVlanPortTableInfoGroup,
                       vtssIpmcMvrStatusIgmpVlanTableInfoGroup,
                       vtssIpmcMvrStatusIgmpGroupAddressTableInfoGroup,
                       vtssIpmcMvrStatusIgmpGroupSrcListTableInfoGroup,
                       vtssIpmcMvrStatusMldVlanTableInfoGroup,
                       vtssIpmcMvrStatusMldGroupAddressTableInfoGroup,
                       vtssIpmcMvrStatusMldGroupSrcListTableInfoGroup,
                       vtssIpmcMvrControlStatisticsClearInfoGroup }

    ::= { vtssIpmcMvrMibCompliances 1 }

END
