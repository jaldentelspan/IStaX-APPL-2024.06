-- *****************************************************************
-- DHCP6-RELAY-MIB:  Microsemi ENT private MIB
-- ****************************************************************

VTSS-DHCP6-RELAY-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    InetAddressIPv6 FROM INET-ADDRESS-MIB
    Integer32 FROM SNMPv2-SMI
    TruthValue FROM SNMPv2-TC
    VTSSInterfaceIndex FROM VTSS-TC
    ;

vtssDhcp6RelayMib MODULE-IDENTITY
    LAST-UPDATED "201804200000Z"
    ORGANIZATION
        "Microsemi Corporation"
    CONTACT-INFO
        "Application support: http://www.microchip.com/support"
    DESCRIPTION
        "This is a private mib for dhcp6_relays"
    REVISION    "201804200000Z"
    DESCRIPTION
        "Initial version"
    ::= { vtssSwitchMgmt 145 }


vtssDhcp6RelayMibObjects OBJECT IDENTIFIER
    ::= { vtssDhcp6RelayMib 1 }

vtssDhcp6RelayConfig OBJECT IDENTIFIER
    ::= { vtssDhcp6RelayMibObjects 2 }

vtssDhcp6RelayConfigTable OBJECT-TYPE
    SYNTAX      SEQUENCE OF VTSSDhcp6RelayConfigEntry
    MAX-ACCESS  not-accessible
    STATUS      current
    DESCRIPTION
        "This is a table to configure Dhcp6_Relay for a specific vlan."
    ::= { vtssDhcp6RelayConfig 1 }

vtssDhcp6RelayConfigEntry OBJECT-TYPE
    SYNTAX      VTSSDhcp6RelayConfigEntry
    MAX-ACCESS  not-accessible
    STATUS      current
    DESCRIPTION
        "Each vlan interface can be configured for dhcp relay"
    INDEX       { vtssDhcp6RelayConfigVlanInterface,
                  vtssDhcp6RelayConfigRelayVlanInterface }
    ::= { vtssDhcp6RelayConfigTable 1 }

VTSSDhcp6RelayConfigEntry ::= SEQUENCE {
    vtssDhcp6RelayConfigVlanInterface       VTSSInterfaceIndex,
    vtssDhcp6RelayConfigRelayVlanInterface  VTSSInterfaceIndex,
    vtssDhcp6RelayConfigRelayDestination    InetAddressIPv6
}

vtssDhcp6RelayConfigVlanInterface OBJECT-TYPE
    SYNTAX      VTSSInterfaceIndex
    MAX-ACCESS  accessible-for-notify
    STATUS      current
    DESCRIPTION
        "Vlan Interface."
    ::= { vtssDhcp6RelayConfigEntry 1 }

vtssDhcp6RelayConfigRelayVlanInterface OBJECT-TYPE
    SYNTAX      VTSSInterfaceIndex
    MAX-ACCESS  accessible-for-notify
    STATUS      current
    DESCRIPTION
        "Relay Vlan Interface."
    ::= { vtssDhcp6RelayConfigEntry 2 }

vtssDhcp6RelayConfigRelayDestination OBJECT-TYPE
    SYNTAX      InetAddressIPv6
    MAX-ACCESS  read-write
    STATUS      current
    DESCRIPTION
        "Ipv6 address of the DHCP server that requests are being relayed to. The
         default address is the multicast address ALL_DHCP_SERVERS (FF05::1:3)"
    ::= { vtssDhcp6RelayConfigEntry 3 }

vtssDhcp6RelayStatus OBJECT IDENTIFIER
    ::= { vtssDhcp6RelayMibObjects 3 }

vtssDhcp6RelayStatusStatisticsTable OBJECT-TYPE
    SYNTAX      SEQUENCE OF VTSSDhcp6RelayStatusStatisticsEntry
    MAX-ACCESS  not-accessible
    STATUS      current
    DESCRIPTION
        "This is a table to containing statistics for Dhcp6_Relay for a specific
         vlan. Statistics can be cleared"
    ::= { vtssDhcp6RelayStatus 1 }

vtssDhcp6RelayStatusStatisticsEntry OBJECT-TYPE
    SYNTAX      VTSSDhcp6RelayStatusStatisticsEntry
    MAX-ACCESS  not-accessible
    STATUS      current
    DESCRIPTION
        "Vlan interface being serviced by relay agent"
    INDEX       { vtssDhcp6RelayStatusStatisticsVlanInterface,
                  vtssDhcp6RelayStatusStatisticsRelayVlanInterface }
    ::= { vtssDhcp6RelayStatusStatisticsTable 1 }

VTSSDhcp6RelayStatusStatisticsEntry ::= SEQUENCE {
    vtssDhcp6RelayStatusStatisticsVlanInterface       VTSSInterfaceIndex,
    vtssDhcp6RelayStatusStatisticsRelayVlanInterface  VTSSInterfaceIndex,
    vtssDhcp6RelayStatusStatisticsTxToServer          Integer32,
    vtssDhcp6RelayStatusStatisticsRxFromServer        Integer32,
    vtssDhcp6RelayStatusStatisticsServerPktDropped    Integer32,
    vtssDhcp6RelayStatusStatisticsTxToClient          Integer32,
    vtssDhcp6RelayStatusStatisticsRxFromClient        Integer32,
    vtssDhcp6RelayStatusStatisticsClientPktDropped    Integer32
}

vtssDhcp6RelayStatusStatisticsVlanInterface OBJECT-TYPE
    SYNTAX      VTSSInterfaceIndex
    MAX-ACCESS  accessible-for-notify
    STATUS      current
    DESCRIPTION
        "Vlan Interface."
    ::= { vtssDhcp6RelayStatusStatisticsEntry 1 }

vtssDhcp6RelayStatusStatisticsRelayVlanInterface OBJECT-TYPE
    SYNTAX      VTSSInterfaceIndex
    MAX-ACCESS  accessible-for-notify
    STATUS      current
    DESCRIPTION
        "Relay Vlan Interface."
    ::= { vtssDhcp6RelayStatusStatisticsEntry 2 }

vtssDhcp6RelayStatusStatisticsTxToServer OBJECT-TYPE
    SYNTAX      Integer32
    MAX-ACCESS  read-write
    STATUS      current
    DESCRIPTION
        "Number of packets sent to dhcpv6 server from vlan."
    ::= { vtssDhcp6RelayStatusStatisticsEntry 3 }

vtssDhcp6RelayStatusStatisticsRxFromServer OBJECT-TYPE
    SYNTAX      Integer32
    MAX-ACCESS  read-write
    STATUS      current
    DESCRIPTION
        "Number of packets received from dhcpv6 server on vlan."
    ::= { vtssDhcp6RelayStatusStatisticsEntry 4 }

vtssDhcp6RelayStatusStatisticsServerPktDropped OBJECT-TYPE
    SYNTAX      Integer32
    MAX-ACCESS  read-write
    STATUS      current
    DESCRIPTION
        "Number of packets from dhcpv6 server to vlan dropped."
    ::= { vtssDhcp6RelayStatusStatisticsEntry 5 }

vtssDhcp6RelayStatusStatisticsTxToClient OBJECT-TYPE
    SYNTAX      Integer32
    MAX-ACCESS  read-write
    STATUS      current
    DESCRIPTION
        "Number of packets sent to dhcpv6 client from vlan."
    ::= { vtssDhcp6RelayStatusStatisticsEntry 6 }

vtssDhcp6RelayStatusStatisticsRxFromClient OBJECT-TYPE
    SYNTAX      Integer32
    MAX-ACCESS  read-write
    STATUS      current
    DESCRIPTION
        "Number of packets received from dhcpv6 client on vlan."
    ::= { vtssDhcp6RelayStatusStatisticsEntry 7 }

vtssDhcp6RelayStatusStatisticsClientPktDropped OBJECT-TYPE
    SYNTAX      Integer32
    MAX-ACCESS  read-write
    STATUS      current
    DESCRIPTION
        "Number of packets from dhcpv6 client to vlan dropped."
    ::= { vtssDhcp6RelayStatusStatisticsEntry 8 }

vtssDhcp6RelayStatusStatisticsInterfaceMissingLeaf OBJECT IDENTIFIER
    ::= { vtssDhcp6RelayStatus 2 }

vtssDhcp6RelayStatusStatisticsInterfaceMissingLeafNumIntfMissing OBJECT-TYPE
    SYNTAX      Integer32
    MAX-ACCESS  read-only
    STATUS      current
    DESCRIPTION
        "Number of server packets dropped because interface option is missing."
    ::= { vtssDhcp6RelayStatusStatisticsInterfaceMissingLeaf 1 }

vtssDhcp6RelayControl OBJECT IDENTIFIER
    ::= { vtssDhcp6RelayMibObjects 4 }

vtssDhcp6RelayControlLeaf OBJECT IDENTIFIER
    ::= { vtssDhcp6RelayControl 1 }

vtssDhcp6RelayControlLeafClearAllStatistics OBJECT-TYPE
    SYNTAX      TruthValue
    MAX-ACCESS  read-write
    STATUS      current
    DESCRIPTION
        "The action to clear all statistics. True clears the statistics data.
         False does nothing."
    ::= { vtssDhcp6RelayControlLeaf 1 }

vtssDhcp6RelayMibConformance OBJECT IDENTIFIER
    ::= { vtssDhcp6RelayMib 2 }

vtssDhcp6RelayMibCompliances OBJECT IDENTIFIER
    ::= { vtssDhcp6RelayMibConformance 1 }

vtssDhcp6RelayMibGroups OBJECT IDENTIFIER
    ::= { vtssDhcp6RelayMibConformance 2 }

vtssDhcp6RelayConfigTableInfoGroup OBJECT-GROUP
    OBJECTS     { vtssDhcp6RelayConfigVlanInterface,
                  vtssDhcp6RelayConfigRelayVlanInterface,
                  vtssDhcp6RelayConfigRelayDestination }
    STATUS      current
    DESCRIPTION
        "A collection of objects."
    ::= { vtssDhcp6RelayMibGroups 1 }

vtssDhcp6RelayStatusStatisticsTableInfoGroup OBJECT-GROUP
    OBJECTS     { vtssDhcp6RelayStatusStatisticsVlanInterface,
                  vtssDhcp6RelayStatusStatisticsRelayVlanInterface,
                  vtssDhcp6RelayStatusStatisticsTxToServer,
                  vtssDhcp6RelayStatusStatisticsRxFromServer,
                  vtssDhcp6RelayStatusStatisticsServerPktDropped,
                  vtssDhcp6RelayStatusStatisticsTxToClient,
                  vtssDhcp6RelayStatusStatisticsRxFromClient,
                  vtssDhcp6RelayStatusStatisticsClientPktDropped }
    STATUS      current
    DESCRIPTION
        "A collection of objects."
    ::= { vtssDhcp6RelayMibGroups 2 }

vtssDhcp6RelayStatusStatisticsInterfaceMissingLeafInfoGroup OBJECT-GROUP
    OBJECTS     {                   vtssDhcp6RelayStatusStatisticsInterfaceMissingLeafNumIntfMissing }
    STATUS      current
    DESCRIPTION
        "A collection of objects."
    ::= { vtssDhcp6RelayMibGroups 3 }

vtssDhcp6RelayControlLeafInfoGroup OBJECT-GROUP
    OBJECTS     { vtssDhcp6RelayControlLeafClearAllStatistics }
    STATUS      current
    DESCRIPTION
        "A collection of objects."
    ::= { vtssDhcp6RelayMibGroups 4 }

vtssDhcp6RelayMibCompliance MODULE-COMPLIANCE
    STATUS      current
    DESCRIPTION
        "The compliance statement for the implementation."

    MODULE      -- this module

    MANDATORY-GROUPS { vtssDhcp6RelayConfigTableInfoGroup,
                       vtssDhcp6RelayStatusStatisticsTableInfoGroup,
                       vtssDhcp6RelayStatusStatisticsInterfaceMissingLeafInfoGroup,
                       vtssDhcp6RelayControlLeafInfoGroup }

    ::= { vtssDhcp6RelayMibCompliances 1 }

END
