-- *****************************************************************
-- USERS-MIB:  Microsemi ENT private MIB
-- ****************************************************************

VTSS-USERS-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    vtssSwitchMgmt FROM VTSS-SMI
    Unsigned32 FROM SNMPv2-SMI
    TruthValue FROM SNMPv2-TC
    VTSSDisplayString FROM VTSS-TC
    VTSSRowEditorState FROM VTSS-TC
    ;

vtssUsersMib MODULE-IDENTITY
    LAST-UPDATED "201601190000Z"
    ORGANIZATION
        "Microsemi Corporation"
    CONTACT-INFO
        "Application support: http://www.microchip.com/support"
    DESCRIPTION
        "This is a private version of Users"
    REVISION    "201601190000Z"
    DESCRIPTION
        "Updated the maximum length of password"
    REVISION    "201407010000Z"
    DESCRIPTION
        "Initial version"
    ::= { vtssSwitchMgmt 58 }


vtssUsersMibObjects OBJECT IDENTIFIER
    ::= { vtssUsersMib 1 }

vtssUsersConfig OBJECT IDENTIFIER
    ::= { vtssUsersMibObjects 2 }

vtssUsersConfigTable OBJECT-TYPE
    SYNTAX      SEQUENCE OF VTSSUsersConfigEntry
    MAX-ACCESS  not-accessible
    STATUS      current
    DESCRIPTION
        "The table is Users onfiguration table. The index is user name."
    ::= { vtssUsersConfig 1 }

vtssUsersConfigEntry OBJECT-TYPE
    SYNTAX      VTSSUsersConfigEntry
    MAX-ACCESS  not-accessible
    STATUS      current
    DESCRIPTION
        "Each entry has a set of parameters"
    INDEX       { vtssUsersConfigUsername }
    ::= { vtssUsersConfigTable 1 }

VTSSUsersConfigEntry ::= SEQUENCE {
    vtssUsersConfigUsername   VTSSDisplayString,
    vtssUsersConfigPrivilege  Unsigned32,
    vtssUsersConfigEncrypted  TruthValue,
    vtssUsersConfigPassword   VTSSDisplayString,
    vtssUsersConfigAction     VTSSRowEditorState
}

vtssUsersConfigUsername OBJECT-TYPE
    SYNTAX      VTSSDisplayString (SIZE(0..31))
    MAX-ACCESS  accessible-for-notify
    STATUS      current
    DESCRIPTION
        "Name of user."
    ::= { vtssUsersConfigEntry 1 }

vtssUsersConfigPrivilege OBJECT-TYPE
    SYNTAX      Unsigned32
    MAX-ACCESS  read-write
    STATUS      current
    DESCRIPTION
        "Privilege level of the user."
    ::= { vtssUsersConfigEntry 2 }

vtssUsersConfigEncrypted OBJECT-TYPE
    SYNTAX      TruthValue
    MAX-ACCESS  read-write
    STATUS      current
    DESCRIPTION
        "The flag indicates the password is encrypted or not. TRUE means the
         password is encrypted. FALSE means the password is plain text."
    ::= { vtssUsersConfigEntry 3 }

vtssUsersConfigPassword OBJECT-TYPE
    SYNTAX      VTSSDisplayString (SIZE(0..128))
    MAX-ACCESS  read-write
    STATUS      current
    DESCRIPTION
        "Password of the user. The password length depends on the type of
         password. If the password is encrypted, then the length is 128. If it
         is unencrypted, then the maximum length is 31."
    ::= { vtssUsersConfigEntry 4 }

vtssUsersConfigAction OBJECT-TYPE
    SYNTAX      VTSSRowEditorState
    MAX-ACCESS  read-write
    STATUS      current
    DESCRIPTION
        "Action"
    ::= { vtssUsersConfigEntry 100 }

vtssUsersConfigTableRowEditor OBJECT IDENTIFIER
    ::= { vtssUsersConfig 2 }

vtssUsersConfigTableRowEditorUsername OBJECT-TYPE
    SYNTAX      VTSSDisplayString (SIZE(0..31))
    MAX-ACCESS  read-write
    STATUS      current
    DESCRIPTION
        "Name of user."
    ::= { vtssUsersConfigTableRowEditor 1 }

vtssUsersConfigTableRowEditorPrivilege OBJECT-TYPE
    SYNTAX      Unsigned32
    MAX-ACCESS  read-write
    STATUS      current
    DESCRIPTION
        "Privilege level of the user."
    ::= { vtssUsersConfigTableRowEditor 2 }

vtssUsersConfigTableRowEditorEncrypted OBJECT-TYPE
    SYNTAX      TruthValue
    MAX-ACCESS  read-write
    STATUS      current
    DESCRIPTION
        "The flag indicates the password is encrypted or not. TRUE means the
         password is encrypted. FALSE means the password is plain text."
    ::= { vtssUsersConfigTableRowEditor 3 }

vtssUsersConfigTableRowEditorPassword OBJECT-TYPE
    SYNTAX      VTSSDisplayString (SIZE(0..128))
    MAX-ACCESS  read-write
    STATUS      current
    DESCRIPTION
        "Password of the user. The password length depends on the type of
         password. If the password is encrypted, then the length is 128. If it
         is unencrypted, then the maximum length is 31."
    ::= { vtssUsersConfigTableRowEditor 4 }

vtssUsersConfigTableRowEditorAction OBJECT-TYPE
    SYNTAX      VTSSRowEditorState
    MAX-ACCESS  read-write
    STATUS      current
    DESCRIPTION
        "Action"
    ::= { vtssUsersConfigTableRowEditor 100 }

vtssUsersMibConformance OBJECT IDENTIFIER
    ::= { vtssUsersMib 2 }

vtssUsersMibCompliances OBJECT IDENTIFIER
    ::= { vtssUsersMibConformance 1 }

vtssUsersMibGroups OBJECT IDENTIFIER
    ::= { vtssUsersMibConformance 2 }

vtssUsersConfigTableInfoGroup OBJECT-GROUP
    OBJECTS     { vtssUsersConfigUsername, vtssUsersConfigPrivilege,
                  vtssUsersConfigEncrypted, vtssUsersConfigPassword,
                  vtssUsersConfigAction }
    STATUS      current
    DESCRIPTION
        "A collection of objects."
    ::= { vtssUsersMibGroups 1 }

vtssUsersConfigTableRowEditorInfoGroup OBJECT-GROUP
    OBJECTS     { vtssUsersConfigTableRowEditorUsername,
                  vtssUsersConfigTableRowEditorPrivilege,
                  vtssUsersConfigTableRowEditorEncrypted,
                  vtssUsersConfigTableRowEditorPassword,
                  vtssUsersConfigTableRowEditorAction }
    STATUS      current
    DESCRIPTION
        "A collection of objects."
    ::= { vtssUsersMibGroups 2 }

vtssUsersMibCompliance MODULE-COMPLIANCE
    STATUS      current
    DESCRIPTION
        "The compliance statement for the implementation."

    MODULE      -- this module

    MANDATORY-GROUPS { vtssUsersConfigTableInfoGroup,
                       vtssUsersConfigTableRowEditorInfoGroup }

    ::= { vtssUsersMibCompliances 1 }

END
